FME workspace INSPIRE_WFS.fmw
Title: INSPIRE_WFS.fmw
Description: This WFS workspace reads from an INSPIRE staging PostGIS database and uses WFS to publish GML via the data streaming service, based on the query parameters provided by the WFS client. The Loader workspaces (INSPIRE_WFS_A1.CadastralParcels.Loader.fmw, INSPIRE_WFS_A1.GeoNames.Loader.fmw) handle data loading, reprojection and schema mapping to the databases 'INSPIRE like' data model. 
INSPIRE_WFS.fmw is a WFS 'service broker' workspace. This just needs to be published to the data streaming service and will accept WFS GET or POST requests (GetCapabilities, DescribeFeature and GetFeature) and generate the appropriate responses as XML or GML data streams (GetCapabilities, Describe feature XML docs or GML features). Supports XMLfilters which is something our built in WFS did not do. 
Also, configured to support FME Data Inspector as a WFS client. Note that this requires FME Server 2014 or later to function. This is required to support the new GML writer.
Requirements: FME 2014 14234 or higher

Parameters:
- SERVICE = WFS   # Service
- REQUEST = GetFeature   # Request
- VERSION = 1.1   # Version
- TYPENAME = CadastralParcel   # Type name
- FILTER =   # Filter
- bboxWest =   # Bounding box - minimum X coordinate
- bboxSouth =   # Bounding box - minimum Y coordinate
- bboxEast =   # Bounding box - maximum X coordinate
- bboxNorth =   # Bounding box - maximum Y coordinate
- bboxCRS =   # Bounding box - coordinate system
- BBOX =   # Bounding box
- MAXFEATURES = 5000   # MaxFeatures
- DestDataset_INSPIRE = .\outGML.xml   # Destination Geography Markup Language (GML) File
- Themes = NamedPlace CadastralParcel
- REPOSITORY = INSPIRE   # Repository

Readers:
- TEXTLINE_1: TEXTLINE from .\source_get.txt

Writers:
- TEXTLINE_2: TEXTLINE to .\outText.xml
- INSPIRE_1: INSPIRE to $(DestDataset_INSPIRE)

AttributeCreator
    ATTR_LIST = workSpaceURL,$(FME_SERVER_WEB_URL)/fmedatastreaming/$(REPOSITORY)/INSPIRE_WFS.fmw,theme,$(Themes)
    -> XMLTemplater_2 [input 1]
    -> AttributeSplitter_2

Bookmark: Docs
Docs
Utilities
    VERSION = 1.1
    SERVICE = WFS
    REQUEST = GetFeature

Bookmark: Check Input
text_line (reader TEXTLINE_1)
    attributes: text_line_data buffer
    -> XMLValidator
    -> Logger_text_line
Logger_text_line
    MESSAGE = Source text stream feature is:
    MAXFEATS = 2
    MAXCOORDS = 20
Note: Determines whether the input is a GET or POST request / by evaluating whether the file contains valid XML: / -> If it contains valid XML then it is a POST request / -> If it does not contain valid XML then it is assumed to be / a URL for a GET request
XMLValidator
    VAL_MODE_1 = Syntax Only
    XML_ATTR_TEXT = text_line_data
    LIST_NAME = _xml_error
    XML_INPUT_TYPE = Attribute Specifying XML Text
    LIMIT_ERRORS = No
    PASSED -> XQueryExtractor_2
    FAILED -> Logger_FAILED
    FAILED -> ParameterFetcher_2
Logger_FAILED [off]
    MESSAGE = XML Invalid:
    MAXFEATS = 3
    MAXCOORDS = 20

Bookmark: POST: GetCapabilities
Note: Retrieves the value of the service attribute
XQueryExtractor_2
    XML_TYPE = Attribute specifying XML
    RESULT_ATTRIBUTE = service
    XML_REMOVE_SOURCE_ATTR = No
    SEPARATOR_VALUE = ,
    QUERY_EXPR:
      declare namespace wfs='http://www.opengis.net/wfs';

      string(/wfs:GetCapabilities/@service)
    XML_ATTR = text_line_data
    WRITE_XML_HEADER = No
    RESULT_TYPE_NAME = Separated values
    XQUERY_TYPE = XQuery expression
    QUERY_RESULTS -> Tester_3
Note: Determines whether the extracted XML contains WFS as the service value / -> If it contains WFS, then direct the output to GetCapabilities / -> If it does not contain WFS, then direct the output to DescribeFeatureType
Note: Determines whether the result attribute value is populated / -> If yes, a DescribeFeatureType request is processed / -> If no, a GetFeature request is processed
Tester_3
    TEST_MODE = Automatic
    TEST_DESCRIPTION = ""
    BOOL_OP = OR
    TEST_CLAUSE = TEST @Value(service) != WFS
    PASSED -> XQueryExtractor
    FAILED -> AttributeCreator_4
AttributeCreator_4
    ATTR_LIST = workSpaceURL,$(FME_SERVER_WEB_URL)/fmedatastreaming/$(REPOSITORY)/INSPIRE_WFS.fmw,theme,NamedPlace
    -> XMLTemplater_2 [input 1]

Bookmark: POST: DescribeFeatureType
XQueryExtractor
    XML_TYPE = Attribute specifying XML
    RESULT_ATTRIBUTE = _result
    XML_REMOVE_SOURCE_ATTR = No
    SEPARATOR_VALUE = ,
    QUERY_EXPR:
      declare namespace wfs='http://www.opengis.net/wfs';

      string(/wfs:DescribeFeatureType/wfs:TypeName)
    XML_ATTR = text_line_data
    WRITE_XML_HEADER = No
    RESULT_TYPE_NAME = Separated values
    XQUERY_TYPE = XQuery expression
    QUERY_RESULTS -> Tester_2
    INVALID -> Tester_2
Tester_2
    TEST_MODE = Automatic
    TEST_DESCRIPTION = ""
    BOOL_OP = OR
    TEST_CLAUSE = TEST @Value(_result) = ""
    FAILED -> AttributeSplitter
    PASSED -> NamedPlace [input 1]
AttributeSplitter
    LIST_NAME = theme
    ATTR_NAME = _result
    DELIMITER = :
    TRIM_OPTION = Both
    DROP_EMPTY_PARTS = No
    -> ListIndexer
ListIndexer
    LIST_ATTR = theme{}
    INDEX = 1
    -> AttributeCreator_3
AttributeCreator_3
    ATTR_LIST = workSpaceURL,$(FME_SERVER_WEB_URL)/fmedatastreaming/$(REPOSITORY)/INSPIRE_WFS.fmw
    -> AttributeFilter_2

Bookmark: Process GET Request
Note: Retrieves parameters from URL
Note: GetFeature Request: / 'http://inspire-safe-software.fmecloud.com:80/fmedatastreaming/INSPIRE/INSPIRE_WFS.fmw?SERVICE=WFS&VERSION=1.1.0&REQUEST=GetFeature&TYPENAME=NamedPlace&MAXFEATURES=1111'
ParameterFetcher_2
    ATTR_LIST = _VERSION {$(VERSION)} _REQUEST {$(REQUEST)} _SERVICE {$(SERVICE)} _TYPENAME {$(TYPENAME)} _Filter {$(FILTER)} _BBOX {$(BBOX)} _bboxWest {$(bboxWest)}
    -> TestFilter
Note: Drive output based on the REQUEST parameter
Note: Unfiltered directs to a GetCapabilities response
TestFilter
    TEST_LIST = BOOL_OP,OR,COMPOSITE_TEST,<Unused>,TEST_CLAUSE,"TEST @Value(_REQUEST) CONTAINS GetCapabilities",GetCapabilities,BOOL_OP,OR,COMPOSITE_TEST,<Unused>,TEST_CLAUSE,"TEST @Value(_REQUEST) CONTAINS DescribeFeatureType",DescribeFeatureType,BOOL_OP,OR,COMPOSITE_TEST,<Unused>,TEST_CLAUSE,"TEST @Value(_REQUEST) CONTAINS GetFeature",GetFeature
    DEFAULT_VALUE = <UNFILTERED>
    GetCapabilities -> AttributeCreator
    GetFeature -> AttributeFilter
    DescribeFeatureType -> AttributeFilter_2
    <UNFILTERED> -> AttributeCreator
Note: Select feature type based on / TypeName parameter
AttributeFilter
    ATTR_NAME = _TYPENAME
    ATTR_VALUES = NamedPlace,CadastralParcel,<EMPTY>,<MISSING>,<NULL>,<UNFILTERED>
    NamedPlace -> NamedPlace [input 2]
    CadastralParcel -> CadastralParcel

Bookmark: GetCapabilities
AttributeSplitter_2
    LIST_NAME = theme
    ATTR_NAME = theme
    DELIMITER = " "
    TRIM_OPTION = None
    DROP_EMPTY_PARTS = No
    -> ListExploder
ListExploder
    INDEX_ATTR = _element_index
    MODE = List Elements and Original Attributes
    LIST_ATTR = theme{}
    LIST_FOUND -> AttributeFilter_3
Note: Filters attributes based on theme, either / NamedPlace or CadastralParcels
Note: DescribeFeatureType response is / obtained from the XML schema file
AttributeFilter_3
    ATTR_NAME = theme
    ATTR_VALUES = NamedPlace,CadastralParcel,<EMPTY>,<MISSING>,<NULL>,<UNFILTERED>
    NamedPlace -> XMLTemplater_2 [input 2]
    CadastralParcel -> XMLTemplater_2 [input 3]
Note: Populates an XML document with feature / attribute values based on a XML template
XMLTemplater_2
    RESULT_ATTRIBUTE = _result
    ROOT_QUERY_EXPR:
      <wfs:WFS_Capabilities xmlns:gml="http://www.opengis.net/gml"
      xmlns:ogc="http://www.opengis.net/ogc" xmlns:ows="http://www.opengis.net/ows"
      xmlns:wfs="http://www.opengis.net/wfs" xmlns:xlink="http://www.w3.org/1999/xlink"
      xmlns:xsi="http://www.w3.org/2001/XMLSchema-instance" updateSequence="0" version="1.1.0"
      xsi:schemaLocation="http://www.opengis.net/wfs ../wfs/1.1.0/WFS.xsd">
      <!-- Service Identification Section -->
      <ows:ServiceIdentification>
      <ows:Title>
      WFS Service Compliant with OGC WFS Specification Version 1.1.0
      </ows:Title>
      <ows:Abstract>
      An OGC WFS Service created by Safe Software's FME Server. This is a template only and Safe Software provides no warrantee for the data supplied by the web service.
      </ows:Abstract>
      <ows:ServiceType>WFS</ows:ServiceType>
      <ows:ServiceTypeVersion>1.1.0</ows:ServiceTypeVersion>
      <ows:Fees>None</ows:Fees>
      <ows:AccessConstraints>None</ows:AccessConstraints>
      </ows:ServiceIdentification>
      <!-- Service Provider Section -->
      <ows:ServiceProvider>
      <ows:ProviderName>Safe Software</ows:ProviderName>
      <ows:ProviderSite xlink:href="www.safe.com"/>
      <ows:ServiceContact>
      <ows:IndividualName>Safe Software Inc.</ows:IndividualName>
      <ows:PositionName>Safe Software Inc.</ows:PositionName>
      <ows:ContactInfo>
      <ows:Phone>
      <ows:Voice>1-604-501-9985</ows:Voice>
      <ows:Facsimile>1-604-501-9965</ows:Facsimile>
      </ows:Phone>
      <ows:Address>
      <ows:City>Surrey</ows:City>
      <ows:PostalCode>V3W 1J8</ows:PostalCode>
      <ows:Country>Canada</ows:Country>
      <ows:ElectronicMailAddress>info@safe.com</ows:ElectronicMailAddress>
      </ows:Address>
      <ows:OnlineResource xlink:href="http://safe.com/about/contact"/>
      <ows:HoursOfService>24x7</ows:HoursOfService>
      <ows:ContactInstructions>none</ows:ContactInstructions>
      </ows:ContactInfo>
      <ows:Role>Developer</ows:Role>
      </ows:ServiceContact>
      </ows:ServiceProvider>
      <!-- Operations Metadata Section -->
      <ows:OperationsMetadata>
      <ows:Operation name="GetCapabilities">
      <ows:DCP>
      <ows:HTTP>
      <ows:Get xlink:href="{fme:get-attribute("workSpaceURL")}"/>
      <ows:Post xlink:href="{fme:get-attribute("workSpaceURL")}"/>
      </ows:HTTP>
      </ows:DCP>
      <ows:Parameter name="AcceptVersions">
      <ows:Value>1.1.0</ows:Value>
      <ows:Value>1.0.0</ows:Value>
      </ows:Parameter>
      <ows:Parameter name="AcceptFormats">
      <ows:Value>text/xml</ows:Value>
      </ows:Parameter>
      <ows:Parameter name="Sections">
      <ows:Value>ServiceIdentification</ows:Value>
      <ows:Value>ServiceProvider</ows:Value>
      <ows:Value>OperationsMetadata</ows:Value>
      <ows:Value>FeatureTypeList</ows:Value>
      <ows:Value>ServesGMLObjectTypeList</ows:Value>
      <ows:Value>SupportsGMLObjectTypeList</ows:Value>
      </ows:Parameter>
      </ows:Operation>
      <ows:Operation name="GetFeature">
      <ows:DCP>
      <ows:HTTP>
      <ows:Get xlink:href="{fme:get-attribute("workSpaceURL")}"/>
      <ows:Post xlink:href="{fme:get-attribute("workSpaceURL")}"/>
      </ows:HTTP>
      </ows:DCP>
      <ows:Parameter name="resultType">
      <ows:Value>results</ows:Value>
      </ows:Parameter>
      <ows:Parameter name="outputFormat">
      <ows:Value>text/xml; subtype=gml/3.1.1</ows:Value>
      </ows:Parameter>
      </ows:Operation>
      <ows:Operation name="DescribeFeatureType">
      <ows:DCP>
      <ows:HTTP>
      <ows:Get xlink:href="{fme:get-attribute("workSpaceURL")}"/>
      <ows:Post xlink:href="{fme:get-attribute("workSpaceURL")}"/>
      </ows:HTTP>
      </ows:DCP>
      <ows:Parameter name="outputFormat">
      <ows:Value>text/xml; subtype=gml/3.1.1</ows:Value>
      </ows:Parameter>
      </ows:Operation>
      </ows:OperationsMetadata>
      <!-- Feature Type List Section -->
      <wfs:FeatureTypeList>

      {fme:process-features("NAMEDPLACE")}
      {fme:process-features("CADASTRALPARCEL")}

      </wfs:FeatureTypeList>
      <!-- Supports GML Object Type List Section -->
      <wfs:SupportsGMLObjectTypeList>
      <wfs:GMLObjectType>
      <wfs:Name>gml:AbstractGMLFeatureType</wfs:Name>
      <wfs:OutputFormats>
      <wfs:Format>text/xml; subtype=gml3.1.1</wfs:Format>
      </wfs:OutputFormats>
      </wfs:GMLObjectType>
      </wfs:SupportsGMLObjectTypeList>
      <!-- Filter Capabilities Section -->
      <ogc:Filter_Capabilities>
      <ogc:Spatial_Capabilities>
      <ogc:GeometryOperands>
      <ogc:GeometryOperand>gml:Envelope</ogc:GeometryOperand>
      </ogc:GeometryOperands>
      <ogc:SpatialOperators>
      <ogc:SpatialOperator name="BBOX"/>
      </ogc:SpatialOperators>
      </ogc:Spatial_Capabilities>
      <ogc:Scalar_Capabilities/>
      <ogc:Id_Capabilities>
      <ogc:EID/>
      <ogc:FID/>
      </ogc:Id_Capabilities>
      </ogc:Filter_Capabilities>
      </wfs:WFS_Capabilities>
    NAMEDPLACE_QUERY_EXPR:
      <wfs:FeatureType
      xmlns="urn:x-inspire:specification:gmlas:GeographicalNames:3.0"
      xmlns:base="urn:x-inspire:specification:gmlas:BaseTypes:3.2"
      xmlns:gmd="http://www.isotc211.org/2005/gmd"
      xmlns:xlink="http://www.w3.org/1999/xlink"
      xmlns:gml="http://www.opengis.net/gml"
      xmlns:ogc="http://www.opengis.net/ogc"
      xmlns:ows="http://www.opengis.net/ows"
      xmlns:wfs="http://www.opengis.net/wfs"
      xmlns:xsi="http://www.w3.org/2001/XMLSchema-instance" updateSequence="0" version="1.1.0"
      xsi:schemaLocation="http://www.opengis.net/wfs ../wfs/1.1.0/WFS.xsd">
      <wfs:Name>{fme:get-attribute("theme")}</wfs:Name>
      <wfs:Title>{fme:get-attribute("theme")}</wfs:Title>
      <wfs:Abstract/>
      <wfs:DefaultSRS>EPSG:4326</wfs:DefaultSRS>
      <wfs:OutputFormats>
      <wfs:Format>text/xml; subtype=gml/3.1.1</wfs:Format>
      </wfs:OutputFormats>
      <ows:WGS84BoundingBox>
      <ows:LowerCorner>-20 20</ows:LowerCorner>
      <ows:UpperCorner>60 80</ows:UpperCorner>
      </ows:WGS84BoundingBox>
      </wfs:FeatureType>
    VISIBLE_QUERY_VALIDATE = Yes
    CADASTRALPARCEL_QUERY_EXPR:
      <wfs:FeatureType
      xmlns="urn:x-inspire:specification:gmlas:CadastralParcels:3.0"
      xmlns:base="urn:x-inspire:specification:gmlas:BaseTypes:3.2"
      xmlns:gmd="http://www.isotc211.org/2005/gmd"
      xmlns:xlink="http://www.w3.org/1999/xlink"
      xmlns:gml="http://www.opengis.net/gml"
      xmlns:ogc="http://www.opengis.net/ogc"
      xmlns:ows="http://www.opengis.net/ows"
      xmlns:wfs="http://www.opengis.net/wfs"
      xmlns:xsi="http://www.w3.org/2001/XMLSchema-instance" updateSequence="0" version="1.1.0"
      xsi:schemaLocation="http://www.opengis.net/wfs ../wfs/1.1.0/WFS.xsd">
      <wfs:Name>{fme:get-attribute("theme")}</wfs:Name>
      <wfs:Title>{fme:get-attribute("theme")}</wfs:Title>
      <wfs:Abstract/>
      <wfs:DefaultSRS>EPSG:4326</wfs:DefaultSRS>
      <wfs:OutputFormats>
      <wfs:Format>text/xml; subtype=gml/3.1.1</wfs:Format>
      </wfs:OutputFormats>
      <ows:WGS84BoundingBox>
      <ows:LowerCorner>-20 20</ows:LowerCorner>
      <ows:UpperCorner>60 80</ows:UpperCorner>
      </ows:WGS84BoundingBox>
      </wfs:FeatureType>
    OUTPUT_XML_HEADER = Yes
    -> XMLFormatter

Bookmark: DescribeFeatureType
AttributeFilter_2
    ATTR_NAME = _TYPENAME
    ATTR_VALUES = NamedPlace,CadastralParcel,<EMPTY>,<MISSING>,<NULL>,<UNFILTERED>
    NamedPlace -> AttributeFileReader
    CadastralParcel -> AttributeFileReader_2
AttributeFileReader
    CHAR_ENCODING = utf-8
    FILE_NAME = .\schemas\GeographicalNames.xsd
    DEST_ATTR = _result
    -> XMLFormatter
AttributeFileReader_2
    CHAR_ENCODING = utf-8
    FILE_NAME = .\schemas\CadastralParcels.xsd
    DEST_ATTR = _result
    -> XMLFormatter

Bookmark: Stream XML Output
XMLFormatter
    REMOVE_EMPTY_ELEMENT = No
    XML_OUTPUT_ATTR = text_line_data
    OUTPUT_ENCODING = utf-8
    XML_ATTR_TEXT = _result
    FORMATTING_CHOICE = Pretty-Print XML
    NAMESPACE_CLEANUP = Yes
    LIST_NAME = _xml_error
    COLLAPSE_EMPTY_ELEMENT = No
    SCHEMALOC_CLEANUP = No
    XML_INPUT_TYPE = Attribute Specifying XML Text
    XML_OUTPUT_TYPE = Attribute
    WHITESPACE_HANDLING = Preserve all whitespace
    REMOVE_ALL_COMMENT = No
    FAILED -> Logger_FAILED_2
    PASSED -> text_line (writer TEXTLINE_2)
Logger_FAILED_2
    MESSAGE = OUPUT Format Failed:
    MAXFEATS = 20
    MAXCOORDS = 20
Note: Text File Writer used for / GetCapabilities and / DescribeFeature responses
text_line (writer TEXTLINE_2)
    attributes: text_line_data buffer

Bookmark: GetFeature
NamedPlace
    bboxWest = $(bboxWest)
    _FILTER = @Value(_Filter)
    BBOX = $(BBOX)
    bboxEast = $(bboxEast)
    bboxNorth = $(bboxNorth)
    bboxSouth = $(bboxSouth)
    POSTbody = text_line_data
    -> Counter
CadastralParcel
    bboxWest = $(bboxWest)
    _FILTER = @Value(_Filter)
    BBOX = $(BBOX)
    bboxEast = $(bboxEast)
    bboxNorth = $(bboxNorth)
    bboxSouth = $(bboxSouth)
    -> Counter_2

Bookmark: MaxFeatures
Counter
    SCOPE = Global
    START = 0
    DOMAIN = counter
    CNT_ATTR = _count
    -> Tester
Note: Limits the number of features written / by the MAXFEATURES value
Tester
    TEST_MODE = Automatic
    TEST_DESCRIPTION = ""
    BOOL_OP = OR
    TEST_CLAUSE = TEST @Value(_count) < $(MAXFEATURES)
    PASSED -> NoFeaturesTester
Counter_2
    SCOPE = Global
    START = 0
    DOMAIN = counter
    CNT_ATTR = _count
    -> Tester_4
Tester_4
    TEST_MODE = Automatic
    TEST_DESCRIPTION = ""
    BOOL_OP = OR
    TEST_CLAUSE = TEST @Value(_count) < $(MAXFEATURES)
    PASSED -> NoFeaturesTester

Bookmark: Error Handling - No Features
Note: Tests whether there is data / output from the database
NoFeaturesTester
    INPUT -> TestFilter_2
    NOINPUT -> Tester_5
Tester_5
    TEST_MODE = Automatic
    TEST_DESCRIPTION = ""
    BOOL_OP = OR
    TEST_CLAUSE = TEST $(REQUEST) = GetFeature
    PASSED -> AttributeCreator_2
Note: If no features are returned from / the database, create an error message / which will be written out to outText file
AttributeCreator_2
    ATTR_LIST = text_line_data,<error>Extent or XML filter too restrictive. No data returned from the database.</error>
    -> text_line (writer TEXTLINE_2)
TestFilter_2
    TEST_LIST = BOOL_OP,OR,COMPOSITE_TEST,<Unused>,TEST_CLAUSE,"TEST namedplace_type ATTRIBUTE_IS_MISSING """"",CadastralParcel,BOOL_OP,OR,COMPOSITE_TEST,<Unused>,TEST_CLAUSE,"TEST areavalue ATTRIBUTE_IS_MISSING """"",NamedPlace
    DEFAULT_VALUE = <UNFILTERED>
    NamedPlace -> NamedPlace (writer INSPIRE_1)
    CadastralParcel -> CadastralParcel (writer INSPIRE_1)

Bookmark: INSPIRE GML Writer
Note: Writes out CadastralParcel features / to the outGML file
CadastralParcel (writer INSPIRE_1)
    attributes: gml_parent_id xml_buffer, gml_metaDataProperty{} xml_xml, gml_metaDataProperty{}.about xml_buffer, gml_metaDataProperty{}.nilReason xml_buffer, gml_metaDataProperty{}.gml_remoteSchema xml_buffer, gml_metaDataProperty{}.xlink_href xml_buffer, gml_description xml_buffer, gml_description.nilReason xml_buffer, gml_description.gml_remoteSchema xml_buffer, gml_description.xlink_href xml_buffer, gml_descriptionReference.owns xml_boolean, gml_descriptionReference.nilReason xml_buffer, gml_descriptionReference.gml_remoteSchema xml_buffer, gml_descriptionReference.xlink_href xml_buffer, gml_identifier xml_buffer, gml_identifier.codeSpace xml_buffer, gml_name{} xml_buffer, gml_name{}.codeSpace xml_buffer, gml_boundedBy xml_geometry, gml_location xml_geometry, gml_priorityLocation xml_geometry, areaValue xml_real64, areaValue.nilReason xml_buffer, areaValue.uom xml_buffer, areaValue.xsi_nil xml_boolean, beginLifespanVersion xml_datetime, beginLifespanVersion.nilReason xml_buffer, beginLifespanVersion.xsi_nil xml_boolean, endLifespanVersion xml_datetime, endLifespanVersion.nilReason xml_buffer,
      endLifespanVersion.xsi_nil xml_boolean, geometry xml_geometry, inspireId.Identifier.localId xml_buffer, inspireId.Identifier.namespace xml_buffer, inspireId.Identifier.versionId xml_buffer, inspireId.Identifier.versionId.nilReason xml_buffer, inspireId.Identifier.versionId.xsi_nil xml_boolean, label xml_buffer, nationalCadastralReference xml_buffer, referencePoint xml_geometry, validFrom xml_datetime, validFrom.nilReason xml_buffer, validFrom.xsi_nil xml_boolean, validTo xml_datetime, validTo.nilReason xml_buffer, validTo.xsi_nil xml_boolean, basicPropertyUnit{}.owns xml_boolean, basicPropertyUnit{}.nilReason xml_buffer, basicPropertyUnit{}.gml_remoteSchema xml_buffer, basicPropertyUnit{}.xlink_href xml_buffer, basicPropertyUnit{}.xsi_nil xml_boolean, administrativeUnit.owns xml_boolean, administrativeUnit.nilReason xml_buffer, administrativeUnit.gml_remoteSchema xml_buffer, administrativeUnit.xlink_href xml_buffer, administrativeUnit.xsi_nil xml_boolean, zoning.owns xml_boolean, zoning.nilReason xml_buffer, zoning.gml_remoteSchema xml_buffer, zoning.xlink_href xml_buffer,
      zoning.xsi_nil xml_boolean
Note: Writes out NamedPlace features / to the outGML file
NamedPlace (writer INSPIRE_1)
    attributes: gml_parent_id xml_buffer, gml_metaDataProperty{} xml_xml, gml_metaDataProperty{}.about xml_buffer, gml_metaDataProperty{}.nilReason xml_buffer, gml_metaDataProperty{}.gml_remoteSchema xml_buffer, gml_metaDataProperty{}.xlink_href xml_buffer, gml_description xml_buffer, gml_description.nilReason xml_buffer, gml_description.gml_remoteSchema xml_buffer, gml_description.xlink_href xml_buffer, gml_descriptionReference.owns xml_boolean, gml_descriptionReference.nilReason xml_buffer, gml_descriptionReference.gml_remoteSchema xml_buffer, gml_descriptionReference.xlink_href xml_buffer, gml_identifier xml_buffer, gml_identifier.codeSpace xml_buffer, gml_name{} xml_buffer, gml_name{}.codeSpace xml_buffer, gml_boundedBy xml_geometry, gml_location xml_geometry, gml_priorityLocation xml_geometry, beginLifespanVersion xml_datetime, beginLifespanVersion.nilReason xml_buffer, beginLifespanVersion.xsi_nil xml_boolean, endLifespanVersion xml_datetime, endLifespanVersion.nilReason xml_buffer, endLifespanVersion.xsi_nil xml_boolean, geometry xml_geometry, inspireId.Identifier.localId xml_buffer, inspireId.Identifier.namespace xml_buffer,
      inspireId.Identifier.versionId xml_buffer, inspireId.Identifier.versionId.nilReason xml_buffer, inspireId.Identifier.versionId.xsi_nil xml_boolean, leastDetailedViewingResolution.nilReason xml_buffer, leastDetailedViewingResolution.owns xml_boolean, leastDetailedViewingResolution.xsi_nil xml_boolean, leastDetailedViewingResolution.MD_Resolution.equivalentScale.nilReason xml_buffer, leastDetailedViewingResolution.MD_Resolution.equivalentScale.uuidref xml_buffer, leastDetailedViewingResolution.MD_Resolution.equivalentScale.xlink_href xml_buffer, leastDetailedViewingResolution.MD_Resolution.equivalentScale.MD_RepresentativeFraction.id xml_buffer, leastDetailedViewingResolution.MD_Resolution.equivalentScale.MD_RepresentativeFraction.uuid xml_buffer, leastDetailedViewingResolution.MD_Resolution.equivalentScale.MD_RepresentativeFraction.denominator.gco_nilReason xml_buffer, leastDetailedViewingResolution.MD_Resolution.equivalentScale.MD_RepresentativeFraction.denominator.Integer xml_int64, leastDetailedViewingResolution.MD_Resolution.distance.gco_nilReason xml_buffer, leastDetailedViewingResolution.MD_Resolution.distance.Distance xml_real64, leastDetailedViewingResolution.MD_Resolution.distance.Distance.uom xml_buffer, localType{}.gco_nilReason xml_buffer, localType{}.uuidref xml_buffer, localType{}.xlink_href xml_buffer, localType{}.xsi_nil xml_boolean, localType{}.LocalisedCharacterString xml_buffer, localType{}.LocalisedCharacterString.id xml_buffer, localType{}.LocalisedCharacterString.locale xml_buffer, mostDetailedViewingResolution.nilReason xml_buffer, mostDetailedViewingResolution.owns xml_boolean, mostDetailedViewingResolution.xsi_nil xml_boolean, mostDetailedViewingResolution.MD_Resolution.equivalentScale.nilReason xml_buffer, mostDetailedViewingResolution.MD_Resolution.equivalentScale.uuidref xml_buffer, mostDetailedViewingResolution.MD_Resolution.equivalentScale.xlink_href xml_buffer, mostDetailedViewingResolution.MD_Resolution.equivalentScale.MD_RepresentativeFraction.id xml_buffer,
      mostDetailedViewingResolution.MD_Resolution.equivalentScale.MD_RepresentativeFraction.uuid xml_buffer, mostDetailedViewingResolution.MD_Resolution.equivalentScale.MD_RepresentativeFraction.denominator.gco_nilReason xml_buffer, mostDetailedViewingResolution.MD_Resolution.equivalentScale.MD_RepresentativeFraction.denominator.Integer xml_int64, mostDetailedViewingResolution.MD_Resolution.distance.gco_nilReason xml_buffer, mostDetailedViewingResolution.MD_Resolution.distance.Distance xml_real64, mostDetailedViewingResolution.MD_Resolution.distance.Distance.uom xml_buffer, name{}.GeographicalName.language xml_buffer, name{}.GeographicalName.language.nilReason xml_buffer, name{}.GeographicalName.language.xsi_nil xml_boolean, name{}.GeographicalName.nativeness xml_buffer, name{}.GeographicalName.nativeness.nilReason xml_buffer, name{}.GeographicalName.nativeness.codeSpace xml_buffer, name{}.GeographicalName.nativeness.xsi_nil xml_boolean, name{}.GeographicalName.nameStatus xml_buffer, name{}.GeographicalName.nameStatus.nilReason xml_buffer, name{}.GeographicalName.nameStatus.codeSpace xml_buffer, name{}.GeographicalName.nameStatus.xsi_nil xml_boolean, name{}.GeographicalName.sourceOfName xml_buffer, name{}.GeographicalName.sourceOfName.nilReason xml_buffer, name{}.GeographicalName.sourceOfName.xsi_nil xml_boolean, name{}.GeographicalName.pronunciation.nilReason xml_buffer, name{}.GeographicalName.pronunciation.xsi_nil xml_boolean, name{}.GeographicalName.pronunciation.PronunciationOfName.pronunciationSoundLink xml_buffer, name{}.GeographicalName.pronunciation.PronunciationOfName.pronunciationSoundLink.nilReason xml_buffer, name{}.GeographicalName.pronunciation.PronunciationOfName.pronunciationSoundLink.xsi_nil xml_boolean, name{}.GeographicalName.pronunciation.PronunciationOfName.pronunciationIPA xml_buffer, name{}.GeographicalName.pronunciation.PronunciationOfName.pronunciationIPA.nilReason xml_buffer, name{}.GeographicalName.pronunciation.PronunciationOfName.pronunciationIPA.xsi_nil xml_boolean, name{}.GeographicalName.spelling{}.SpellingOfName.text xml_buffer, name{}.GeographicalName.spelling{}.SpellingOfName.script xml_buffer,
      name{}.GeographicalName.spelling{}.SpellingOfName.script.nilReason xml_buffer, name{}.GeographicalName.spelling{}.SpellingOfName.script.xsi_nil xml_boolean, name{}.GeographicalName.spelling{}.SpellingOfName.transliterationScheme xml_buffer, name{}.GeographicalName.spelling{}.SpellingOfName.transliterationScheme.nilReason xml_buffer, name{}.GeographicalName.spelling{}.SpellingOfName.transliterationScheme.xsi_nil xml_boolean, name{}.GeographicalName.grammaticalGender xml_buffer, name{}.GeographicalName.grammaticalGender.nilReason xml_buffer, name{}.GeographicalName.grammaticalGender.codeSpace xml_buffer, name{}.GeographicalName.grammaticalGender.xsi_nil xml_boolean, name{}.GeographicalName.grammaticalNumber xml_buffer, name{}.GeographicalName.grammaticalNumber.nilReason xml_buffer, name{}.GeographicalName.grammaticalNumber.codeSpace xml_buffer, name{}.GeographicalName.grammaticalNumber.xsi_nil xml_boolean, relatedSpatialObject{}.nilReason xml_buffer, relatedSpatialObject{}.xsi_nil xml_boolean, relatedSpatialObject{}.Identifier.localId xml_buffer, relatedSpatialObject{}.Identifier.namespace xml_buffer, relatedSpatialObject{}.Identifier.versionId xml_buffer, relatedSpatialObject{}.Identifier.versionId.nilReason xml_buffer, relatedSpatialObject{}.Identifier.versionId.xsi_nil xml_boolean, type{} xml_buffer, type{}.nilReason xml_buffer, type{}.codeSpace xml_buffer, type{}.xsi_nil xml_boolean

FME custom transformer NamedPlace
NamedPlace GetFeature request handling

Parameters:
- bboxWest =   # Bounding box - minimum X coordinate
- bboxSouth =   # Bounding box - minimum Y coordinate
- bboxEast =   # Bounding box - maximum X coordinate
- bboxNorth =   # Bounding box - maximum Y coordinate
- BBOX =   # Bounding box
- _FILTER = @Value(_Filter)   # Filter
- POSTbody = text_line_data   # " " "" POSTbody

Note: Geographical Names feature extraction, filtering and geometry/attribute transformation to INSPIRE schema
GetFeaturePOST (input)
    -> XMLFlattener_2
GetFeatureGET (input)
    -> Tester
OUTPUT (output)

Bookmark: POST: GetFeature
XMLFlattener_2
    ATTRIBUTE_XML = $(POSTbody)
    XML_SOURCE_TYPE = Attribute with XML document
    EMBEDDED_EXPRESSIONS = Filter
    FLATTEN_OPTIONS = <structure separator="." map-empty-elements="yes" matched-prefix="attributes" matched-attributes="yes" cardinality="+{?}" structure-prefix="" child-position-attribute="" except-expression="" ui-mode="basic" matched-ancestor-attributes=""/>
    -> AttributeExposer_2
AttributeExposer_2
    ATTR_LIST = PropertyIsEqualTo.Function.Literal,"",PropertyIsEqualTo.Function.ValueReference,"",PropertyIsEqualTo.Function.name,"",PropertyIsEqualTo.PropertyName,"",PropertyIsEqualTo.PropertyLiteral,"","",""
    -> Tester_5
Tester_5
    TEST_MODE = Automatic
    TEST_DESCRIPTION = ""
    BOOL_OP = OR
    TEST_CLAUSE = TEST @Value(PropertyIsEqualTo.PropertyName) = ""
    PASSED -> AttributeCopier_3
    FAILED -> Tester_4
AttributeCopier_3
    ATTR_LIST = PropertyIsEqualTo.PropertyName,PropertyIsEqualTo.Function.ValueReference,PropertyIsEqualTo.Literal,PropertyIsEqualTo.Function.Literal
    -> Tester_4
Note: POST BBOX / Extents query NOT handled / since FME WFS client does not support it
Tester_4
    TEST_MODE = Automatic
    TEST_DESCRIPTION = ""
    BOOL_OP = AND
    TEST_CLAUSE:
      TEST @Value(PropertyIsEqualTo.PropertyName) != ""
      TEST @Value(PropertyIsEqualTo.Literal) != ""
    FAILED -> GetBBOX
    PASSED -> StringConcatenator
    FAILED -> Tester_4_Failed
Tester_4_Failed: Logger
    MESSAGE = Feature is:
    MAXFEATS = 20
    MAXCOORDS = 20

Bookmark: Parse GetFeature
Tester
    TEST_MODE = Automatic
    TEST_DESCRIPTION = ""
    BOOL_OP = OR
    TEST_CLAUSE = TEST @Value(_Filter) != ""
    PASSED -> GetFilterProcessor
    FAILED -> GetBBOX
GetFilterProcessor
    _FILTER = @Value(_Filter)
    FAILED -> GetBBOX
    -> GetBBOX_2

Bookmark: Query Database
GetBBOX_2
    bboxWest = $(bboxWest)
    BBOX = $(BBOX)
    bboxEast = $(bboxEast)
    bboxNorth = $(bboxNorth)
    bboxSouth = $(bboxSouth)
    BBox -> StringConcatenator
    <UNFILTERED> -> StringConcatenator
StringConcatenator
    PARM_LINE = @Value(PropertyIsEqualTo.PropertyName)='@Value(PropertyIsEqualTo.Literal)'
    VAL_ATTR = _whereQuery
    -> FeatureReader_2
Note: With Where and extents
FeatureReader_2
    WHERE = @Value(_whereQuery)
    INTERACT = ENVELOPE_INTERSECT
    ATTRIBUTES = NamedPlace,"beginlifespanversion,geographicalname_language,geographicalname_namestatus,geographicalname_nativeness,geographicalname_pronounciation,geographicalname_script,geographicalname_source_nilreason,geographicalname_spellingofname_text,gml_id,inspireid_identifier_localid,inspireid_identifier_namespace,localtype_localisedcharacterstring,localtype_localisedcharacterstring_locale,name_geographicalname_language,name_geographicalname_namestatus,name_geographicalname_nativeness,name_geographicalname_pronunciation_pronunciationofname_pron,name_geographicalname_sourceofname,name_geographicalname_sourceofname_nilreason,name_geographicalname_spelling_spellingofname_script,name_geographicalname_spelling_spellingofname_text,namedplace_beginlifespanversion,namedplace_featureid,namedplace_localid,namedplace_localtype,namedplace_localtype_locale,namedplace_namespace,namedplace_pointid,namedplace_type,type,PRIMARYINDEX"
    FEATURETYPES = NamedPlace
    SUPPORTED_SPATIAL_INTERACTIONS = ENVELOPE_INTERSECT%ENVELOPE_INTERSECT%INTERSECTS%CONTAINS%CROSSES%DISJOINT%EQUALS%OVERLAPS%TOUCHES%WITHIN
    DATASET = .\INSPIREdb.sdf
    SDF3_REMOVE_SCHEMA_QUALIFIER = YES
    SDF3_TABLELIST = NamedPlace
    COMBINE_GEOM = Keep result geometry only
    COMBINE_ATTRS = Keep result attributes only
    FORMAT = SDF3
    SDF3_DUMMY = YES
    NamedPlace -> GeometryPropertySetter_2
GetBBOX
    bboxWest = $(bboxWest)
    BBOX = $(BBOX)
    bboxEast = $(bboxEast)
    bboxNorth = $(bboxNorth)
    bboxSouth = $(bboxSouth)
    <UNFILTERED> -> FeatureReader_4
    BBox -> FeatureReader_4
Note: With extents
FeatureReader_4
    INTERACT = ENVELOPE_INTERSECT
    ATTRIBUTES = NamedPlace,"beginlifespanversion,geographicalname_language,geographicalname_namestatus,geographicalname_nativeness,geographicalname_pronounciation,geographicalname_script,geographicalname_source_nilreason,geographicalname_spellingofname_text,gml_id,inspireid_identifier_localid,inspireid_identifier_namespace,localtype_localisedcharacterstring,localtype_localisedcharacterstring_locale,name_geographicalname_language,name_geographicalname_namestatus,name_geographicalname_nativeness,name_geographicalname_pronunciation_pronunciationofname_pron,name_geographicalname_sourceofname,name_geographicalname_sourceofname_nilreason,name_geographicalname_spelling_spellingofname_script,name_geographicalname_spelling_spellingofname_text,namedplace_beginlifespanversion,namedplace_featureid,namedplace_localid,namedplace_localtype,namedplace_localtype_locale,namedplace_namespace,namedplace_pointid,namedplace_type,type,PRIMARYINDEX"
    FEATURETYPES = NamedPlace
    SUPPORTED_SPATIAL_INTERACTIONS = ENVELOPE_INTERSECT%ENVELOPE_INTERSECT%INTERSECTS%CONTAINS%CROSSES%DISJOINT%EQUALS%OVERLAPS%TOUCHES%WITHIN
    DATASET = .\INSPIREdb.sdf
    SDF3_REMOVE_SCHEMA_QUALIFIER = YES
    SDF3_TABLELIST = NamedPlace
    COMBINE_GEOM = Keep result geometry only
    COMBINE_ATTRS = Keep result attributes only
    FORMAT = SDF3
    SDF3_DUMMY = YES
    NamedPlace -> GeometryPropertySetter_2

Bookmark: Schema Transformation
GeometryPropertySetter_2
    OVERWRITE_CHOICE = No
    SETTYPE_PARAM = Geometry Name
    GEOM_NAME_FIELD = geometry
    SET -> GeometryPropertySetter_3
GeometryPropertySetter_3
    OVERWRITE_CHOICE = Yes
    SRC_ATTRS = gml_id
    SETTYPE_PARAM = Traits From Attributes
    SET -> UUIDGenerator
UUIDGenerator
    UUID_ATTR = _uuid
    -> AttributeCreator
AttributeCreator
    ATTR_LIST = namedplace_featureid,@Value(gml_id).@Value(_uuid)
    -> AttributeCopier_2
AttributeCopier_2
    ATTR_LIST = beginlifespanversion,beginLifespanVersion,"",inspireid_identifier_localid,inspireId.Identifier.localId,"",namedplace_namespace,inspireId.Identifier.namespace,"",localtype_localisedcharacterstring_locale,localType{0}.LocalisedCharacterString.locale,"",localtype_localisedcharacterstring,localType{0}.LocalisedCharacterString,"",type,type{0},"",name_geographicalname_language,name{0}.GeographicalName.language,"",name_geographicalname_namestatus,name{0}.GeographicalName.nativeness,"",name_geographicalname_namestatus,name{0}.GeographicalName.nameStatus,"",name_geographicalname_sourceofname,name{0}.GeographicalName.sourceOfName,"",name_geographicalname_spelling_spellingofname_text,name{0}.GeographicalName.spelling{0}.SpellingOfName.text,"",name_geographicalname_spelling_spellingofname_script,name{0}.GeographicalName.spelling{0}.SpellingOfName.script,"",namedplace_featureid,gml_id,""
    -> OUTPUT (output)

FME custom transformer CadastralParcel
Cadastral Parcel GET request handling

Parameters:
- bboxWest =   # Bounding box - minimum X coordinate
- bboxSouth =   # Bounding box - minimum Y coordinate
- bboxEast =   # Bounding box - maximum X coordinate
- bboxNorth =   # Bounding box - maximum Y coordinate
- BBOX =   # Bounding box
- _FILTER = @Value(_Filter)   # Filter

Note: Cadastral parcels feature extraction, filtering and geometry transformation to INSPIRE schema
GetFeature_GET (input)
    -> Tester_4

Bookmark: Parse GetFeature
Note: Determine whether there is a value in the filter parameter / If there is -> Passed
Tester_4
    TEST_MODE = Automatic
    TEST_DESCRIPTION = ""
    BOOL_OP = OR
    TEST_CLAUSE = TEST @Value(_Filter) != ""
    PASSED -> GetFilterProcessor
    FAILED -> GetBBOX
Note: Convert XML Filter to where fields
GetFilterProcessor
    _FILTER = @Value(_Filter)
    FAILED -> GetBBOX
    -> GetBBOX_2

Bookmark: Query Database and Apply Filters
GetBBOX_2
    bboxWest = $(bboxWest)
    BBOX = $(BBOX)
    bboxEast = $(bboxEast)
    bboxNorth = $(bboxNorth)
    bboxSouth = $(bboxSouth)
    BBox -> StringConcatenator
    <UNFILTERED> -> StringConcatenator
Note: WHERE is the XML filter expression??
StringConcatenator
    PARM_LINE = "@Value(PropertyIsEqualTo.PropertyName)"='@Value(PropertyIsEqualTo.Literal)'
    VAL_ATTR = _whereQuery
    -> FeatureReader_2
Note: With Where and extents
FeatureReader_2
    WHERE = @Value(_whereQuery)
    INTERACT = ENVELOPE_INTERSECT
    ATTRIBUTES = CadastralParcel,"gml_parent_id,gml_id,areavalue,areavalue_nilreason,areavalue_uom,areavalue_xsi_nil,beginlifespanversion,beginlifespanversion_nilreason,beginlifespanversion_xsi_nil,endlifespanversion,endlifespanversion_nilreason,endlifespanversion_xsi_nil,geometry,inspireid_identifier_localid,inspireid_identifier_namespace,inspireid_identifier_versionid,inspireid_identifier_versionid_nilreason,inspireid_identifier_versionid_xsi_nil,label,nationalcadastralreference,referencepoint,validfrom,validfrom_nilreason,validfrom_xsi_nil,validto,validto_nilreason,validto_xsi_nil,basicpropertyunit{}_owns,basicpropertyunit{}_nilreason,basicpropertyunit{}_gml_remoteschema,basicpropertyunit{}_xlink_href,basicpropertyunit{}_xsi_nil,administrativeunit_owns,administrativeunit_nilreason,administrativeunit_gml_remoteschema,administrativeunit_xlink_href,administrativeunit_xsi_nil,zoning_owns,zoning_nilreason,zoning_gml_remoteschema,zoning_xlink_href,zoning_xsi_nil,PRIMARYINDEX"
    FEATURETYPES = CadastralParcel
    SUPPORTED_SPATIAL_INTERACTIONS = ENVELOPE_INTERSECT%ENVELOPE_INTERSECT%INTERSECTS%CONTAINS%CROSSES%DISJOINT%EQUALS%OVERLAPS%TOUCHES%WITHIN
    DATASET = .\INSPIREdb.sdf
    SDF3_REMOVE_SCHEMA_QUALIFIER = YES
    SDF3_TABLELIST = CadastralParcel
    COMBINE_GEOM = Keep result geometry only
    COMBINE_ATTRS = Keep result attributes only
    FORMAT = SDF3
    SDF3_DUMMY = YES
    CadastralParcel -> GeometryPropertySetter
GetBBOX
    bboxWest = $(bboxWest)
    BBOX = $(BBOX)
    bboxEast = $(bboxEast)
    bboxNorth = $(bboxNorth)
    bboxSouth = $(bboxSouth)
    <UNFILTERED> -> FeatureReader_4
    BBox -> FeatureReader_4
Note: With extents
FeatureReader_4
    INTERACT = ENVELOPE_INTERSECT
    ATTRIBUTES = CadastralParcel,"gml_parent_id,gml_id,areavalue,areavalue_nilreason,areavalue_uom,areavalue_xsi_nil,beginlifespanversion,beginlifespanversion_nilreason,beginlifespanversion_xsi_nil,endlifespanversion,endlifespanversion_nilreason,endlifespanversion_xsi_nil,geometry,inspireid_identifier_localid,inspireid_identifier_namespace,inspireid_identifier_versionid,inspireid_identifier_versionid_nilreason,inspireid_identifier_versionid_xsi_nil,label,nationalcadastralreference,referencepoint,validfrom,validfrom_nilreason,validfrom_xsi_nil,validto,validto_nilreason,validto_xsi_nil,basicpropertyunit{}_owns,basicpropertyunit{}_nilreason,basicpropertyunit{}_gml_remoteschema,basicpropertyunit{}_xlink_href,basicpropertyunit{}_xsi_nil,administrativeunit_owns,administrativeunit_nilreason,administrativeunit_gml_remoteschema,administrativeunit_xlink_href,administrativeunit_xsi_nil,zoning_owns,zoning_nilreason,zoning_gml_remoteschema,zoning_xlink_href,zoning_xsi_nil,PRIMARYINDEX"
    FEATURETYPES = CadastralParcel
    SUPPORTED_SPATIAL_INTERACTIONS = ENVELOPE_INTERSECT%ENVELOPE_INTERSECT%INTERSECTS%CONTAINS%CROSSES%DISJOINT%EQUALS%OVERLAPS%TOUCHES%WITHIN
    DATASET = .\INSPIREdb.sdf
    SDF3_REMOVE_SCHEMA_QUALIFIER = YES
    SDF3_TABLELIST = CadastralParcel
    COMBINE_GEOM = Keep result geometry only
    COMBINE_ATTRS = Keep result attributes only
    FORMAT = SDF3
    SDF3_DUMMY = YES
    CadastralParcel -> GeometryPropertySetter

Bookmark: Build and Format INSPIRE Geometries
GeometryPropertySetter
    OVERWRITE_CHOICE = Yes
    SETTYPE_PARAM = Geometry Name
    GEOM_NAME_FIELD = geometry
    SET -> Aggregator_2
    SET -> InsidePointReplacer
InsidePointReplacer
    INSIDEPOINT -> GeometryPropertySetter_5
GeometryPropertySetter_5
    OVERWRITE_CHOICE = Yes
    SETTYPE_PARAM = Geometry Name
    GEOM_NAME_FIELD = referencePoint
    SET -> Aggregator_2
Aggregator_2
    GROUP_BY = gml_id
    MODE = Geometry - Assemble One Level
    ACCUM_ATTRS_NAME = Yes
    SEP = ,
    AGGREGATE_TYPE = Multiple Geometry
    ORDERED = No
    AGGREGATE -> AttributeCopier
AttributeCopier
    ATTR_LIST = nationalcadastralreference,nationalCadastralReference,"",beginlifespanversion,beginLifespanVersion,"",beginlifespanversion_xsi_nil,beginLifespanVersion.xsi_nil,"",inspireid_identifier_localid,inspireId.Identifier.localId,"",inspireid_identifier_namespace,inspireId.Identifier.namespace,""
    -> AttributeCopier_2_Output
AttributeCopier_2_Output: Logger
    MESSAGE = GetFeature OUTPUT:
    MAXFEATS = 3
    MAXCOORDS = 20
    LOGGED -> OUTPUT (output)
OUTPUT (output)

FME custom transformer GetBBOX
Generate bounding box depending on values of bbox parameters

Parameters:
- bboxWest =   # Bounding box - minimum X coordinate
- bboxSouth =   # Bounding box - minimum Y coordinate
- bboxEast =   # Bounding box - maximum X coordinate
- bboxNorth =   # Bounding box - maximum Y coordinate
- BBOX =

Note: Use bbox parameters to build geometry for use in spatial query
INPUT (input)
    -> ParameterFetcher
Note: Output all attributes
<UNFILTERED> (output)

Bookmark: Determine BBox Type
Note: Fetches bbox values, both BBOX and / the individual bboxDirection values
ParameterFetcher
    ATTR_LIST = _BBOX {$(BBOX)} _bboxWest {$(bboxWest)} _bboxSouth {$(bboxSouth)} _bboxEast {$(bboxEast)} _bboxNorth {$(bboxNorth)}
    -> AttributeExposer
Note: Exposes attributes so that they / can be used by other transformers
AttributeExposer
    ATTR_LIST = _bbox.coord{0},_bbox.coord{1},_bbox.coord{2},_bbox.coord{3},_bbox.coord{4}
    -> TestFilter_2
Note: Directs the flow of data depending on whether BBOX or / bboxCoords contain values, or if neither contain values -> Unfiltered
Note: Create BBox geometry from the bboxCoords
TestFilter_2
    TEST_LIST = BOOL_OP,OR,COMPOSITE_TEST,<Unused>,TEST_CLAUSE,"TEST @Value(_BBOX) != """"",BBOX,BOOL_OP,OR,COMPOSITE_TEST,<Unused>,TEST_CLAUSE,"TEST @Value(_bboxWest) != """"",bboxCoords
    DEFAULT_VALUE = <UNFILTERED>
    bboxCoords -> 2DBoxReplacer_coords
    BBOX -> Tester_7
    <UNFILTERED> -> <UNFILTERED> (output)

Bookmark: Generate BBox Polygon from Parameters
Note: Tests whether BBOX contain % / If it does contain % -> Failed
Tester_7
    TEST_MODE = Automatic
    TEST_DESCRIPTION = ""
    BOOL_OP = OR
    TEST_CLAUSE = TEST @Value(_BBOX) NOT_CONTAINS %
    PASSED -> AttributeSplitter_2
    FAILED -> TextDecoder
Note: URL (Percent Encoding) / This encoding is used to ensure that a string is valid for inclusion in a URL. / All characters that are not a letter, digit, dash, period, underscore or tilde will be encoded.
TextDecoder
    ENCODING_TYPE = URL (Percent Encoding)
    DEST_ATTR = _BBOX
    STRING_TO_DECODE = @Value(_BBOX)
    -> AttributeSplitter_2
Note: Splits value in BBOX based on , (commas)
AttributeSplitter_2
    LIST_NAME = _bbox.coord
    ATTR_NAME = _BBOX
    DELIMITER = ,
    TRIM_OPTION = Both
    DROP_EMPTY_PARTS = No
    -> AttributeCopier
Note: Copies BBOX attributes / to target attributes
AttributeCopier
    ATTR_LIST = Xmin,_bbox.coord{0},Ymin,_bbox.coord{1},Xmax,_bbox.coord{2},Ymax,_bbox.coord{3},epsg,_bbox.coord{4}
    -> 2DBoxReplacer_bbox
Note: Create BBox geometry from BBOX attributes
2DBoxReplacer_bbox
    MAXXVALATTR = @Value(Xmax)
    MINYVALATTR = @Value(Ymin)
    MAXYVALATTR = @Value(Ymax)
    MINXVALATTR = @Value(Xmin)
    BOX -> Tester
Note: If EPSG is >= 4000 or < 5000 direct / output to Coordinate Swapper
Tester
    TEST_MODE = Automatic
    TEST_DESCRIPTION = ""
    BOOL_OP = OR
    TEST_CLAUSE:
      TEST @Value(epsg) >= 4000
      TEST @Value(epsg) < 5000
    FAILED -> BBox (output)
    PASSED -> CoordinateSwapper
Note: Swap X for Y
CoordinateSwapper
    SWAP_TYPE = X <-> Y
    -> BBox (output)
2DBoxReplacer_coords
    MAXXVALATTR = $(bboxEast)
    MINYVALATTR = $(bboxSouth)
    MAXYVALATTR = $(bboxNorth)
    MINXVALATTR = $(bboxWest)
    BOX -> BBox (output)
Note: BBox
BBox (output)

FME custom transformer NoFeaturesTester
This transformer checks whether there are any input features. If not, then a single feature is ouput via the NOINPUT port. If INPUT features exist, then they are output via the INPUT output port.
Other transformers often generate features that signify an error condition. This transformer can be used to check for those features and if those features exists, then a separate action can be triggered.
    Example
This may be useful to test if any data emerges from a reader, when the 'Ignore Failed Readers' advanced parameter is set to yes.
There are no special instructions for using this transformer.
Copyright (c) 2012 Safe Software Inc.
Permission is granted to anyone, free of charge, to use, modify and distribute the object code form of this template for any purpose, subject to the following restrictions:
1) The origin of this template and associated FME(R) software must not be misrepresented.
2) This template may only be used in conjunction with a validly licensed copy of FME software.
THIS SOFTWARE IS PROVIDED BY SAFE SOFTWARE INC. "AS IS" AND ANY EXPRESS OR IMPLIED WARRANTIES, INCLUDING, BUT NOT LIMITED TO, THE IMPLIED WARRANTIES OF MERCHANTABILITY, NONINFRINGEMENT AND FITNESS FOR A PARTICULAR PURPOSE ARE DISCLAIMED. IN NO EVENT SHALL SAFE SOFTWARE INC. BE LIABLE FOR ANY DIRECT, INDIRECT, INCIDENTAL, SPECIAL, EXEMPLARY, OR CONSEQUENTIAL DAMAGES (INCLUDING, BUT NOT LIMITED TO, PROCUREMENT OF SUBSTITUTE GOODS OR SERVICES; LOSS OF USE, DATA, OR PROFITS; OR BUSINESS INTERRUPTION) HOWEVER CAUSED AND ON ANY THEORY OF LIABILITY, WHETHER IN CONTRACT, STRICT LIABILITY, OR TORT (INCLUDING NEGLIGENCE OR OTHERWISE) ARISING IN ANY WAY OUT OF THE USE OF THIS SOFTWARE, EVEN IF ADVISED OF THE POSSIBILITY OF SUCH DAMAGE.

INPUT (input)
    -> INPUT (output)
    -> Sampler
INPUT (output)

Bookmark: Obtain Features
Note: Takes the first input feature
Sampler
    RATE = 1
    SAMPLE_TYPE_LONG = First N Features
    SAMPLED -> StatisticsCalculator
Note: Creates 1 feature
Creator
    NUM = 1
    GEOMTYPE = Geometry Object
    CREATED -> StatisticsCalculator

Bookmark: Count Features
Note: Counts features received
StatisticsCalculator
    STATS_ATTR = no_features
    PASS_THROUGH = No
    COUNT_ATTR = NFT_count
    STATISTICS -> Tester_2

Bookmark: Handling if No Features Received
Note: If the number of features is equal to 1, / no feature came through the INPUT port
Tester_2
    TEST_MODE = Automatic
    TEST_DESCRIPTION = ""
    BOOL_OP = OR
    TEST_CLAUSE = TEST "@Value(NFT_count)" = "1"
    PASSED -> AttributeCreator
Note: Provides an attribute for filtering
AttributeCreator
    ATTR_LIST = no_features,true
    -> NOINPUT (output)
NOINPUT (output)

FME custom transformer Docs

Bookmark: Documentation
Note: BACKGROUND / This is a WFS 'service broker' workspace. This just needs to be published to the data streaming service and will accept WFS GET or POST requests (GetCapabilities, DescribeFeatureType, and GetFeature) and generate the appropriate responses as XML or GML data streams (GetCapabilities and DescribeFeatureType XML docs, or GetFeature GML docs). The workspace supports XML filters which replace the old WFS service approach. Also, the workspace is configured to support FME Data Inspector as a WFS client. Note that this demo requires FME Desktop and Server 2014 or later to function, which is required to support the new INSPIRE GML Writer. / This demo is a fairly basic example as it only supports 2 feature types and one XML filter operation, though these can be extended fairly easily by following the example/approach laid out in the workspace. / Any WxS such as WFS-T, WCS, WPS, etc. could be supported by a similar workspace. All that is required is to understand the web service protocol client/server requirements and configure accordingly. It also could be used to support SOS O&M (observation and measurements). Additionally, any complex XML/GML that needs to be transmitted via WFS can be supported by this, whether INSPIRE, AIXM, metadata/CSW, etc. Of course, this still entails a lot of setup work depending on the service. But essentially this approach gives the user control to configure their web services how they want - basically a custom web service. / INSPIRE_WFS.fmw Version 2.0 / OVERVIEW / This workspace comprises an INSPIRE WFS when published to the FME Server data streaming service. / The local server URL is: / http://localhost/fmedatastreaming/INSPIRE/INSPIRE_WFS.fmw / Safe Software's WFS demo server URL is: / http://inspire-safe-software.fmecloud.com/fmedatastreaming/INSPIRE/INSPIRE_WFS.fmw / The workspace supports writing INSPIRE GML using the XSD enabled INSPIRE GML Writer available as of FME 2014. It accepts GetCapabilities, DescribeFeatureType and GetFeature requests, either as a GET URL or POST XML. Also, it supports Filter expressions. / When you send an HTTP POST to FME Server, it automatically overrides the input of this workspace with the POST body. Note this means you need to have only one input and you assume that it is HTTP POST WFS XML. If there is a POST method, then the POST body is the WFS request, such as the WFS GetFeature XML with the embedded XML filter query. / The workspace supports FME Viewer and FME Data Inspector as WFS clients. It should support third party WFS clients as well. / Setup: / 1. Modify workspace paths to make sure source database is accessible by FeatureReaders in the theme data extraction custom transformers (CadastralParcel and NamedPlace). / 2. Update workspace parameters as needed (default theme, max features etc.) / 3. Set GML writer default parameters such as axis order, SRS etc. / 4. Test run workspace locally using each of GetCapabilities, DescribeFeatureType and GetFeature request types to make sure correct output is generated. / 5. Prepare for publishing by changing request back to GetCapabilities and removing any filters before saving. The goal is to have user friendly default parameter values. / 6. Publish to FME Server Data Streaming service. Upload all supporting resources: source_get.txt etc. Make sure both Text File writer and GML writer are published outputs. Note XSDs no longer need to be uploaded as they are included with the INSPIRE Writer. If you wish to use a draft or newer schema than what is delivered with FME you will need to make sure these are uploaded. / USAGE NOTES: / Make sure you publish with a non-XML source so that by default the XML test will fail. / Also make sure parameter Filter = "" and Request = GetCapabilities by default. / GeoServer uses TypeNames and FME Viewer client uses TypeName. / Adding Another Feature Type Theme / 1. Under Private Parameters, add the theme to the Themes parameter / 2. In XMLTemplater, add a call to the theme in the ROOT template and add a sub template for the theme / 3. Add a new custom transformer and INSPIRE GML Writer for the theme / Error Handling - features from the database / 1. Input stream is tested to determine whether features are received from database / 2. If no features are received from the database, an error message is written to the outText file, which notifies the user that no data was obtained / Error Handling - WFS requests / If a request results in an error message, run the following WFS diagnostics: / 1. Make a simple request, such as making the only constraint max features, to determine whether the WFS is responding / 2. If the WFS is responding, examine the syntax of the desired request to check for errors / Data Inspector Troubleshooting / 1. Copy http request from Data Inspector Log to browser and test server response / 2. Download GML with browser to test if problem is with WFS client/server or GML reading / 3. Try removing all constraints except for max features / 4. Try specifying local schema file (.xsd) / Configuration alternative to extend the WFS template / Add error reporting (no results from WHERE, etc.) / Add new themes / Create wrapper schema file (.xsd) for multiple theme support / Configure responses to support WFS 2.0 Add new XML filter options (range queries, etc.)
Note: Modification History / By: Dean Hintz, Safe Software / Created: Feb 25, 2013 / Last modified March 27, 2014 / Current Version: 2.0 / March 27, 2014 / Modified by Natalie Wlock / Added in a Themes Private Parameter, which makes it easier to add themes / Updated Docs / March 14, 2014 / Modified by Natalie Wlock / Selected Pretty Print INSPIRE GML Writer parameter to account for the Pretty Print option in FME Desktop 2014 Service Pack 1 and later / Created error handling in case no data is received from the database. If no features are returned, an error message will be printed out to the outText file. / Jan 8, 2014 / Extensive modifications to support INSPIRE webinar: / Replaced GML writer with INSPIRE writer - xsds no longer need to be uploaded / Changed query database from SDF to PostGIS / Added CadastralParcels / Generalized theme handling to handle multiple themes. This required changes to GetCapabilities and DescribeFeatureType. Theme is now checked before providing response xsd. / Added MaxFeature parameter and handling / Created custom transformers for each INSPIRE theme to more clearly separate WFS message handling from GML data stream publication. / Updated Docs / Oct 10, 2013 / Updated to support FME 2014 (reimported destination feature type and made required schemaMappings in AttributeCopier) / Updated Docs / Set SRS to 4326 (LL84 axis 2,1) / Corrected DescribeFeature to DescribeFeatureType / Sept 6, 2013 / Disabled XML / Text File writer for GetFeature GML output and added new GML Writer instead. / New GML writer is based on GeographicalNames.xsd not XMLTemplater / templates. / Added the GML writer and then import the schema from GeographicalNames.xsd / OUTSTANDING / Currently only handles WFS 1.1 / GML 3.1.1. / Only handles queries to one theme at a time. / Need to add support for WFS 2.0. This should be straight forward - just need to update template headers and use GML 3.2.1 geometry extraction. Needs to handle POST extents query / Limited error handling in the workspace. Only able to output a specific error message if no data is received from the database. Bad feature requests may output unhelpful messages, just yields an XML error. This should be detected and return a valid GML or XML error feature. For example, if the XML filter has a syntax error, log may return an XML parser error, when it would be more descriptive to state that it does not have a not valid name. / Cannot currently make POST requests for CadastralParcels, can only make POST request for NamedPlace

Bookmark: Sample Requests and Filters
Note: Reading Safe's INSPIRE WFS / Jan 8, 2014 / Use this URL: / http://inspire-safe-software.fmecloud.com:80/fmedatastreaming/INSPIRE/INSPIRE_WFS.fmw / Backup / development Server: / http://inspire-safe-software.fmecloud.com:80/fmedatastreaming/INSPIRE/INSPIRE_WFSdev.fmw / *** Only query one theme at a time NamedPlace or CadastralParcels but not both at once*** / Sample GetFeature request: / http://inspire-safe-software.fmecloud.com:80/fmedatastreaming/INSPIRE/INSPIRE_WFSdev.fmw?SERVICE=WFS&VERSION=1.1.0&REQUEST=GetFeature&TYPENAME=CadastralParcel&MAXFEATURES=1111 / CADASTRAL PARCELS QUERIES: / Parcels XML FILTERS: / <Filter><PropertyIsEqualTo><PropertyName>inspireId.Identifier.localId</PropertyName><Literal>136000AZ0063</Literal></PropertyIsEqualTo></Filter> / (Generates: `_whereQuery' has value `inspireId.Identifier.localId='136000AZ0063'') / <Filter><PropertyIsEqualTo><PropertyName>gml_id</PropertyName><Literal>id-ff84b9a7-5e8e-458b-8488-fd5d01d9ea29</Literal></PropertyIsEqualTo></Filter> / <Filter><PropertyIsEqualTo><PropertyName>nationalCadastralReference</PropertyName><Literal>66136000AZ0492</Literal></PropertyIsEqualTo></Filter / Parcels SPATIAL QUERY: / 0 to 5, 40 to 50 (W France) / GEOGRAPHIC NAMES QUERIES: / NamedPlace XML FILTERS: / <Filter><PropertyIsEqualTo><PropertyName>GeographicalName_language</PropertyName><Literal>Italian</Literal></PropertyIsEqualTo></Filter> / <Filter><PropertyIsEqualTo><PropertyName>geographicalname_spellingofname_text</PropertyName><Literal>Roma</Literal></PropertyIsEqualTo></Filter> / NamedPlace Spatial query: / 0 to 5, 40 to 50 (W France) / 0 to 25, 42 to 48 (should cover both Italy and S France so results overlap with parcels) / Can also get schemas from: / http://inspire.ec.europa.eu/schemas/cp/3.0/CadastralParcels.xsd etc.

FME custom transformer Utilities

Parameters:
- SERVICE = WFS   # Service
- REQUEST = GetFeature   # Request
- VERSION = 1.1   # Version

Bookmark: Log
Creator
    NUM = 1
    GEOMTYPE = Geometry Object
    CREATED -> ParameterFetcher
ParameterFetcher
    ATTR_LIST = _VERSION {$(VERSION)} _REQUEST {$(REQUEST)} _SERVICE {$(SERVICE)}
    -> Logger_OUTPUT
Logger_OUTPUT
    MESSAGE = URL Parameters are:
    MAXFEATS = 20
    MAXCOORDS = 20

FME custom transformer GetFilterProcessor
Process XML Filter from GET GetFeature Request

Parameters:
- _FILTER = @Value(_Filter)   # _Filter

Note: Parse Filter XML to attribute name and value fields to support building WHERE clause
INPUT (input)
    -> XMLValidator_2
AttributeRemover
    REMOVE_ATTRS = _Filter,filterXML,fitlerXML,PropertyIsEqualTo.Function.Literal,PropertyIsEqualTo.Function.ValueReference,PropertyIsEqualTo.Function.name
    -> StringCaseChanger
StringCaseChanger
    ATTRCHOICE = Selected Attributes
    CHANGE_TYPE = lowercase
    ATTRLIST = PropertyIsEqualTo.PropertyName
    -> StringReplacer
StringReplacer
    SRC_ATTRS = PropertyIsEqualTo.PropertyName
    REGEXP = no
    CASE = no
    REPLACE_TEXT = _
    NO_MATCH = _FME_NO_OP_
    FIND_TEXT = .
    -> OUTPUT (output)
OUTPUT (output)
FAILED (output)

Bookmark: Validate Filter XML Expression
Note: Make sure Filter expression is valid
XMLValidator_2
    VAL_MODE_1 = Syntax Only
    XML_ATTR_TEXT = _Filter
    LIST_NAME = _xml_error
    XML_INPUT_TYPE = Attribute Specifying XML Text
    LIMIT_ERRORS = No
    FAILED -> TextDecoder
    PASSED -> AttributeCopier
AttributeCopier
    ATTR_LIST = filterXML,_Filter
    -> XMLFlattener
Note: If valid XML fails try to decode
TextDecoder
    ENCODING_TYPE = URL (Percent Encoding)
    DEST_ATTR = fitlerXML
    STRING_TO_DECODE = @Value(_Filter)
    -> XMLFormatter_2
Note: Required to pass validation after decoding
XMLFormatter_2
    REMOVE_EMPTY_ELEMENT = No
    XML_OUTPUT_ATTR = filterXML
    OUTPUT_ENCODING = utf-8
    XML_ATTR_TEXT = fitlerXML
    FORMATTING_CHOICE = Pretty-Print XML
    NAMESPACE_CLEANUP = No
    LIST_NAME = _xml_error
    COLLAPSE_EMPTY_ELEMENT = No
    SCHEMALOC_CLEANUP = No
    XML_INPUT_TYPE = Attribute Specifying XML Text
    XML_OUTPUT_TYPE = Attribute
    WHITESPACE_HANDLING = Preserve all whitespace
    REMOVE_ALL_COMMENT = No
    PASSED -> XMLValidator_3
    FAILED -> FAILED (output)
Note: If all filter validation fails simply / ignore filter and return all features
XMLValidator_3
    VAL_MODE_1 = Syntax Only
    XML_ATTR_TEXT = fitlerXML
    LIST_NAME = _xml_error
    XML_INPUT_TYPE = Attribute Specifying XML Text
    LIMIT_ERRORS = No
    PASSED -> XMLFlattener
    FAILED -> FAILED (output)

Bookmark: Convert Filter XML to Field and Value
Note: Generate fields from Filter XML
XMLFlattener
    ATTRIBUTE_XML = filterXML
    XML_SOURCE_TYPE = Attribute with XML document
    EMBEDDED_EXPRESSIONS = Filter
    FLATTEN_OPTIONS = <structure separator="." map-empty-elements="yes" matched-prefix="attributes" matched-attributes="yes" cardinality="+{?}" structure-prefix="" child-position-attribute="" except-expression="" ui-mode="basic" matched-ancestor-attributes=""/>
    -> AttributeExposer
AttributeExposer
    ATTR_LIST = PropertyIsEqualTo.PropertyName,PropertyIsEqualTo.Literal
    -> AttributeExposer_2
AttributeExposer_2
    ATTR_LIST = PropertyIsEqualTo.Function.Literal,PropertyIsEqualTo.Function.ValueReference,PropertyIsEqualTo.Function.name
    -> Tester_2
Tester_2
    TEST_MODE = Automatic
    TEST_DESCRIPTION = ""
    BOOL_OP = OR
    TEST_CLAUSE = TEST @Value(PropertyIsEqualTo.PropertyName) = ""
    PASSED -> AttributeCopier_3
    FAILED -> AttributeRemover
AttributeCopier_3
    ATTR_LIST = PropertyIsEqualTo.PropertyName,PropertyIsEqualTo.Function.ValueReference,PropertyIsEqualTo.Literal,PropertyIsEqualTo.Function.Literal
    -> AttributeRemover
