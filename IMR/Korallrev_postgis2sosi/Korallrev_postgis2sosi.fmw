FME workspace Korallrev_postgis2sosi.fmw
# Copyright: (c) xgrimor 2015
# Licence: <your licence>
Shutdown Python:
      # -*- coding: utf-8 -*-
      #-------------------------------------------------------------------------------
      # Name:        zipfiles.py
      # Purpose:     Pakker filer i output folderen
      #
      # Author:      xsunknu
      #
      # Created:     18.09.2015
      # Copyright:   (c) xsunknu 2015
      # Licence:     <your licence>
      #-------------------------------------------------------------------------------

      import sys, os, zipfile, fme

      def zip(sosifile, zfile):
          from os.path import basename

          # Lager korresponderende zip-fil av SOSI-fil
          if os.path.isfile(zfile):
              os.remove(zfile)

          zf = zipfile.ZipFile(zfile, "w", zipfile.ZIP_DEFLATED)

          # Ønsker ikke full sti inn i ZIP-filen
          arcname = basename(sosifile)

          # ZIP-formatet støtter ikke non-ascii tegn
          # Erstatter AØÅæøå med ascii-tegn
          arcname = arcname.replace('\xc6', 'E')
          arcname = arcname.replace('\xd8', 'O')
          arcname = arcname.replace('\xc5', 'A')
          arcname = arcname.replace('\xe6', 'e')
          arcname = arcname.replace('\xf8', 'o')
          arcname = arcname.replace('\xe5', 'a')

          zf.write(sosifile, arcname)
          zf.close()
          os.remove(sosifile)

          return

      def main():

          # Kjøres ikke på FME Server, da FME Server selv sørger for pakkingen
          if not 'FME_SERVER_DEST_DIR' in fme.macroValues:
              if 'FANOUT_FOLDER' in fme.macroValues:
                  logger = open(fme.logFileName, 'a')
                  path = fme.macroValues['FANOUT_FOLDER']
                  for dirpath, dnames, fnames in os.walk(path):
                      for f in fnames:
                          if f.endswith(".sos"):
                              # Scanner gjennom alle SOSI-filer
                              sosifile = os.path.join(path, f)
                              zfile = os.path.splitext(sosifile)[0] + '.zip'
                              if os.path.isfile(zfile):

                                  # Korresponderende ZIP-fil finnes, sjekker timestamps
                                  sositstamp = os.stat(sosifile).st_mtime
                                  ziptstamp = os.stat(zfile).st_mtime

                                  if sositstamp > ziptstamp:
                                      # SOSI-fil er nyere enn ZIP-fila, ZIP-fila oppdateres
                                      # SOSI-fila slettes
                                      try:
                                          zip(sosifile, zfile)
                                      except:
      #                                    print 'Kunne ikke pakke: ' + sosifile
                                          logger.write('Kunne ikke pakke: ' + sosifile + '\n')
                                  else:
                                      # SOSI-fila er eldre enn ZIP-fila
                                      # SOSI-fila slettes
                                      try:
                                          os.remove(sosifile)
                                      except:
      #                                    print 'Kunne ikke slette: ' + sosifile
                                          logger.write('Kunne ikke slette: ' + sosifile + '\n')
                              else:
                                  # ZIP-fila eksisterer ikke og lages
                                  # SOSI-fila slettes
                                  try:
                                      zip(sosifile, zfile)
                                  except:
      #                                print 'Kunne ikke pakke: ' + sosifile
                                      logger.write('Kunne ikke pakke: ' + sosifile + '\n')

                  logger.close()

      if __name__ == '__main__':
          main()

Parameters:
- KNR =   # Kommune(r)
- FNR =   # Fylke(r)
- CLIPPERCOORDS =   # Clipper coordinates
- CLIPPER_EPSG_CODE =   # Clipper EPSG code
- CLIPPER_FILE =   # "" Clipper file (any format)
- OUTPUT_EPSG_CODE = 25833   # Output EPSG code
- FANOUT = Norge   # Fanout områder
- CONFIG_FILE:   # Python Script
      #-------------------------------------------------------------------------------
      # Name:        GetConfigFile
      # Purpose:
      #
      # Author:      xsunknu
      #
      # Created:     21.08.2015
      # Copyright:   (c) xsunknu 2015
      # Licence:     <your licence>
      #-------------------------------------------------------------------------------
      
      import os, fme
      
      fmwdir = fme.macroValues['FME_MF_DIR']
      fmwfile = fme.macroValues['FME_MF_NAME']
      
      fmwfile = os.path.join(fmwdir, fmwfile)
      configfile = os.path.splitext(fmwfile)[0] + '_config.xml'
      
      return configfile
- PG_PWD:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgpwd').text
      
      return value
- PG_USER:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pguser').text
      
      return value
- PG_HOST:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pghost').text
      
      return value
- PG_DB:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgdb').text
      
      return value
- SOSI_FILE = korallrev   # SOSI file 
- MAPPING_FILE:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme, os
      from xml.etree import ElementTree as ET
      
      #Read XML config file
      configtree = ET.parse(fme.macroValues['CONFIG_FILE'])
      configdoc = configtree.getroot()
      
      value = os.path.join(fme.macroValues['FME_MF_DIR'], configdoc.find('mappingfile').text)
      
      return value
- SOSIDEF_FILE:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme, os
      from xml.etree import ElementTree as ET
      
      #Read XML config file
      configtree = ET.parse(fme.macroValues['CONFIG_FILE'])
      configdoc = configtree.getroot()
      
      value = os.path.join(fme.macroValues['FME_MF_DIR'], configdoc.find('sosideffile').text)
      
      return value
- FIXEDCLIPPERCOORDS:   # Python Script
      #-------------------------------------------------------------------------------
      # Name:        FixClipperCoords
      # Purpose:
      #
      # Author:      xsunknu
      #
      # Created:     21.08.2015
      # Copyright:   (c) xsunknu 2015
      # Licence:     <your licence>
      #-------------------------------------------------------------------------------
      
      import fme
      clippercoords = fme.macroValues['CLIPPERCOORDS']
      
      if clippercoords == '':
          clippercoords = '1 1'
      
      return clippercoords
- DESTCOORDSYS:   # Python Script
      #-------------------------------------------------------------------------------
      # Name:        SetCoordinateSystem
      # Purpose:
      #
      # Author:      xsunknu
      #
      # Created:     21.08.2015
      # Copyright:   (c) xsunknu 2015
      # Licence:     <your licence>
      #-------------------------------------------------------------------------------
      
      import os, fme
      
      EPSGvalue = fme.macroValues['OUTPUT_EPSG_CODE']
      EPSGcode  = 'EPSG:' + EPSGvalue
      
      return EPSGcode
- CLIPPERCOORDSYS:   # Python Script
      #-------------------------------------------------------------------------------
      # Name:        SetCoordinateSystem
      # Purpose:
      #
      # Author:      xsunknu
      #
      # Created:     21.08.2015
      # Copyright:   (c) xsunknu 2015
      # Licence:     <your licence>
      #-------------------------------------------------------------------------------
      
      import os, fme
      
      EPSGvalue = fme.macroValues['CLIPPER_EPSG_CODE']
      EPSGcode  = 'EPSG:' + EPSGvalue
      
      return EPSGcode
- LOG_FILE:   # Python Script
      #-------------------------------------------------------------------------------
      # Name:        GetConfigFile
      # Purpose:
      #
      # Author:      xsunknu
      #
      # Created:     21.08.2015
      # Copyright:   (c) xsunknu 2015
      # Licence:     <your licence>
      #-------------------------------------------------------------------------------
      
      import os, uuid, fme
      
      fmwdir = fme.macroValues['FME_MF_DIR']
      fmwfile = fme.macroValues['FME_MF_NAME']
      
      logdir = os.path.join(fmwdir, 'log')
      if not os.path.isdir(logdir):
          os.mkdir(logdir)
      
      logfile = os.path.splitext(fmwfile)[0] + '_' + str(uuid.uuid1()).replace('-','') + '.log'
      logfile = os.path.join(logdir, logfile)
      
      return logfile
- FANOUT_FOLDER:   # Python Script
      #-------------------------------------------------------------------------------
      # Name:        GetConfigFile
      # Purpose:
      #
      # Author:      xsunknu
      #
      # Created:     21.08.2015
      # Copyright:   (c) xsunknu 2015
      # Licence:     <your licence>
      #-------------------------------------------------------------------------------
      
      import os, fme
      from xml.etree import ElementTree as ET
      
      if 'FME_SERVER_DEST_DIR' in fme.macroValues:
          value = fme.macroValues['FME_SERVER_DEST_DIR']
      else:
          #Read XML config file
          configtree = ET.parse(fme.macroValues['CONFIG_FILE'])
          configdoc = configtree.getroot()
          value = configdoc.find('destdir').text
      
      return value

Readers:
- POSTGIS_1: POSTGIS from $(PG_DB)
- POSTGIS_2: POSTGIS from $(PG_DB)

Writers:
- SOSI_1: SOSI to D:\GeoNorge\IMR\korallrev.sos in $(DESTCOORDSYS)

korallrev.v_korallrev (reader POSTGIS_2)
    attributes: objid int4, objtype varchar(32), obs_metode varchar(80), obs_sted varchar(80), obs_start timestamp, obs_slutt timestamp, bmnatyp varchar(80), bm_kildenavn varchar(80), bm_kildetittel varchar(80), bmkildtyp varchar(80), bm_kildear int4, dybde_min int4, dybde_max int4, lokalid uuid, navnerom varchar(80), versjonid varchar(80), verifiseringsdato timestamp, malemetode varchar(80), noyaktighet int4, synbarhet varchar(80), h_malemetode varchar(80), h_noyaktighet int4, max_avvik int4, medium varchar(80), opphav varchar(80), noyaktighetsklasse varchar(80), produkt varchar(80), versjon varchar(80), k_kommuneid int4, k_navn varchar(80),
      f_fylkeid int4, f_navn varchar(80)
    -> ClipperAttributeCreator
ClipperAttributeCreator: AttributeCreator
    ATTR_LIST = _clippercoords,$(CLIPPERCOORDS),_clipper_file,$(CLIPPER_FILE),_fnr,$(FNR),_knr,$(KNR)
    -> ClipperTester
ClipperTester: TestFilter
    DEFAULT_VALUE = <UNFILTERED>
    TEST_LIST:
      BOOL_OP,AND,COMPOSITE_TEST,<Unused>,TEST_CLAUSE,"TEST _clipper_file ATTRIBUTE_IS_EMPTY """"
      TEST _clippercoords ATTRIBUTE_IS_EMPTY """"
      TEST _fnr ATTRIBUTE_IS_EMPTY """"
      TEST _knr ATTRIBUTE_IS_EMPTY """"",Landsdekkende,BOOL_OP,AND,COMPOSITE_TEST,<Unused>,TEST_CLAUSE,"TEST _clipper_file ATTRIBUTE_IS_EMPTY """"
      TEST _clippercoords ATTRIBUTE_IS_EMPTY """"
      TEST _fnr NOT_ATTRIBUTE_IS_EMPTY """"
      TEST _knr ATTRIBUTE_IS_EMPTY """"",Fylkesvis,BOOL_OP,AND,COMPOSITE_TEST,<Unused>,TEST_CLAUSE,"TEST _clipper_file ATTRIBUTE_IS_EMPTY """"
      TEST _clippercoords ATTRIBUTE_IS_EMPTY """"
      TEST _fnr ATTRIBUTE_IS_EMPTY """"
      TEST _knr NOT_ATTRIBUTE_IS_EMPTY """"",Kommunevis
    Landsdekkende -> Destination_Reprojector
    Fylkesvis -> Clipper [input 2]
    Kommunevis -> Clipper [input 2]
CreateClipper
    DESTCOORDSYS = $(DESTCOORDSYS)
    CLIPPERCOORDSYS = $(CLIPPERCOORDSYS)
    CLIPPERCOORDS = $(FIXEDCLIPPERCOORDS)
    reprojectBboxESRI_REPROJECTED_2 -> Clipper [input 1]
Note: Clipper klipper datakilden mot det, eller de, valgte klippeobjektene: / - Kommuner og/eller fylker / - Polygon(er) spesifisert i en klippefil / - Et fritt valgt polygon basert på inntastede koordinater
Clipper
    BOUNDARY_CASES = Treat as Inside
    CLIP_TYPE = Multiple Clippers
    ATTR_CONFLICT_RES = Use Clippee
    CLIPPED_ATTR = _clipped
    CREATE_AGGREGATES = Yes
    ATTR_ACCUM_MODE = Merge Clipper
    PRESERVE_CLIPPEE_EXTENTS = No
    INSIDE -> Destination_Reprojector
    <REJECTED> -> Clipper_Rejected_Logger
Note: Reprojiserer data til ut-koordinatsystem.
Destination_Reprojector: Reprojector
    RASTER_CELL_SIZE = Preserve Cells
    DEST = $(DESTCOORDSYS)
    SOURCE = Read from feature
    INTERPOLATION_TYPE_NAME = Nearest Neighbor
    REPROJECTED -> SOSIfile_AttributeCreator
Note: Her genererer vi filnavnet til SOSI-filen basert på hvilken FANOUT vi har spesifisert.
SOSIfile_AttributeCreator: AttributeCreator
    ATTR_LIST = sosifile,"FME_CONDITIONAL:DEFAULT_VALUE'Havforskningsinstituttet_$(OUTPUT_EPSG_CODE)_$(SOSI_FILE)_SOSI'BOOL_OP;OR;COMPOSITE_TEST;<Unused>;TEST $(FANOUT) LIKE Kommuner'Havforskningsinstituttet_@PadLeft(@Value(k_kommuneid),4,0)_@Value(k_navn)_$(OUTPUT_EPSG_CODE)_$(SOSI_FILE)_SOSI'BOOL_OP;OR;COMPOSITE_TEST;<Unused>;TEST $(FANOUT) LIKE Fylker'Havforskningsinstituttet_@PadLeft(@Value(f_fylkeid),2,0)_@Value(f_navn)_$(OUTPUT_EPSG_CODE)_$(SOSI_FILE)_SOSI'BOOL_OP;OR;COMPOSITE_TEST;<Unused>;TEST $(FANOUT) LIKE Norge'Havforskningsinstituttet_Norge_$(OUTPUT_EPSG_CODE)_$(SOSI_FILE)_SOSI'FME_NUM_CONDITIONS4___"
    -> korallrev.korallrev (writer SOSI_1)
Note: Writer er satt opp til "Fanout by attribute" for å klare å skrive til [FME_SERVER_OUTPUT_DIR]. Attributtet vi bruker som "fanout" er SosiFile, som er opprettet til dette formålet. Filnavnet det skrives til blir da: / [FME_SERVER_OUTPUT_DIR][SosiFile].sos
korallrev.korallrev (writer SOSI_1)
    attributes: objid SOSI_int32, objtype SOSI_varchar(32), obs_metode SOSI_varchar(80), obs_sted SOSI_varchar(80), obs_start SOSI_datetime, obs_slutt SOSI_datetime, bmnatyp SOSI_varchar(80), bm_kildenavn SOSI_varchar(80), bm_kildetittel SOSI_varchar(80), bmkildtyp SOSI_varchar(80), bm_kildear SOSI_int32, dybde_min SOSI_int32, dybde_max SOSI_int32, lokalid SOSI_buffer, navnerom SOSI_varchar(80), versjonid SOSI_varchar(80), verifiseringsdato SOSI_datetime, malemetode SOSI_varchar(80), synbarhet SOSI_varchar(80), max_avvik SOSI_int32, medium SOSI_varchar(80), opphav SOSI_varchar(80), produkt SOSI_varchar(80), versjon SOSI_varchar(80), noyaktighet SOSI_int32, h_malemetode SOSI_varchar(80), h_noyaktighet SOSI_int32, noyaktighetsklasse SOSI_varchar(80)
Clipper_Rejected_Logger: Logger
    MAXFEATS = 20
    MESSAGE = Dette koralrevet er utenfor kjent posisjon:
    MAXCOORDS = 20

Bookmark: Fylke og/eller kommune clippers
admingrense.fylkeflate (reader POSTGIS_1)
    attributes: fylkeid int4, navn varchar(80)
    -> Fylkeid_Tester
    -> HeleNorge_AttributeCreator
HeleNorge_AttributeCreator: AttributeCreator
    ATTR_LIST = _clippercoords,$(CLIPPERCOORDS),_clipper_file,$(CLIPPER_FILE),_fnr,$(FNR),_knr,$(KNR)
    -> HeleNorge_Tester
HeleNorge_Tester: Tester
    BOOL_OP = AND
    TEST_MODE = Automatic
    TEST_CLAUSE:
      TEST _clipper_file ATTRIBUTE_IS_EMPTY ""
      TEST _clippercoords ATTRIBUTE_IS_EMPTY ""
      TEST _fnr ATTRIBUTE_IS_EMPTY ""
      TEST _knr ATTRIBUTE_IS_EMPTY ""
    TEST_DESCRIPTION = ""
    PASSED -> AdminFlateReprojector
Fylkeid_Tester: Tester
    BOOL_OP = OR
    TEST_MODE = Automatic
    TEST_CLAUSE = TEST @Value(fylkeid) IN $(FNR)
    TEST_DESCRIPTION = ""
    PASSED -> AdminFlateReprojector
admingrense.kommuneflate (reader POSTGIS_1)
    attributes: kommuneid int4, navn varchar(80)
    -> kommuneid_Tester
kommuneid_Tester: Tester
    BOOL_OP = OR
    TEST_MODE = Automatic
    TEST_CLAUSE = TEST @Value(kommuneid) IN $(KNR)
    TEST_DESCRIPTION = ""
    PASSED -> AdminFlateReprojector
AdminFlateReprojector: Reprojector
    RASTER_CELL_SIZE = Preserve Cells
    DEST = EPSG:4258
    SOURCE = Read from feature
    INTERPOLATION_TYPE_NAME = Nearest Neighbor
    REPROJECTED -> Clipper [input 1]

Bookmark: Clipper file (any format)
Creator
    NUM = 1
    GEOMTYPE = Geometry Object
    CREATED -> ClipperFile_FeatureReader
ClipperFile_FeatureReader: FeatureReader
    DATASET = $(CLIPPER_FILE)
    FORMAT = GENERIC
    COMBINE_GEOM = Use Result
    ATTRIBUTES = NewFeatureType,
    OUTPUT_FEATURES_DISPLAY = Based on Connections
    INTERACT = <No Spatial Filter>
    GENERIC_REAL_FORMAT = GUESS_FROM_EXTENSION
    ATTR_ACCUM_MODE = Only Use Result
    FEATURETYPES_RADIO = FEATURETYPES
    <OTHER> -> ClipperFileReprojector
ClipperFileReprojector: Reprojector
    RASTER_CELL_SIZE = Preserve Cells
    DEST = EPSG:4258
    SOURCE = Read from feature
    INTERPOLATION_TYPE_NAME = Nearest Neighbor
    REPROJECTED -> Clipper [input 1]

FME custom transformer CreateClipper

Parameters:
- CLIPPERCOORDS = 253577 6650999 253577 6651246 253763 6651246 253763 6650999 253577 6650999   # Clipper Coordinate List
- CLIPPERCOORDSYS = EPSG:25833   # Clipper Coordinate System
- DESTCOORDSYS = "ESRIWKT|ETRS_1989_UTM_Zone_35N|PROJCS["ETRS_1989_UTM_Zone_35N",GEOGCS["GCS_ETRS_1989",DATUM["D_ETRS_1989",SPHEROID["GRS_1980",6378137.0,298.257222101]],PRIMEM["Greenwich",0.0],UNIT["Degree",0.0174532925199433]],PROJECTION["Transverse_Mercator"],PARAMETER["False_Easting",500000.0],PARAMETER["False_Northing",0.0],PARAMETER["Central_Meridian",27.0],PARAMETER["Scale_Factor",0.9996],PARAMETER["Latitude_Of_Origin",0.0],UNIT["Meter",1.0]]"   # Destination Coordinate System

Note: Creating geometry from / the Clipper coords
Creator
    NUM = 1
    COORDS = $(CLIPPERCOORDS)
    GEOMTYPE = 2D Coordinate List
    COORDSYS = $(CLIPPERCOORDSYS)
    CREATED -> BoundingBoxAccumulator
Note: Calculating the bounding / box (envelope) from the geometry
BoundingBoxAccumulator
    TOPFER_INDEX = No
    BOUNDING_BOX -> SpatialFilter [input 1]
    ORIGINAL -> SpatialFilter [input 2]
Note: If the geometry is equal to its / own bounding box - it is a rectangle!
SpatialFilter
    PREDICATES = EQUALS
    BASE_TYPE = Single Base
    PREDATTR = _predicate
    PASS_CRITERIA = Pass Against One Base
    MERGE_ATTRS = No
    USE_BOUNDING_BOX = No
    CURVE_BOUNDARY_RULE_PARAM = Default Rule
    PASSED -> Reprojector
    FAILED -> Reprojector_2
Note: If rectangle, reproject the / geometry to the destination / coordinate system
Reprojector
    RASTER_CELL_SIZE = Preserve Cells
    DEST = $(DESTCOORDSYS)
    STROKE_ARCS = Yes
    SOURCE = Read from feature
    INTERPOLATION_TYPE_NAME = Nearest Neighbor
    REPROJECTED -> BoundingBoxAccumulator_2
Note: Then calculate the bounding / box from the projected geoemtry
BoundingBoxAccumulator_2
    TOPFER_INDEX = No
    BOUNDING_BOX -> Reprojector_3
Note: Reproject the geometry back to / the DB coordsys (LL/EUREF89)
Reprojector_3
    RASTER_CELL_SIZE = Preserve Cells
    DEST = EPSG:4258
    STROKE_ARCS = Yes
    SOURCE = Read from feature
    INTERPOLATION_TYPE_NAME = Nearest Neighbor
    REPROJECTED -> reprojectBboxESRI_REPROJECTED_2 (output)
Note: Reproject clipper to / the DB coordsys (LL/EUREF89)
Reprojector_2
    RASTER_CELL_SIZE = Preserve Cells
    DEST = EPSG:4258
    STROKE_ARCS = Yes
    SOURCE = Read from feature
    INTERPOLATION_TYPE_NAME = Nearest Neighbor
    REPROJECTED -> reprojectBboxESRI_REPROJECTED_2 (output)
reprojectBboxESRI_REPROJECTED_2 (output)
