FME workspace KorallrevAtomFeed.fmw
Title: SOSI ATOM Data Download Feed
Description: Pakka data for SOSI tilbys.
Requirements: FME 2015.0+
History: 23/02/2015,N Wlock,Created

Parameters:
- FMEServerRoot = http://nnrite507   # Base URL for the FME Server host
- Title = IMR ATOM Feed: IMR Data
- Description = IMR data for korallrev
- Author = Per Arne Horneland   # Author of ATOM service
- Repository_Name = IMR   # Server Repository name which contains workspace(s)
- workspaceName = Korallrev_postgis2sosi.fmw   # INSPIRE Data Streaming Workspace(s) on FME Server
- LastUpdate = 2015-08-27T 09:50Z   # Date the workspace was last updated
- FMEVersion = 2015.1   # Version of FME being used

Writers:
- GEORSS_1: GEORSS to $(FME_MF_DIR)ATOM\DSBAtomFeed.xml

Note: Explodes options.option{}
ListExploder
    INDEX_ATTR = _element_index
    MODE = List Elements and Original Attributes
    LIST_ATTR = options.option{}

Bookmark: Feed
Creator_2
    NUM = 1
    GEOMTYPE = Geometry Object
    CREATED -> AttributeCreator
AttributeCreator
    ATTR_LIST = Title,$(Title),Description,$(Description),LinkURI,$(FMEServerRoot)/$(Repository_Name),Id,$(FMEServerRoot)/$(Repository_Name),LastUpdate,$(LastUpdate),LinkRelation,self,LinkType,application/atom+xml,Copyright,IMR,Description,$(Description),GeneratorURI,$(FMEServerRoot),GeneratorVersion,$(FMEVersion)
    -> Feed (writer GEORSS_1)
Feed (writer GEORSS_1)

Bookmark: Entry
Creator_3
    NUM = 1
    GEOMTYPE = Geometry Object
    CREATED -> AttributeCreator_5
Entry (writer GEORSS_1)

Bookmark: Set Up Entry Content with Download Link
Note: Creates the download URL
AttributeCreator_5
    ATTR_LIST = DownloadUrl,$(FMEServerRoot)/fmedatastreaming/$(Repository_Name)/$(workspaceName)?OUTPUT_EPSG_CODE=25833,name,IMR,value,IMR SOSI Data
    -> AttributeCreator_2
AttributeCreator_2
    ATTR_LIST = Title,@Value(value),Content,Trykk på linken for å laste ned data. <br />  <a href="@Value(DownloadUrl)">@Value(value)<\a>,Description,Data over korallforekomster fra Havforskningsinstituttet. Trykk på linken for nedlasting: @Value(value),ContentType,html,LastUpdate,$(LastUpdate),Id,@Value(DownloadUrl),Category{0}.Category,EPSG:25833,Category{0}.Domain,http://www.opengis.net/def/crs/,Category{0}.Label,EPSG/0/25833,Author,Per Arne Horneland,Copyright,Havforskningsinstituttet,LinkURI,@Value(DownloadUrl)
    -> Entry (writer GEORSS_1)
