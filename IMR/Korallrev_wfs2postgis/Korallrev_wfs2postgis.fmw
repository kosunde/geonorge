FME workspace Korallrev_wfs2postgis.fmw

Parameters:
- CONFIG_FILE:   # Python Script
      #-------------------------------------------------------------------------------
      # Name:        GetConfigFile
      # Purpose:
      #
      # Author:      xsunknu
      #
      # Created:     21.08.2015
      # Copyright:   (c) xsunknu 2015
      # Licence:     <your licence>
      #-------------------------------------------------------------------------------
      
      import os, fme
      
      fmwdir = fme.macroValues['FME_MF_DIR']
      fmwfile = fme.macroValues['FME_MF_NAME']
      
      fmwfile = os.path.join(fmwdir, fmwfile)
      configfile = os.path.splitext(fmwfile)[0] + '_config.xml'
      
      return configfile
- WFS_IN:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('wfsin').text
      
      return value
- PG_DB:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgdb').text
      
      return value
- COORDSYS_OUT = EPSG:4258   # Destination Coordinate System
- LOG_FILE:   # Python Script
      #-------------------------------------------------------------------------------
      # Name:        GetConfigFile
      # Purpose:
      #
      # Author:      xsunknu
      #
      # Created:     21.08.2015
      # Copyright:   (c) xsunknu 2015
      # Licence:     <your licence>
      #-------------------------------------------------------------------------------
      
      import os, uuid, fme
      
      fmwdir = fme.macroValues['FME_MF_DIR']
      fmwfile = fme.macroValues['FME_MF_NAME']
      
      logdir = os.path.join(fmwdir, 'log')
      if not os.path.isdir(logdir):
          os.mkdir(logdir)
      
      logfile = os.path.splitext(fmwfile)[0] + '_' + str(uuid.uuid1()).replace('-','') + '.log'
      logfile = os.path.join(logdir, logfile)
      
      return logfile

Readers:
- WFS_1: WFS from $(WFS_IN)

Writers:
- POSTGIS_1: POSTGIS to $(PG_DB) in $(COORDSYS_OUT)

coralreefs (reader WFS_1)
    attributes: gml_parent_id xml_buffer, gml_parent_property xml_buffer, gml_id xml_buffer, the_geom xml_geometry, OBJTYPE xml_buffer, OBJTYPE.xsi_nil xml_boolean, OBS_METODE xml_buffer, OBS_METODE.xsi_nil xml_boolean, OBS_STED xml_buffer, OBS_STED.xsi_nil xml_boolean, OBS_START xml_buffer, OBS_START.xsi_nil xml_boolean, OBS_SLUTT xml_buffer, OBS_SLUTT.xsi_nil xml_boolean, BMNATYP xml_buffer, BMNATYP.xsi_nil xml_boolean, BM_KILDENA xml_buffer, BM_KILDENA.xsi_nil xml_boolean, DYBDE_MIN xml_real64, DYBDE_MIN.xsi_nil xml_boolean, DYBDE_MAX xml_buffer, DYBDE_MAX.xsi_nil xml_boolean, VERIFISERI xml_buffer, VERIFISERI.xsi_nil xml_boolean, MALEMETODE xml_buffer, MALEMETODE.xsi_nil xml_boolean, NØYAKTIGH xml_real64, NØYAKTIGH.xsi_nil xml_boolean, MEDIUM xml_buffer, MEDIUM.xsi_nil xml_boolean,
      OPPHAV xml_buffer, OPPHAV.xsi_nil xml_boolean, NOYAKTIGHE xml_buffer, NOYAKTIGHE.xsi_nil xml_boolean, PRODUKT xml_buffer, PRODUKT.xsi_nil xml_boolean, VERSJON xml_buffer, VERSJON.xsi_nil xml_boolean
    -> BulkAttributeRemover
Note: WFS'en inneholder en del attributter / som ender på ".xsi_nil". Disse trenger / vi ikke og de fjernes.
BulkAttributeRemover
    ATTR_EXP = .xsi_nil
    -> BulkAttributeRenamer
Note: Attributtlisten inneholder variabelnavn med store bokstaver. Vi endrer til små...
BulkAttributeRenamer
    CASE_CHANGE_TYPE = lowercase
    ATTRCHOICE = All Attributes
    PATTERN_ACTION_DISP = Change Case
    -> Reprojector
Note: ETRS89 LL -> EPSG:4258
Reprojector
    INTERPOLATION_TYPE_NAME = Nearest Neighbor
    SOURCE = Read from feature
    DEST = $(COORDSYS_OUT)
    RASTER_CELL_SIZE = Preserve Cells
    REPROJECTED -> LOKALID_UUIDGenerator
Note: LOKALID skal være en UUID, / vi genererer denne her.
LOKALID_UUIDGenerator: UUIDGenerator
    UUID_ATTR = lokalid
    -> Obs_slutt_Creator
DATO_NullSetter: NullAttributeMapper
    NEW_VALUE = 1899-12-31
    ATTRLIST = obs_slutt obs_start verifiseringsdato
    ATTRCHOICE = Selected Attributes
    NULL_TREATMENT = New Value
    SOURCE_ATTR_VAL = Null
    -> NullAttributeMapper
Note: Setter strenger lik "tom streng" / dersom de har verdien <NULL>.
NullAttributeMapper
    ATTRLIST = bm_kildear bm_kildenavn bm_kildetittel bmkildtyp bmnatyp malemetode medium noyaktighetsklasse obs_metode opphav produkt versjon obs_sted
    ATTRCHOICE = Selected Attributes
    NULL_TREATMENT = Empty String
    SOURCE_ATTR_VAL = Null
    -> OBS_START_DateFormatter
Note: OBJID er en PostgreSQL kolonne, / har ingenting med SOSI å gjøre. Dette / er en PK i PG og populeres med en teller.
OBJID_Counter: Counter
    DOMAIN = counter
    CNT_ATTR = objid
    SCOPE = Global
    START = 1
    -> korallrev.korallrev (writer POSTGIS_1)
korallrev.korallrev (writer POSTGIS_1)
    attributes: objid serial,PRIKEY, objtype varchar(32), obs_metode varchar(100), obs_sted varchar(100), obs_start timestamp, obs_slutt timestamp, bmnatyp varchar(5), bm_kildenavn varchar(20), bm_kildetittel varchar(20), bmkildtyp int2, bm_kildear int4, dybde_min int4, dybde_max int4, lokalid uuid,PRIKEY, navnerom varchar(100), versjonid varchar(100), verifiseringsdato timestamp, malemetode int2, noyaktighet int4, synbarhet int2, h_malemetode int4, h_noyaktighet int4, max_avvik int4, medium varchar(1), opphav varchar(255), noyaktighetsklasse int2, produkt varchar(50), versjon varchar(20)

Bookmark: Oppretter attributter
Obs_slutt_Creator: AttributeCreator
    ATTR_LIST = obs_slutt,"FME_CONDITIONAL:DEFAULT_VALUE'20001231'BOOL_OP;OR;COMPOSITE_TEST;<Unused>;TEST @Value(obs_slutt) = D'19100101'BOOL_OP;OR;COMPOSITE_TEST;<Unused>;TEST @Value(obs_slutt) = DD'19200202'BOOL_OP;OR;COMPOSITE_TEST;<Unused>;TEST @Value(obs_slutt) = U'19300303'BOOL_OP;OR;COMPOSITE_TEST;<Unused>;TEST @Value(obs_slutt) = Y'19400404'BOOL_OP;OR;COMPOSITE_TEST;<Unused>;TEST @Value(obs_slutt) = YY'19500505'FME_NUM_CONDITIONS6___"
    -> SOSI_AttributeCreator
SOSI_AttributeCreator: AttributeCreator
    ATTR_LIST = bm_kildear,1899,bm_kildetittel,FME_NULL_VALUE,bmkildtyp,9,h_malemetode,70,h_noyaktighet,FME_NULL_VALUE,max_avvik,FME_NULL_VALUE,navnerom,no_Korallrev_20150408,synbarhet,0,versjonid,FME_NULL_VALUE
    -> Malemetode_ValueMapper
Malemetode_ValueMapper: AttributeValueMapper
    DIRECTION = Forward (Source To Destination)
    LUT = Annet  (denne har ingen mening, bør fjernes?),19,Annet (spesifiseres i filhode) ( bør vel fjernes, blir borte ved overføring mellom systemer),79,Digitaliseringsbord: Kart,50,Digitaliseringsbord: Kart, blyantoriginal,51,Digitaliseringsbord: Kart, papirkopi,55,Digitalisert på skjerm fra andre digitale rasterdata,47,Digitalisert på skjerm fra skannet kart,56,Digitalisert på skjerm fra tolkning av seismikk,48,Fastsatt punkt,77,Frihåndstegning på kart,81,Frihåndstegning på skjerm,82,GNSS: Fasemåling , float-løsning,97,GNSS: Fasemåling RTK,96,GNSS: Fasemåling, andre metoder,94,GNSS: Kodemåling, enkle målinger,92,GNSS: Kodemåling, relative målinger,91,Genererte data (interpolasjon),60,Genererte data (interpolasjon): Terrengmodell,61,Genererte data (interpolasjon): Vektet middel,62,Genererte data: Fra annen geometri,63,Genererte data: Generalisering,64,Genererte data: Sentralpunkt,65,Kombinasjon av GNSS/Treghet,95,Lineær referanse,38,Scannet fra kart,30,Skannet fra kart: Blyantoriginal,31,Skannet fra kart: Papirkopi,35,Skannet fra kart: Rissefolie,32,Skannet fra kart: Transparent folie, god kvalitet,33,Skannet fra kart: Transparent folie, mindre god kvalitet,34,Spesielle metoder,70,Spesielle metoder: Målt med stigningsmåler,74,Tatt fra plan,18,Terrengmålt: Uspesifisert måleinstrument,10,Ukjent målemetode,99,Beregnet,69,Frihåndstegning,80,Utmål,15
    VAL_ATTR = malemetode_looked_up
    SRC = malemetode
    -> Bmnatyp_ValueMapper
Bmnatyp_ValueMapper: AttributeValueMapper
    DIRECTION = Forward (Source To Destination)
    LUT = Andre viktige marine naturtyper,I15,Annen viktig forekomst,H,Rikt strandberg,G09,Spesielt dype fjordområder,I04,Sterke tidevannsstrømmer,I02,Større kamskjellforekomster,I14,Større tareforekomster,I01,Ålegrasenger og andre undervannsenger,I11,Korallforekomster,I09,Sanddyne,G03,Skjellsandforekomster,I12,Tangvoll,G06,Undervannseng,G02,Østersforekomster,I13
    VAL_ATTR = bmnatyp_looked_up
    SRC = bmnatyp
    -> Noyaktighetsklasse_ValueMapper
Noyaktighetsklasse_ValueMapper: AttributeValueMapper
    DIRECTION = Forward (Source To Destination)
    LUT = Meget god,3,Mindre god,1,Særs god,4,God,2
    VAL_ATTR = noyaktighetsklasse
    SRC = noyaktighe
    -> AttributeRemover
AttributeRemover
    REMOVE_ATTRS = bmnatyp,malemetode,noyaktighe
    -> SOSI_AttributeRenamer
SOSI_AttributeRenamer: AttributeRenamer
    ATTR_LIST = bm_kildena,bm_kildenavn,,verifiseri,verifiseringsdato,,malemetode_looked_up,malemetode,,bmnatyp_looked_up,bmnatyp,,nøyaktigh,noyaktighet,
    -> DATO_NullSetter

Bookmark: Datoformattering
OBS_START_DateFormatter: DateFormatter
    INVALID_DATE_VALUE = FME_NULL_VALUE
    SRCFMT = Unknown - Automatic Detection
    DATE_ATTR = obs_start
    FMT = FME Date/Time (%Y%m%d%H%M%S)
    -> OBS_SLUTT_DateFormatter
OBS_SLUTT_DateFormatter: DateFormatter
    INVALID_DATE_VALUE = FME_NULL_VALUE
    SRCFMT = Unknown - Automatic Detection
    DATE_ATTR = obs_slutt
    FMT = FME Date/Time (%Y%m%d%H%M%S)
    -> VERIFISERINGSDATO_DateFormatter
VERIFISERINGSDATO_DateFormatter: DateFormatter
    INVALID_DATE_VALUE = FME_NULL_VALUE
    SRCFMT = Unknown - Automatic Detection
    DATE_ATTR = verifiseringsdato
    FMT = FME Date/Time (%Y%m%d%H%M%S)
    -> OBJID_Counter
