FME workspace Korallrev_AtomFeed_old.fmw
Title: SOSI ATOM Data Download Feed
Description: Pakka data for SOSI tilbys.
Requirements: FME 2015.0+
History: 23/02/2015,N Wlock,Created

Parameters:
- FMEServerRoot = http://nnrite507   # Base URL for the FME Server host
- Title = ATOM Feed: Korallrev
- Description = Datasettet Korallrev viser dokumenterte og stedfestede korallrev av steinkorallen Lophelia pertusa. Forekomstene av korallrev er angitt som punkter på kart. Disse utgjør verdifull informasjon som beslutningsgrunnlag ved vurdering av nye oppdrettskonsesjoner, utslipp i sjø, deponering, utbygging av petroleumsrelaterte installasjoner, og regulering av fiskeriaktivitet.
- Author = Geonorge   # Author of ATOM service
- Repository_Name = IMR   # Server Repository name which contains workspace(s)
- workspaceName = Korallrev_postgis2sosi.fmw   # INSPIRE Data Streaming Workspace(s) on FME Server
- LastUpdate = 2015-08-19T16:15Z   # Date the workspace was last updated
- FMEVersion = 2015.1.1.0   # Version of FME being used

Writers:
- GEORSS_1: GEORSS to Z:\Geonorge\IMR\ATOM\IMRAtomFeed.xml

Entry (writer GEORSS_1)

Bookmark: Fylker
Creator_4
    NUM = 19
    GEOMTYPE = Geometry Object
    CREATED -> AttributeValueMapper_2
Note: Lager FylkesID-attributt
AttributeValueMapper_2
    VAL_ATTR = FylkesID
    DIRECTION = Forward (Source To Destination)
    LUT = 0,1,1,2,2,3,3,4,4,5,5,6,6,7,7,8,8,9,9,10,10,11,11,12,12,14,13,15,14,16,15,17,16,18,17,19,18,20
    SRC = _creation_instance
    -> AttributeValueMapper
Note: Lager Fylkesnavn-attributt
AttributeValueMapper
    VAL_ATTR = Fylkesnavn
    DIRECTION = Forward (Source To Destination)
    LUT = 1,Østfold,2,Akershus,3,Oslo,4,Hedmark,5,Oppland,6,Buskerud,7,Vestfold,8,Telemark,9,Aust-agder,10,Vest-Agder,11,Rogaland,12,Hordaland,14,Sogn og Fjordane,15,Møre og Romsdal,16,Sør-Trøndelag,17,Nord-Trøndelag,18,Nordland,19,Troms,20,Finnmark
    SRC = FylkesID
    -> AttributeCreator_9
Note: Finner lokal UTM-sone
AttributeCreator_9
    ATTR_LIST = output_epsg_code,"FME_CONDITIONAL:DEFAULT_VALUE'25833'BOOL_OP;OR;COMPOSITE_TEST;<Unused>;TEST @Value(FylkesID) < 18'25832'BOOL_OP;OR;COMPOSITE_TEST;<Unused>;TEST @Value(FylkesID) = 20'25835'FME_NUM_CONDITIONS3___",outcoordsys,"FME_CONDITIONAL:DEFAULT_VALUE'UTM33/EUREF89'BOOL_OP;OR;COMPOSITE_TEST;<Unused>;TEST @Value(FylkesID) < 18'UTM32/EUREF89'BOOL_OP;OR;COMPOSITE_TEST;<Unused>;TEST @Value(FylkesID) = 20'UTM35/EUREF89'FME_NUM_CONDITIONS3___"
    -> AttributeCreator_3
Note: Lager nedlastingsURL
AttributeCreator_3
    ATTR_LIST = DownloadUrl,$(FMEServerRoot)/fmedatastreaming/$(Repository_Name)/$(workspaceName)?CLIPPERCOORDS=&CLIPPER_EPSG_CODE=4258&CLIPPER_FILE=&OUTPUT_EPSG_CODE=@Value(output_epsg_code)&FNR=@Value(FylkesID)&FANOUT=Fylker,name,Akvakultur,value,@PadLeft(@Value(FylkesID),2,0) @Value(Fylkesnavn)
    -> AttributeCreator_4
AttributeCreator_4
    ATTR_LIST = Title,@Value(value),Content,Trykk på linken for å laste ned data på SOSI-format  (@Value(outcoordsys)). <br />  <a href="@Value(DownloadUrl)">@Value(value)<\a>,Description,Korallrev fra Havforskningsinstituttet. Trykk på linken for nedlasting: @Value(value),ContentType,html,LastUpdate,$(LastUpdate),Id,@Value(DownloadUrl),Category{0}.Category,EPSG:@Value(output_epsg_code),Category{0}.Domain,http://www.opengis.net/def/crs/,Category{0}.Label,EPSG/0/@Value(output_epsg_code),Author,Geonorge,Copyright,Havforskningsinstituttet,LinkURI,@Value(DownloadUrl)
    -> Entry (writer GEORSS_1)

Bookmark: Kommuner
Creator_5
    NUM = 428
    GEOMTYPE = Geometry Object
    CREATED -> Tester
Tester
    TEST_MODE = Automatic
    TEST_CLAUSE = TEST @Value(_creation_instance) != 0
    TEST_DESCRIPTION = ""
    BOOL_OP = OR
    PASSED -> AttributeValueMapper_4
Note: Lager KommuneID-attributt
AttributeValueMapper_4
    VAL_ATTR = KommuneID
    DIRECTION = Forward (Source To Destination)
    LUT = 1,101,2,104,3,105,4,106,5,111,6,118,7,119,8,121,9,122,10,123,11,124,12,125,13,127,14,128,15,135,16,136,17,137,18,138,19,211,20,213,21,214,22,215,23,216,24,217,25,219,26,220,27,221,28,226,29,227,30,228,31,229,32,230,33,231,34,233,35,234,36,235,37,236,38,237,39,238,40,239,41,301,42,402,43,403,44,412,45,415,46,417,47,418,48,419,49,420,50,423,51,425,52,426,53,427,54,428,55,429,56,430,57,432,58,434,59,436,60,437,61,438,62,439,63,441,64,501,65,502,66,511,67,512,68,513,69,514,70,515,71,516,72,517,73,519,74,520,75,521,76,522,77,528,78,529,79,532,80,533,81,534,82,536,83,538,84,540,85,541,86,542,87,543,88,544,89,545,90,602,91,604,92,605,93,612,94,615,95,616,96,617,97,618,98,619,99,620,100,621,101,622,102,623,103,624,104,625,105,626,106,627,107,628,108,631,109,632,110,633,111,701,112,702,113,704,114,706,115,709,116,711,117,713,118,714,119,716,120,719,121,720,122,722,123,723,124,728,125,805,126,806,127,807,128,811,129,814,130,815,131,817,132,819,133,821,134,822,135,826,136,827,137,828,138,829,139,830,140,831,141,833,142,834,143,901,144,904,145,906,146,911,147,912,148,914,149,919,150,926,151,928,152,929,153,935,154,937,155,938,156,940,157,941,158,1001,159,1002,160,1003,161,1004,162,1014,163,1017,164,1018,165,1021,166,1026,167,1027,168,1029,169,1032,170,1034,171,1037,172,1046,173,1101,174,1102,175,1103,176,1106,177,1111,178,1112,179,1114,180,1119,181,1120,182,1121,183,1122,184,1124,185,1127,186,1129,187,1130,188,1133,189,1134,190,1135,191,1141,192,1142,193,1144,194,1145,195,1146,196,1149,197,1151,198,1160,199,1201,200,1211,201,1216,202,1219,203,1221,204,1222,205,1223,206,1224,207,1227,208,1228,209,1231,210,1232,211,1233,212,1234,213,1235,214,1238,215,1241,216,1242,217,1243,218,1244,219,1245,220,1246,221,1247,222,1251,223,1252,224,1253,225,1256,226,1259,227,1260,228,1263,229,1264,230,1265,231,1266,232,1401,233,1411,234,1412,235,1413,236,1416,237,1417,238,1418,239,1419,240,1420,241,1421,242,1422,243,1424,244,1426,245,1428,246,1429,247,1430,248,1431,249,1432,250,1433,251,1438,252,1439,253,1441,254,1443,255,1444,256,1445,257,1449,258,1502,259,1504,260,1505,261,1511,262,1514,263,1515,264,1516,265,1517,266,1519,267,1520,268,1523,269,1524,270,1525,271,1526,272,1528,273,1529,274,1531,275,1532,276,1534,277,1535,278,1539,279,1543,280,1545,281,1546,282,1547,283,1548,284,1551,285,1554,286,1557,287,1560,288,1563,289,1566,290,1567,291,1571,292,1573,293,1576,294,1601,295,1612,296,1613,297,1617,298,1620,299,1621,300,1622,301,1624,302,1627,303,1630,304,1632,305,1633,306,1634,307,1635,308,1636,309,1638,310,1640,311,1644,312,1648,313,1653,314,1657,315,1662,316,1663,317,1664,318,1665,319,1702,320,1703,321,1711,322,1714,323,1717,324,1718,325,1719,326,1721,327,1724,328,1725,329,1736,330,1738,331,1739,332,1740,333,1742,334,1743,335,1744,336,1748,337,1749,338,1750,339,1751,340,1755,341,1756,342,1804,343,1805,344,1811,345,1812,346,1813,347,1815,348,1816,349,1818,350,1820,351,1822,352,1824,353,1825,354,1826,355,1827,356,1828,357,1832,358,1833,359,1834,360,1835,361,1836,362,1837,363,1838,364,1839,365,1840,366,1841,367,1845,368,1848,369,1849,370,1850,371,1851,372,1852,373,1853,374,1854,375,1856,376,1857,377,1859,378,1860,379,1865,380,1866,381,1867,382,1868,383,1870,384,1871,385,1874,386,1902,387,1903,388,1911,389,1913,390,1917,391,1919,392,1920,393,1922,394,1923,395,1924,396,1925,397,1926,398,1927,399,1928,400,1929,401,1931,402,1933,403,1936,404,1938,405,1939,406,1940,407,1941,408,1942,409,1943,410,2002,411,2003,412,2004,413,2011,414,2012,415,2014,416,2015,417,2017,418,2018,419,2019,420,2020,421,2021,422,2022,423,2023,424,2024,425,2025,426,2027,427,2028,428,2030
    SRC = _creation_instance
    -> AttributeValueMapper_3
Note: Lager kommunenavn-attributt
AttributeValueMapper_3
    VAL_ATTR = Kommunenavn
    DIRECTION = Forward (Source To Destination)
    LUT = 1001, Kristiansand,1002, Mandal,1003, Farsund,1004, Flekkefjord,101, Halden,1014, Vennesla,1017, Songdalen,1018, Søgne,1021, Marnardal,1026, Åseral,1027, Audnedal,1029, Lindesnes,1032, Lyngdal,1034, Hægebostad,1037, Kvinesdal,104, Moss,1046, Sirdal,105, Sarpsborg,106, Fredrikstad,1101, Eigersund,1102, Sandnes,1103, Stavanger,1106, Haugesund,111, Hvaler,1111, Sokndal,1112, Lund,1114, Bjerkreim,1119, Hå,1120, Klepp,1121, Time,1122, Gjesdal,1124, Sola,1127, Randaberg,1129, Forsand,1130, Strand,1133, Hjelmeland,1134, Suldal,1135, Sauda,1141, Finnøy,1142, Rennesøy,1144, Kvitsøy,1145, Bokn,1146, Tysvær,1149, Karmøy,1151, Utsira,1160, Vindafjord,118, Aremark,119, Marker,1201, Bergen,121, Rømskog,1211, Etne,1216, Sveio,1219, Bømlo,122, Trøgstad,1221, Stord,1222, Fitjar,1223, Tysnes,1224, Kvinnherad,1227, Jondal,1228, Odda,123, Spydeberg,1231, Ullensvang,1232, Eidfjord,1233, Ulvik,1234, Granvin,1235, Voss,1238, Kvam,124, Askim,1241, Fusa,1242, Samnanger,1243, Os (Hord.),1244, Austevoll,1245, Sund,1246, Fjell,1247, Askøy,125, Eidsberg,1251, Vaksdal,1252, Modalen,1253, Osterøy,1256, Meland,1259, Øygarden,1260, Radøy,1263, Lindås,1264, Austrheim,1265, Fedje,1266, Masfjorden,127, Skiptvet,128, Rakkestad,135, Råde,136, Rygge,137, Våler (Østf.),138, Hobøl,1401, Flora,1411, Gulen,1412, Solund,1413, Hyllestad,1416, Høyanger,1417, Vik,1418, Balestrand,1419, Leikanger,1420, Sogndal,1421, Aurland,1422, Lærdal,1424, Årdal,1426, Luster,1428, Askvoll,1429, Fjaler,1430, Gaular,1431, Jølster,1432, Førde,1433, Naustdal,1438, Bremanger,1439, Vågsøy,1441, Selje,1443, Eid,1444, Hornindal,1445, Gloppen,1449, Stryn,1502, Molde,1504, Ålesund,1505, Kristiansund,1511, Vanylven,1514, Sande (M. og R.),1515, Herøy (M. og R.),1516, Ulstein,1517, Hareid,1519, Volda,1520, Ørsta,1523, Ørskog,1524, Norddal,1525, Stranda,1526, Stordal,1528, Sykkylven,1529, Skodje,1531, Sula,1532, Giske,1534, Haram,1535, Vestnes,1539, Rauma,1543, Nesset,1545, Midsund,1546, Sandøy,1547, Aukra,1548, Fræna,1551, Eide,1554, Averøy,1557, Gjemnes,1560, Tingvoll,1563, Sunndal,1566, Surnadal,1567, Rindal,1571, Halsa,1573, Smøla,1576, Aure,1601, Trondheim,1612, Hemne,1613, Snillfjord,1617, Hitra,1620, Frøya,1621, Ørland,1622, Agdenes,1624, Rissa,1627, Bjugn,1630, Åfjord,1632, Roan,1633, Osen,1634, Oppdal,1635, Rennebu,1636, Meldal,1638, Orkdal,1640, Røros,1644, Holtålen,1648, Midtre Gauldal,1653, Melhus,1657, Skaun,1662, Klæbu,1663, Malvik,1664, Selbu,1665, Tydal,1702, Steinkjer,1703, Namsos,1711, Meråker,1714, Stjørdal,1717, Frosta,1718, Leksvik,1719, Levanger,1721, Verdal,1724, Verran,1725, Namdalseid,1736, Snåase Snåsa,1738, Lierne,1739, Raarvihke Røyrvik,1740, Namsskogan,1742, Grong,1743, Høylandet,1744, Overhalla,1748, Fosnes,1749, Flatanger,1750, Vikna,1751, Nærøy,1755, Leka,1756, Inderøy,1804, Bodø,1805, Narvik,1811, Bindal,1812, Sømna,1813, Brønnøy,1815, Vega,1816, Vevelstad,1818, Herøy (Nordl.),1820, Alstahaug,1822, Leirfjord,1824, Vefsn,1825, Grane,1826, Hattfjelldal,1827, Dønna,1828, Nesna,1832, Hemnes,1833, Rana,1834, Lurøy,1835, Træna,1836, Rødøy,1837, Meløy,1838, Gildeskål,1839, Beiarn,1840, Saltdal,1841, Fauske,1845, Sørfold,1848, Steigen,1849, Hábmer Hamarøy,1850, Divtasvuodna Tysfjord,1851, Lødingen,1852, Tjeldsund,1853, Evenes,1854, Ballangen,1856, Røst,1857, Værøy,1859, Flakstad,1860, Vestvågøy,1865, Vågan,1866, Hadsel,1867, Bø (Nordl.),1868, Øksnes,1870, Sortland,1871, Andøy,1874, Moskenes,1902, Tromsø,1903, Harstad,1911, Kvæfjord,1913, Skånland,1917, Ibestad,1919, Gratangen,1920, Lavangen,1922, Bardu,1923, Salangen,1924, Målselv,1925, Sørreisa,1926, Dyrøy,1927, Tranøy,1928, Torsken,1929, Berg,1931, Lenvik,1933, Balsfjord,1936, Karlsøy,1938, Lyngen,1939, Omasvuotna Storfjord Omasvuonon,1940, Gáivuotna Kåfjord,1941, Skjervøy,1942, Nordreisa,1943, Kvænangen,2002, Vardø,2003, Vadsø,2004, Hammerfest,2011, Guovdageaidnu Kautokeino,2012, Alta,2014, Loppa,2015, Hasvik,2017, Kvalsund,2018, Måsøy,2019, Nordkapp,2020, Porsanger Porsángu Porsanki,2021, Kárásjohka Karasjok,2022, Lebesby,2023, Gamvik,2024, Berlevåg,2025, Deatnu Tana,2027, Unjárga Nesseby,2028, Båtsfjord,2030, Sør-Varanger,211, Vestby,213, Ski,214, Ås,215, Frogn,216, Nesodden,217, Oppegård,219, Bærum,220, Asker,221, Aurskog-Høland,226, Sørum,227, Fet,228, Rælingen,229, Enebakk,230, Lørenskog,231, Skedsmo,233, Nittedal,234, Gjerdrum,235, Ullensaker,236, Nes (Ak.),237, Eidsvoll,238, Nannestad,239, Hurdal,301, Oslo kommune,402, Kongsvinger,403, Hamar,412, Ringsaker,415, Løten,417, Stange,418, Nord-Odal,419, Sør-Odal,420, Eidskog,423, Grue,425, Åsnes,426, Våler (Hedm.),427, Elverum,428, Trysil,429, Åmot,430, Stor-Elvdal,432, Rendalen,434, Engerdal,436, Tolga,437, Tynset,438, Alvdal,439, Folldal,441, Os (Hedm.),501, Lillehammer,502, Gjøvik,511, Dovre,512, Lesja,513, Skjåk,514, Lom,515, Vågå,516, Nord-Fron,517, Sel,519, Sør-Fron,520, Ringebu,521, Øyer,522, Gausdal,528, Østre Toten,529, Vestre Toten,532, Jevnaker,533, Lunner,534, Gran,536, Søndre Land,538, Nordre Land,540, Sør-Aurdal,541, Etnedal,542, Nord-Aurdal,543, Vestre Slidre,544, Øystre Slidre,545, Vang,602, Drammen,604, Kongsberg,605, Ringerike,612, Hole,615, Flå,616, Nes (Busk.),617, Gol,618, Hemsedal,619, Ål,620, Hol,621, Sigdal,622, Krødsherad,623, Modum,624, Øvre Eiker,625, Nedre Eiker,626, Lier,627, Røyken,628, Hurum,631, Flesberg,632, Rollag,633, Nore og Uvdal,701, Horten,702, Holmestrand (-1963),704, Tønsberg,706, Sandefjord,709, Larvik,711, Svelvik,713, Sande (Vestf.),714, Hof,716, Re,719, Andebu,720, Stokke,722, Nøtterøy,723, Tjøme,728, Lardal,805, Porsgrunn,806, Skien,807, Notodden,811, Siljan,814, Bamble,815, Kragerø,817, Drangedal,819, Nome,821, Bø (Telem.),822, Sauherad,826, Tinn,827, Hjartdal,828, Seljord,829, Kviteseid,830, Nissedal,831, Fyresdal,833, Tokke,834, Vinje,901, Risør,904, Grimstad,906, Arendal,911, Gjerstad,912, Vegårshei,914, Tvedestrand,919, Froland,926, Lillesand,928, Birkenes,929, Åmli,935, Iveland,937, Evje og Hornnes,938, Bygland,940, Valle,941, Bykle
    SRC = KommuneID
    -> AttributeCreator_8
Note: Finner lokal UTM-sone
AttributeCreator_8
    ATTR_LIST = output_epsg_code,"FME_CONDITIONAL:DEFAULT_VALUE'25833'BOOL_OP;OR;COMPOSITE_TEST;<Unused>;TEST @Value(KommuneID) < 1800'25832'BOOL_OP;OR;COMPOSITE_TEST;<Unused>;TEST @Value(KommuneID) > 2000'25835'FME_NUM_CONDITIONS3___",outcoordsys,"FME_CONDITIONAL:DEFAULT_VALUE'UTM33/EUREF89'BOOL_OP;OR;COMPOSITE_TEST;<Unused>;TEST @Value(KommuneID) < 1800'UTM32/EUREF89'BOOL_OP;OR;COMPOSITE_TEST;<Unused>;TEST @Value(KommuneID) > 2000'UTM35/EUREF89'FME_NUM_CONDITIONS3___"
    -> AttributeCreator_6
Note: Lager nedlastingsURL
AttributeCreator_6
    ATTR_LIST = DownloadUrl,$(FMEServerRoot)/fmedatastreaming/$(Repository_Name)/$(workspaceName)?CLIPPERCOORDS=&CLIPPER_EPSG_CODE=4258&CLIPPER_FILE=&OUTPUT_EPSG_CODE=@Value(output_epsg_code)&KNR=@Value(KommuneID)&FANOUT=Kommuner,name,Korallrev,value,@PadLeft(@Value(KommuneID),4,0) @Value(Kommunenavn)
    -> AttributeCreator_7
AttributeCreator_7
    ATTR_LIST = Title,@Value(value),Content,Trykk på linken for å laste ned data på SOSI-format (@Value(outcoordsys)). <br />  <a href="@Value(DownloadUrl)">@Value(value)<\a>,Description,Korallrev fra Havforskningsinstituttet. Trykk på linken for nedlasting: @Value(value),ContentType,html,LastUpdate,$(LastUpdate),Id,@Value(DownloadUrl),Category{0}.Category,EPSG:@Value(output_epsg_code),Category{0}.Domain,http://www.opengis.net/def/crs/,Category{0}.Label,EPSG/0/@Value(output_epsg_code),Author,Geonorge,Copyright,Havforskningsinstituttet,LinkURI,@Value(DownloadUrl)
    -> Entry (writer GEORSS_1)

Bookmark: Feed
Creator_2
    NUM = 1
    GEOMTYPE = Geometry Object
    CREATED -> AttributeCreator
AttributeCreator
    ATTR_LIST = Title,$(Title),Description,$(Description),LinkURI,$(FMEServerRoot)/$(Repository_Name),Id,$(FMEServerRoot)/$(Repository_Name),LastUpdate,$(LastUpdate),LinkRelation,self,LinkType,application/atom+xml,Copyright,Havforskningsinstituttet,Description,$(Description),GeneratorURI,$(FMEServerRoot),GeneratorVersion,$(FMEVersion)
    -> Feed (writer GEORSS_1)
Feed (writer GEORSS_1)

Bookmark: Hele landet
Creator_3
    NUM = 1
    GEOMTYPE = Geometry Object
    CREATED -> AttributeCreator_5

Bookmark: Set Up Entry Content with Download Link
Note: Lager nedlastingsURL for hele landet
AttributeCreator_5
    ATTR_LIST = DownloadUrl,$(FMEServerRoot)/fmedatastreaming/$(Repository_Name)/$(workspaceName)?CLIPPERCOORDS=&CLIPPER_EPSG_CODE=&CLIPPER_FILE=&OUTPUT_EPSG_CODE=25833&KNR=&FNR=&FANOUT=Norge,name,Korallrev,value,Hele Norge
    -> AttributeCreator_2
AttributeCreator_2
    ATTR_LIST = Title,@Value(value),Content,Trykk på linken for å laste ned data på SOSI-format (UTM33/EUREF89). <br />  <a href="@Value(DownloadUrl)">@Value(value)<\a>,Description,Akvakultur fra Fiskeridirektoratet.  Trykk på linken for nedlasting: @Value(value),ContentType,html,LastUpdate,$(LastUpdate),Id,@Value(DownloadUrl),Category{0}.Category,EPSG:25833,Category{0}.Domain,http://www.opengis.net/def/crs/,Category{0}.Label,EPSG/0/25833,Author,Geonorge,Copyright,Fiskeridirektoratet,LinkURI,@Value(DownloadUrl)
    -> Entry (writer GEORSS_1)
