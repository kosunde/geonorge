FME workspace Korallrev_AtomFeed.fmw
Title: SOSI ATOM Data Download Feed
Description: Pakka data for SOSI tilbys.
Requirements: FME 2015.0+
History: 23/02/2015,N Wlock,Created

Parameters:
- FMEServerRoot = http://nnrite507   # Base URL for the FME Server host
- Title = Havforskningsinstituttet ATOM Feed: Data om korallrev
- Description = Havforskningsinstituttet, data om koralrev
- Author = Per Arne Horneland   # Author of ATOM service
- Repository_Name = Havforskningsinstituttet   # Server Repository name which contains workspace(s)
- LastUpdate = 2015-08-19T16:15Z   # Date the workspace was last updated
- FMEVersion = 2015.0   # Version of FME being used
- ROTKATALOG_WEB = http://testnedlasting.geonorge.no/geonorge/Havforskningsinstituttet/Korallrev/SOSI/   # Sti til rotkatalog for SOSI-filene
- CONFIG_FILE:   # Python Script
      #-------------------------------------------------------------------------------
      # Name:        GetConfigFile
      # Purpose:
      #
      # Author:      xsunknu
      #
      # Created:     21.08.2015
      # Copyright:   (c) xsunknu 2015
      # Licence:     <your licence>
      #-------------------------------------------------------------------------------
      
      import os, fme
      
      fmwdir = fme.macroValues['FME_MF_DIR']
      fmwfile = fme.macroValues['FME_MF_NAME']
      
      fmwfile = os.path.join(fmwdir, fmwfile)
      configfile = os.path.splitext(fmwfile)[0] + '_config.xml'
      
      return configfile
- PG_DB:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgdb').text
      
      return value
- FANOUT_FOLDER:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('destdir').text
      
      return value

Readers:
- POSTGRES_1: POSTGRES from $(PG_DB)

Writers:
- GEORSS_1: GEORSS to Z:\Geonorge\IMR\ATOM\KorallrevAtomFeed.xml

Entry (writer GEORSS_1)

Bookmark: Fylker
admingrense.fylker (reader POSTGRES_1)
    attributes: fylkeid int2,PRIKEY, navn varchar(80)
    -> AttributeRangeMapper
AttributeRangeMapper
    IN_ATTR = fylkeid
    LUT = 1,17,25832,18,19,25833,20,20,25835,,,25833
    OUT_ATTR = koordsys
    -> AttributeCreator_3
Note: Lager nedlastingsURL
AttributeCreator_3
    ATTR_LIST = DownloadUrl,$(ROTKATALOG_WEB)Havforskningsinstituttet_@PadLeft(@Value(fylkeid),2,0)_@Value(navn)_@Value(koordsys)_Korallrev_SOSI.zip,name,Havforskningsinstituttet,value,Havforskningsinstituttet SOSI Data @Value(navn),_fileName,$(FANOUT_FOLDER)\Havforskningsinstituttet_@PadLeft(@Value(fylkeid),2,0)_@Value(navn)_@Value(koordsys)_Korallrev_SOSI.zip
    -> FylkeFilnavnSjekker
FylkeFilnavnSjekker: PythonCaller
    NEW_ATTRIBUTES = FILE_EXISTS
    PYTHONSOURCE:
      import fme, os
      import fmeobjects

      # Template Function interface:
      def checkFilename(feature):
          fileName = feature.getAttribute("_fileName")
          doesFileExist = os.path.exists(fileName)
          if doesFileExist:
              feature.setAttribute("FILE_EXISTS","JA")
          else:
              feature.setAttribute("FILE_EXISTS","NEI")
    PYTHONSYMBOL = checkFilename
    -> FylkeFilnavnTester
FylkeFilnavnTester: Tester
    TEST_DESCRIPTION = ""
    TEST_CLAUSE = TEST @Value(FILE_EXISTS) = JA
    BOOL_OP = OR
    TEST_MODE = Automatic
    PASSED -> AttributeCreator_4
AttributeCreator_4
    ATTR_LIST = Title,@Value(value),Content,Trykk på linken for å laste ned data for fylke @Value(fylkeid), @Value(navn) i koordinatsystemet EPSG:@Value(koordsys). <br />  <a href="@Value(DownloadUrl)">@Value(value)<\a>,Description,Oversikt over korallrev. Trykk på linken for nedlasting: @Value(value),ContentType,html,LastUpdate,$(LastUpdate),Id,@Value(DownloadUrl),Category{0}.Category,EPSG:@Value(koordsys),Category{0}.Domain,http://www.opengis.net/def/crs/,Category{0}.Label,EPSG/0/@Value(koordsys),Author,Per Arne Horneland,Copyright,Havforskninginstituttet,LinkURI,@Value(DownloadUrl),Category{1}.Category,Fylke,Category{1}.Label,@Value(navn)
    -> Entry (writer GEORSS_1)

Bookmark: Kommuner
admingrense.kommuner (reader POSTGRES_1)
    attributes: kommuneid int2,PRIKEY, navn varchar(80)
    -> AttributeRangeMapper_2
AttributeRangeMapper_2
    IN_ATTR = kommuneid
    LUT = 1,1799,25832,1800,1999,25833,2000,2099,25835,,,
    OUT_ATTR = koordsys
    -> AttributeCreator_6
Note: Lager nedlastingsURL
AttributeCreator_6
    ATTR_LIST = DownloadUrl,$(ROTKATALOG_WEB)Havforskningsinstituttet_@PadLeft(@Value(kommuneid),4,0)_@Value(navn)_@Value(koordsys)_Korallrev_SOSI.zip,name,Havforskningsinstituttet,value,Havforskniinginstituttet SOSI Data @Value(navn),_fileName,$(FANOUT_FOLDER)\Havforskningsinstituttet_@PadLeft(@Value(kommuneid),4,0)_@Value(navn)_@Value(koordsys)_Korallrev_SOSI.zip
    -> KommuneFilnavnSjekker
KommuneFilnavnSjekker: PythonCaller
    NEW_ATTRIBUTES = FILE_EXISTS
    PYTHONSOURCE:
      import fme, os
      import fmeobjects

      # Template Function interface:
      def checkFilename(feature):
          fileName = feature.getAttribute("_fileName")
          doesFileExist = os.path.exists(fileName)
          if doesFileExist:
              feature.setAttribute("FILE_EXISTS","JA")
          else:
              feature.setAttribute("FILE_EXISTS","NEI")
    PYTHONSYMBOL = checkFilename
    -> KommuneFilnavnTester
KommuneFilnavnTester: Tester
    TEST_DESCRIPTION = ""
    TEST_CLAUSE = TEST @Value(FILE_EXISTS) = JA
    BOOL_OP = OR
    TEST_MODE = Automatic
    PASSED -> AttributeCreator_7
AttributeCreator_7
    ATTR_LIST = Title,@Value(value),Content,Trykk på linken for å laste ned data for kommune @PadLeft(@Value(kommuneid),4,0), @Value(navn) i koordinatsystemet EPSG:@Value(koordsys). <br />  <a href="@Value(DownloadUrl)">@Value(value)<\a>,Description,Oversikt over korallrev. Trykk på linken for nedlasting: @Value(value),ContentType,html,LastUpdate,$(LastUpdate),Id,@Value(DownloadUrl),Category{0}.Category,EPSG:@Value(koordsys),Category{0}.Domain,http://www.opengis.net/def/crs/,Category{0}.Label,EPSG/0/@Value(koordsys),Author,Per Arne Horneland,Copyright,Havforskningsinstituttet,LinkURI,@Value(DownloadUrl),Category{1}.Category,Kommune,Category{1}.Label,@Value(navn)
    -> Entry (writer GEORSS_1)

Bookmark: Feed
Creator_2
    GEOMTYPE = Geometry Object
    NUM = 1
    CREATED -> AttributeCreator
AttributeCreator
    ATTR_LIST = Title,$(Title),Description,$(Description),LinkURI,$(FMEServerRoot)/$(Repository_Name),Id,$(FMEServerRoot)/$(Repository_Name),LastUpdate,$(LastUpdate),LinkRelation,self,LinkType,application/atom+xml,Copyright,Havforskningsinstituttet,Description,$(Description),GeneratorURI,$(FMEServerRoot),GeneratorVersion,$(FMEVersion)
    -> Feed (writer GEORSS_1)
Feed (writer GEORSS_1)

Bookmark: Hele landet
Creator_3
    GEOMTYPE = Geometry Object
    NUM = 1
    CREATED -> AttributeCreator_5

Bookmark: Set Up Entry Content with Download Link
Note: Lager nedlastingsURL for hele landet
AttributeCreator_5
    ATTR_LIST = DownloadUrl,$(ROTKATALOG_WEB)Havforskningsinstituttet_Norge_25833_Korallrev_SOSI.zip,name,Havforskningsinstituttet,value,Havforskningsinstituttet SOSI Data hele Norge
    -> AttributeCreator_2
AttributeCreator_2
    ATTR_LIST = Title,@Value(value),Content,Trykk på linken for å laste ned landsdekkende data i koordinatsystemet EPSG:25833. <br />  <a href="@Value(DownloadUrl)">@Value(value)<\a>,Description,Oversikt over korallrev. Trykk på linken for nedlasting: @Value(value),ContentType,html,LastUpdate,$(LastUpdate),Id,@Value(DownloadUrl),Category{0}.Category,EPSG:25833,Category{0}.Domain,http://www.opengis.net/def/crs/,Category{0}.Label,EPSG/0/25833,Author,Per Arne Horneland,Copyright,Havforskningsinstituttet,LinkURI,@Value(DownloadUrl)
    -> Entry (writer GEORSS_1)
