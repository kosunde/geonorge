FME workspace Korallrev_postgis2gml.fmw
# Copyright: (c) xgrimor 2015
# Licence: <your licence>
Shutdown Python:
      # -*- coding: utf-8 -*-
      #-------------------------------------------------------------------------------
      # Name:        zipfiles.py
      # Purpose:     Pakker filer i output folderen
      #
      # Author:      xsunknu
      #
      # Created:     18.09.2015
      # Copyright:   (c) xsunknu 2015
      # Licence:     <your licence>
      #-------------------------------------------------------------------------------

      import sys, os, zipfile, fme

      def zip(gmlfile, zfile):
          from os.path import basename

          # Lager korresponderende zip-fil av gml-fil
          if os.path.isfile(zfile):
              os.remove(zfile)

          zf = zipfile.ZipFile(zfile, "w", zipfile.ZIP_DEFLATED)

          # Ønsker ikke full sti inn i ZIP-filen
          arcname = basename(gmlfile)

          # ZIP-formatet støtter ikke non-ascii tegn
          # Erstatter AØÅæøå med ascii-tegn
          arcname = arcname.replace('\xc6', 'E')
          arcname = arcname.replace('\xd8', 'O')
          arcname = arcname.replace('\xc5', 'A')
          arcname = arcname.replace('\xe6', 'e')
          arcname = arcname.replace('\xf8', 'o')
          arcname = arcname.replace('\xe5', 'a')

          zf.write(gmlfile, arcname)
          zf.close()
          os.remove(gmlfile)

          return

      def main():

          # Kjøres ikke på FME Server, da FME Server selv sørger for pakkingen
          if not 'FME_SERVER_DEST_DIR' in fme.macroValues:
              if 'FANOUT_FOLDER' in fme.macroValues:
                  logger = open(fme.logFileName, 'a')
                  path = fme.macroValues['FANOUT_FOLDER']
                  for dirpath, dnames, fnames in os.walk(path):
                      for f in fnames:
                          if f.endswith(".gml"):
                              # Scanner gjennom alle gml-filer
                              gmlfile = os.path.join(path, f)
                              zfile = os.path.splitext(gmlfile)[0] + '.zip'
                              if os.path.isfile(zfile):

                                  # Korresponderende ZIP-fil finnes, sjekker timestamps
                                  gmltstamp = os.stat(gmlfile).st_mtime
                                  ziptstamp = os.stat(zfile).st_mtime

                                  if gmltstamp > ziptstamp:
                                      # gml-fil er nyere enn ZIP-fila, ZIP-fila oppdateres
                                      # gml-fila slettes
                                      try:
                                          zip(gmlfile, zfile)
                                      except:
      #                                    print 'Kunne ikke pakke: ' + gmlfile
                                          logger.write('Kunne ikke pakke: ' + gmlfile + '\n')
                                  else:
                                      # gml-fila er eldre enn ZIP-fila
                                      # gml-fila slettes
                                      try:
                                          os.remove(gmlfile)
                                      except:
      #                                    print 'Kunne ikke slette: ' + gmlfile
                                          logger.write('Kunne ikke slette: ' + gmlfile + '\n')
                              else:
                                  # ZIP-fila eksisterer ikke og lages
                                  # gml-fila slettes
                                  try:
                                      zip(gmlfile, zfile)
                                  except:
      #                                print 'Kunne ikke pakke: ' + gmlfile
                                      logger.write('Kunne ikke pakke: ' + gmlfile + '\n')

                  logger.close()

      if __name__ == '__main__':
          main()

Parameters:
- KNR =   # Kommune(r)
- FNR =   # Fylke(r)
- CLIPPERCOORDS =   # Clipper coordinates
- CLIPPER_EPSG_CODE =   # Clipper EPSG code
- CLIPPER_FILE =   # "" Clipper file (any format)
- OUTPUT_EPSG_CODE = 25833   # Output EPSG code
- FANOUT = Norge   # Fanout områder
- CONFIG_FILE:   # Python Script
      #-------------------------------------------------------------------------------
      # Name:        GetConfigFile
      # Purpose:
      #
      # Author:      xsunknu
      #
      # Created:     21.08.2015
      # Copyright:   (c) xsunknu 2015
      # Licence:     <your licence>
      #-------------------------------------------------------------------------------
      
      import os, fme
      
      fmwdir = fme.macroValues['FME_MF_DIR']
      fmwfile = fme.macroValues['FME_MF_NAME']
      
      fmwfile = os.path.join(fmwdir, fmwfile)
      configfile = os.path.splitext(fmwfile)[0] + '_config.xml'
      
      return configfile
- PG_PWD:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgpwd').text
      
      return value
- PG_USER:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pguser').text
      
      return value
- PG_HOST:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pghost').text
      
      return value
- PG_DB:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgdb').text
      
      return value
- SOSI_FILE = korallrev   # SOSI file 
- MAPPING_FILE:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme, os
      from xml.etree import ElementTree as ET
      
      #Read XML config file
      configtree = ET.parse(fme.macroValues['CONFIG_FILE'])
      configdoc = configtree.getroot()
      
      value = os.path.join(fme.macroValues['FME_MF_DIR'], configdoc.find('mappingfile').text)
      
      return value
- SOSIDEF_FILE:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme, os
      from xml.etree import ElementTree as ET
      
      #Read XML config file
      configtree = ET.parse(fme.macroValues['CONFIG_FILE'])
      configdoc = configtree.getroot()
      
      value = os.path.join(fme.macroValues['FME_MF_DIR'], configdoc.find('sosideffile').text)
      
      return value
- FIXEDCLIPPERCOORDS:   # Python Script
      #-------------------------------------------------------------------------------
      # Name:        FixClipperCoords
      # Purpose:
      #
      # Author:      xsunknu
      #
      # Created:     21.08.2015
      # Copyright:   (c) xsunknu 2015
      # Licence:     <your licence>
      #-------------------------------------------------------------------------------
      
      import fme
      clippercoords = fme.macroValues['CLIPPERCOORDS']
      
      if clippercoords == '':
          clippercoords = '1 1'
      
      return clippercoords
- DESTCOORDSYS:   # Python Script
      #-------------------------------------------------------------------------------
      # Name:        SetCoordinateSystem
      # Purpose:
      #
      # Author:      xsunknu
      #
      # Created:     21.08.2015
      # Copyright:   (c) xsunknu 2015
      # Licence:     <your licence>
      #-------------------------------------------------------------------------------
      
      import os, fme
      
      EPSGvalue = fme.macroValues['OUTPUT_EPSG_CODE']
      EPSGcode  = 'EPSG:' + EPSGvalue
      
      return EPSGcode
- CLIPPERCOORDSYS:   # Python Script
      #-------------------------------------------------------------------------------
      # Name:        SetCoordinateSystem
      # Purpose:
      #
      # Author:      xsunknu
      #
      # Created:     21.08.2015
      # Copyright:   (c) xsunknu 2015
      # Licence:     <your licence>
      #-------------------------------------------------------------------------------
      
      import os, fme
      
      EPSGvalue = fme.macroValues['CLIPPER_EPSG_CODE']
      EPSGcode  = 'EPSG:' + EPSGvalue
      
      return EPSGcode
- LOG_FILE:   # Python Script
      #-------------------------------------------------------------------------------
      # Name:        GetConfigFile
      # Purpose:
      #
      # Author:      xsunknu
      #
      # Created:     21.08.2015
      # Copyright:   (c) xsunknu 2015
      # Licence:     <your licence>
      #-------------------------------------------------------------------------------
      
      import os, uuid, fme
      
      fmwdir = fme.macroValues['FME_MF_DIR']
      fmwfile = fme.macroValues['FME_MF_NAME']
      
      logdir = os.path.join(fmwdir, 'log')
      if not os.path.isdir(logdir):
          os.mkdir(logdir)
      
      logfile = os.path.splitext(fmwfile)[0] + '_' + str(uuid.uuid1()).replace('-','') + '.log'
      logfile = os.path.join(logdir, logfile)
      
      return logfile
- FANOUT_FOLDER:   # Python Script
      #-------------------------------------------------------------------------------
      # Name:        GetConfigFile
      # Purpose:
      #
      # Author:      xsunknu
      #
      # Created:     21.08.2015
      # Copyright:   (c) xsunknu 2015
      # Licence:     <your licence>
      #-------------------------------------------------------------------------------
      
      import os, fme
      from xml.etree import ElementTree as ET
      
      if 'FME_SERVER_DEST_DIR' in fme.macroValues:
          value = fme.macroValues['FME_SERVER_DEST_DIR']
      else:
          #Read XML config file
          configtree = ET.parse(fme.macroValues['CONFIG_FILE'])
          configdoc = configtree.getroot()
          value = configdoc.find('destdir').text
      
      return value

Readers:
- POSTGIS_1: POSTGIS from $(PG_DB)
- POSTGIS_2: POSTGIS from $(PG_DB)

Writers:
- GML_1: GML to $(FME_MF_DIR)Korallrev.gml

CreateClipper
    CLIPPERCOORDS = $(FIXEDCLIPPERCOORDS)
    DESTCOORDSYS = $(DESTCOORDSYS)
    CLIPPERCOORDSYS = $(CLIPPERCOORDSYS)
    reprojectBboxESRI_REPROJECTED_2 -> Clipper [input 1]
korallrev.v_korallrev (reader POSTGIS_2)
    attributes: objid int4, objtype varchar(32), obs_metode varchar(80), obs_sted varchar(80), obs_start timestamp, obs_slutt timestamp, bmnatyp varchar(80), bm_kildenavn varchar(80), bm_kildetittel varchar(80), bmkildtyp varchar(80), bm_kildear int4, dybde_min int4, dybde_max int4, lokalid uuid, navnerom varchar(80), versjonid varchar(80), verifiseringsdato timestamp, malemetode varchar(80), noyaktighet int4, synbarhet varchar(80), h_malemetode varchar(80), h_noyaktighet int4, max_avvik int4, medium varchar(80), opphav varchar(80), noyaktighetsklasse varchar(80), produkt varchar(80), versjon varchar(80), k_kommuneid int4, k_navn varchar(80),
      f_fylkeid int4, f_navn varchar(80)
    -> ClipperAttributeCreator
ClipperAttributeCreator: AttributeCreator
    ATTR_LIST = _clippercoords,$(CLIPPERCOORDS),_clipper_file,$(CLIPPER_FILE),_fnr,$(FNR),_knr,$(KNR)
    -> ClipperTester
ClipperTester: TestFilter
    TEST_LIST:
      BOOL_OP,AND,COMPOSITE_TEST,<Unused>,TEST_CLAUSE,"TEST _clipper_file ATTRIBUTE_IS_EMPTY """"
      TEST _clippercoords ATTRIBUTE_IS_EMPTY """"
      TEST _fnr ATTRIBUTE_IS_EMPTY """"
      TEST _knr ATTRIBUTE_IS_EMPTY """"",Landsdekkende,BOOL_OP,AND,COMPOSITE_TEST,<Unused>,TEST_CLAUSE,"TEST _clipper_file ATTRIBUTE_IS_EMPTY """"
      TEST _clippercoords ATTRIBUTE_IS_EMPTY """"
      TEST _fnr NOT_ATTRIBUTE_IS_EMPTY """"
      TEST _knr ATTRIBUTE_IS_EMPTY """"",Fylkesvis,BOOL_OP,AND,COMPOSITE_TEST,<Unused>,TEST_CLAUSE,"TEST _clipper_file ATTRIBUTE_IS_EMPTY """"
      TEST _clippercoords ATTRIBUTE_IS_EMPTY """"
      TEST _fnr ATTRIBUTE_IS_EMPTY """"
      TEST _knr NOT_ATTRIBUTE_IS_EMPTY """"",Kommunevis
    DEFAULT_VALUE = <UNFILTERED>
    Landsdekkende -> Destination_Reprojector
    Fylkesvis -> Clipper [input 2]
    Kommunevis -> Clipper [input 2]
Note: Clipper klipper datakilden mot det, eller de, valgte klippeobjektene: / - Kommuner og/eller fylker / - Polygon(er) spesifisert i en klippefil / - Et fritt valgt polygon basert på inntastede koordinater
Clipper
    CLIPPED_ATTR = _clipped
    ATTR_CONFLICT_RES = Use Clippee
    ATTR_ACCUM_MODE = Merge Clipper
    CREATE_AGGREGATES = Yes
    CLIP_TYPE = Multiple Clippers
    BOUNDARY_CASES = Treat as Inside
    PRESERVE_CLIPPEE_EXTENTS = No
    INSIDE -> Destination_Reprojector
    <REJECTED> -> Clipper_Rejected_Logger
Note: Reprojiserer data til ut-koordinatsystem.
Destination_Reprojector: Reprojector
    SOURCE = Read from feature
    DEST = $(DESTCOORDSYS)
    RASTER_CELL_SIZE = Preserve Cells
    INTERPOLATION_TYPE_NAME = Nearest Neighbor
    REPROJECTED -> GMLfile_AttributeCreator
Note: Her genererer vi filnavnet til GML-filen basert på hvilken FANOUT vi har spesifisert.
GMLfile_AttributeCreator: AttributeCreator
    ATTR_LIST = gmlfile,"FME_CONDITIONAL:DEFAULT_VALUE'Havforskningsinstituttet_$(OUTPUT_EPSG_CODE)_$(SOSI_FILE)_GML'BOOL_OP;OR;COMPOSITE_TEST;<Unused>;TEST $(FANOUT) LIKE Kommuner'Havforskningsinstituttet_@PadLeft(@Value(k_kommuneid),4,0)_@Value(k_navn)_$(OUTPUT_EPSG_CODE)_$(SOSI_FILE)_GML'BOOL_OP;OR;COMPOSITE_TEST;<Unused>;TEST $(FANOUT) LIKE Fylker'Havforskningsinstituttet_@PadLeft(@Value(f_fylkeid),2,0)_@Value(f_navn)_$(OUTPUT_EPSG_CODE)_$(SOSI_FILE)_GML'BOOL_OP;OR;COMPOSITE_TEST;<Unused>;TEST $(FANOUT) LIKE Norge'Havforskningsinstituttet_Norge_$(OUTPUT_EPSG_CODE)_$(SOSI_FILE)_GML'FME_NUM_CONDITIONS4___"
    -> AttributeRenamer
AttributeRenamer
    ATTR_LIST = lokalid,identifikasjon.Identifikasjon.lokalId,,navnerom,identifikasjon.Identifikasjon.navnerom,,versjonid,identifikasjon.Identifikasjon.versjonId,,obs_metode,observasjonsMetode,,obs_start,observasjonsStart,,obs_slutt,observasjonsSlutt,,bm_kildear,bmKilde.BmKilde.kildeÅr,,bm_kildenavn,bmKilde.BmKilde.kildeNavn,,bm_kildetittel,bmKilde.BmKilde.kildeTittel,,bmkildtyp,bmKilde.BmKilde.kildetype,,bmnatyp,naturtype,,dybde_max,maksimumsdybde,,dybde_min,minimumsdybde,,malemetode,kvalitet.Posisjonskvalitet.målemetode,,h_malemetode,kvalitet.Posisjonskvalitet.målemetodeHøyde,,max_avvik,kvalitet.Posisjonskvalitet.maksimaltAvvik,,noyaktighet,kvalitet.Posisjonskvalitet.nøyaktighet,,noyaktighetsklasse,nøyaktighetsklasse,,h_noyaktighet,kvalitet.Posisjonskvalitet.nøyaktighetHøyde,,synbarhet,kvalitet.Posisjonskvalitet.synbarhet,,produkt,registreringsversjon.Registreringsversjon.produkt,,versjon,registreringsversjon.Registreringsversjon.versjon,,obs_sted,observasjonsSted,
    -> GeometryPropertySetter
GeometryPropertySetter
    OVERWRITE_CHOICE = Yes
    SETTYPE_PARAM = Geometry Name
    GEOM_NAME_FIELD = posisjon
    SET -> DateFormatter
DateFormatter
    FMT = ISO DateTime (%Y-%m-%dT%H:%M:%S)
    DATE_ATTR = observasjonsSlutt,observasjonsStart,verifiseringsdato
    SRCFMT = Unknown - Automatic Detection
    INVALID_DATE_VALUE = _FME_NO_OP_
    -> NullAttributeMapper
NullAttributeMapper
    ATTRCHOICE = Selected Attributes
    ATTRLIST = identifikasjon.Identifikasjon.versjonId kvalitet.Posisjonskvalitet.maksimaltAvvik kvalitet.Posisjonskvalitet.målemetodeHøyde kvalitet.Posisjonskvalitet.nøyaktighet kvalitet.Posisjonskvalitet.nøyaktighetHøyde kvalitet.Posisjonskvalitet.synbarhet
    SOURCE_ATTR_VAL = Empty Null
    NULL_TREATMENT = Missing
    -> Korallrev (writer GML_1)
Korallrev (writer GML_1)
    attributes: identifikasjon.Identifikasjon.lokalId xml_buffer, identifikasjon.Identifikasjon.navnerom xml_buffer, identifikasjon.Identifikasjon.versjonId xml_buffer, verifiseringsdato xml_datetime, kvalitet.Posisjonskvalitet.målemetode xml_buffer, kvalitet.Posisjonskvalitet.nøyaktighet xml_int64, kvalitet.Posisjonskvalitet.synbarhet xml_buffer, kvalitet.Posisjonskvalitet.målemetodeHøyde xml_buffer, kvalitet.Posisjonskvalitet.nøyaktighetHøyde xml_int64, kvalitet.Posisjonskvalitet.maksimaltAvvik xml_int64, medium xml_buffer, opphav xml_buffer, nøyaktighetsklasse xml_buffer, registreringsversjon.Registreringsversjon.produkt xml_buffer, registreringsversjon.Registreringsversjon.versjon xml_buffer, minimumsdybde xml_int64, maksimumsdybde xml_int64, posisjon xml_geometry, naturtype xml_buffer, naturtype.codeSpace xml_buffer, bmKilde.BmKilde.kildeNavn xml_buffer, bmKilde.BmKilde.kildeTittel xml_buffer, bmKilde.BmKilde.kildetype xml_buffer, bmKilde.BmKilde.kildetype.codeSpace xml_buffer, bmKilde.BmKilde.kildeÅr xml_int64, observasjonsMetode xml_buffer, observasjonsStart xml_datetime, observasjonsSlutt xml_datetime, observasjonsSted xml_buffer
Clipper_Rejected_Logger: Logger
    MESSAGE = Dette koralrevet er utenfor kjent posisjon:
    MAXCOORDS = 20
    MAXFEATS = 20

Bookmark: Fylke og/eller kommune clippers
admingrense.fylkeflate (reader POSTGIS_1)
    attributes: fylkeid int4, navn varchar(80)
    -> Fylkeid_Tester
    -> HeleNorge_AttributeCreator
HeleNorge_AttributeCreator: AttributeCreator
    ATTR_LIST = _clippercoords,$(CLIPPERCOORDS),_clipper_file,$(CLIPPER_FILE),_fnr,$(FNR),_knr,$(KNR)
    -> HeleNorge_Tester
HeleNorge_Tester: Tester
    BOOL_OP = AND
    TEST_DESCRIPTION = ""
    TEST_MODE = Automatic
    TEST_CLAUSE:
      TEST _clipper_file ATTRIBUTE_IS_EMPTY ""
      TEST _clippercoords ATTRIBUTE_IS_EMPTY ""
      TEST _fnr ATTRIBUTE_IS_EMPTY ""
      TEST _knr ATTRIBUTE_IS_EMPTY ""
    PASSED -> AdminFlateReprojector
Fylkeid_Tester: Tester
    BOOL_OP = OR
    TEST_DESCRIPTION = ""
    TEST_MODE = Automatic
    TEST_CLAUSE = TEST @Value(fylkeid) IN $(FNR)
    PASSED -> AdminFlateReprojector
admingrense.kommuneflate (reader POSTGIS_1)
    attributes: kommuneid int4, navn varchar(80)
    -> kommuneid_Tester
kommuneid_Tester: Tester
    BOOL_OP = OR
    TEST_DESCRIPTION = ""
    TEST_MODE = Automatic
    TEST_CLAUSE = TEST @Value(kommuneid) IN $(KNR)
    PASSED -> AdminFlateReprojector
AdminFlateReprojector: Reprojector
    SOURCE = Read from feature
    DEST = EPSG:4258
    RASTER_CELL_SIZE = Preserve Cells
    INTERPOLATION_TYPE_NAME = Nearest Neighbor
    REPROJECTED -> Clipper [input 1]

Bookmark: Clipper file (any format)
Creator
    GEOMTYPE = Geometry Object
    NUM = 1
    CREATED -> ClipperFile_FeatureReader
ClipperFile_FeatureReader: FeatureReader
    ATTR_ACCUM_MODE = Only Use Result
    GENERIC_REAL_FORMAT = GUESS_FROM_EXTENSION
    ATTRIBUTES = NewFeatureType,
    INTERACT = <No Spatial Filter>
    COMBINE_GEOM = Use Result
    OUTPUT_FEATURES_DISPLAY = Based on Connections
    FORMAT = GENERIC
    FEATURETYPES_RADIO = FEATURETYPES
    DATASET = $(CLIPPER_FILE)
    <OTHER> -> ClipperFileReprojector
ClipperFileReprojector: Reprojector
    SOURCE = Read from feature
    DEST = EPSG:4258
    RASTER_CELL_SIZE = Preserve Cells
    INTERPOLATION_TYPE_NAME = Nearest Neighbor
    REPROJECTED -> Clipper [input 1]

FME custom transformer CreateClipper

Parameters:
- CLIPPERCOORDS = 253577 6650999 253577 6651246 253763 6651246 253763 6650999 253577 6650999   # Clipper Coordinate List
- CLIPPERCOORDSYS = EPSG:25833   # Clipper Coordinate System
- DESTCOORDSYS = "ESRIWKT|ETRS_1989_UTM_Zone_35N|PROJCS["ETRS_1989_UTM_Zone_35N",GEOGCS["GCS_ETRS_1989",DATUM["D_ETRS_1989",SPHEROID["GRS_1980",6378137.0,298.257222101]],PRIMEM["Greenwich",0.0],UNIT["Degree",0.0174532925199433]],PROJECTION["Transverse_Mercator"],PARAMETER["False_Easting",500000.0],PARAMETER["False_Northing",0.0],PARAMETER["Central_Meridian",27.0],PARAMETER["Scale_Factor",0.9996],PARAMETER["Latitude_Of_Origin",0.0],UNIT["Meter",1.0]]"   # Destination Coordinate System

Note: Creating geometry from / the Clipper coords
Creator
    GEOMTYPE = 2D Coordinate List
    COORDS = $(CLIPPERCOORDS)
    COORDSYS = $(CLIPPERCOORDSYS)
    NUM = 1
    CREATED -> BoundingBoxAccumulator
Note: Calculating the bounding / box (envelope) from the geometry
BoundingBoxAccumulator
    TOPFER_INDEX = No
    BOUNDING_BOX -> SpatialFilter [input 1]
    ORIGINAL -> SpatialFilter [input 2]
Note: If the geometry is equal to its / own bounding box - it is a rectangle!
SpatialFilter
    USE_BOUNDING_BOX = No
    PREDICATES = EQUALS
    CURVE_BOUNDARY_RULE_PARAM = Default Rule
    MERGE_ATTRS = No
    BASE_TYPE = Single Base
    PREDATTR = _predicate
    PASS_CRITERIA = Pass Against One Base
    PASSED -> Reprojector
    FAILED -> Reprojector_2
Note: If rectangle, reproject the / geometry to the destination / coordinate system
Reprojector
    SOURCE = Read from feature
    DEST = $(DESTCOORDSYS)
    STROKE_ARCS = Yes
    RASTER_CELL_SIZE = Preserve Cells
    INTERPOLATION_TYPE_NAME = Nearest Neighbor
    REPROJECTED -> BoundingBoxAccumulator_2
Note: Then calculate the bounding / box from the projected geoemtry
BoundingBoxAccumulator_2
    TOPFER_INDEX = No
    BOUNDING_BOX -> Reprojector_3
Note: Reproject the geometry back to / the DB coordsys (LL/EUREF89)
Reprojector_3
    SOURCE = Read from feature
    DEST = EPSG:4258
    STROKE_ARCS = Yes
    RASTER_CELL_SIZE = Preserve Cells
    INTERPOLATION_TYPE_NAME = Nearest Neighbor
    REPROJECTED -> reprojectBboxESRI_REPROJECTED_2 (output)
Note: Reproject clipper to / the DB coordsys (LL/EUREF89)
Reprojector_2
    SOURCE = Read from feature
    DEST = EPSG:4258
    STROKE_ARCS = Yes
    RASTER_CELL_SIZE = Preserve Cells
    INTERPOLATION_TYPE_NAME = Nearest Neighbor
    REPROJECTED -> reprojectBboxESRI_REPROJECTED_2 (output)
reprojectBboxESRI_REPROJECTED_2 (output)
