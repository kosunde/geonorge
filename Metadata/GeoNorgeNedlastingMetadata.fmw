FME workspace GeoNorgeNedlastingMetadata.fmw

Parameters:
- DestDataset_TEXTLINE = $(FME_MF_DIR)return.xml   # Destination Text File
- CONFIG_FILE:   # Python Script
      #-------------------------------------------------------------------------------
      # Name:        GetConfigFile
      # Purpose:
      #
      # Author:      xsunknu
      #
      # Created:     21.08.2015
      # Copyright:   (c) xsunknu 2015
      # Licence:     <your licence>
      #-------------------------------------------------------------------------------
      
      import os, fme
      
      fmwdir = fme.macroValues['FME_MF_DIR']
      fmwfile = fme.macroValues['FME_MF_NAME']
      
      fmwfile = os.path.join(fmwdir, fmwfile)
      configfile = os.path.splitext(fmwfile)[0] + '_config.xml'
      
      return configfile

Writers:
- TEXTLINE_1: TEXTLINE to $(DestDataset_TEXTLINE)

Creator
    GEOMTYPE = Geometry Object
    NUM = 1
    CREATED -> ParameterFetcher_2
ParameterFetcher_2
    ATTR_LIST = _FME_SERVER_REQUEST_URI {$(FME_SERVER_REQUEST_URI)}
    -> NullAttributeMapper_2
NullAttributeMapper_2
    NEW_VALUE = " "
    ATTRLIST = _FME_SERVER_REQUEST_URI
    SOURCE_ATTR_VAL = Empty "Missing (Selected Attributes Only)" Null
    NULL_TREATMENT = New Value
    ATTRCHOICE = Selected Attributes
    -> TextDecoder
TextDecoder
    ENCODING_TYPE = URL (Percent Encoding)
    DEST_ATTR = _FME_SERVER_REQUEST_URI
    STRING_TO_DECODE = @Value(_FME_SERVER_REQUEST_URI)
    -> FMEServerURLSplitter
Note: Split calling URI to get parameters
FMEServerURLSplitter
    _FME_SERVER_REQUEST_URI = @Value(_FME_SERVER_REQUEST_URI)
    -> AttributeExposer_4
Note: Expose parameter attributes
AttributeExposer_4
    ATTR_LIST = REQUEST,UUID
    -> AttributeFilter
AttributeFilter
    ATTR_VALUES = <EMPTY>,<MISSING>,<NULL>,<UNFILTERED>,capabilities,projection,area,format
    ATTR_NAME = REQUEST
    capabilities -> AttributeCreator
    projection -> XMLTemplater_2
    area -> XMLTemplater_2
    format -> XMLTemplater_2
    <EMPTY> -> XMLTemplater_2
    <MISSING> -> XMLTemplater_2
    <NULL> -> XMLTemplater_2
    <UNFILTERED> -> XMLTemplater_2
AttributeCreator
    ATTR_LIST = sql,metadataUuid = "@Value(UUID)"
    -> SQLExecutor
    -> FeatureReader
SQLExecutor [off]
    COMBINE_GEOM = Initiator Geometry Only
    POSTGRES_USER_NAME = geonortst
    POSTGRES_PASSWORD =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
    POSTGRES_HOST = nnridb504
    EXPOSED_ATTRIBUTE_LIST = supportsAreaSelection,supportsFormatSelection,supportsPolygonSelection,supportsProjectionSelection
    FORMAT = POSTGRES
    SQL_STATEMENT = SELECT * FROM metadata.Dataset where metadataUuid="@Value(UUID)"
    POSTGRES_QUERY_FEATURE_TYPES_FOR_MERGE_FILTERS = Yes
    POSTGRES_PORT = 5432
    DATASET = geonor01tst
    COMBINE_ATTRS = Keep Initiator Attributes if Conflict
    RESULT -> FeatureReader
    RESULT -> StringReplacer
FeatureReader
    ATTR_ACCUM_MODE = Merge Initiator and Result
    ATTR_CONFLICT_RES = Use Result
    FORMAT = POSTGRES
    DATASET = geonor01tst
    POSTGRES_QUERY_FEATURE_TYPES_FOR_MERGE_FILTERS = Yes
    FEATURETYPES_RADIO = FEATURETYPES
    POSTGRES_HOST = nnridb504
    POSTGRES_PASSWORD =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
    FEATURETYPES = metadata.Dataset
    POSTGRES_USER_NAME = geonortst
    COMBINE_GEOM = Use Result
    ATTRIBUTES = metadata.Dataset,"ID,Tittel,metadataUuid,supportsAreaSelection,supportsFormatSelection,supportsPolygonSelection,supportsProjectionSelection"
    OUTPUT_FEATURES_DISPLAY = Based on Connections
    POSTGRES_PORT = 5432
    POSTGRES_SCHEMALIST = metadata
    metadata.Dataset -> StringReplacer
StringReplacer
    REGEXP = no
    NO_MATCH = _FME_NO_OP_
    SRC_ATTRS = supportsAreaSelection,supportsFormatSelection,supportsPolygonSelection,supportsProjectionSelection
    REPLACE_TEXT = true
    CASE = no
    FIND_TEXT = t
    -> StringReplacer_2
StringReplacer_2
    REGEXP = no
    NO_MATCH = _FME_NO_OP_
    SRC_ATTRS = supportsAreaSelection,supportsFormatSelection,supportsPolygonSelection,supportsProjectionSelection
    REPLACE_TEXT = false
    CASE = no
    FIND_TEXT = f
    -> XMLTemplater
XMLTemplater
    VISIBLE_QUERY_VALIDATE = Yes
    ROOT_QUERY_EXPR:
      <Capabilities xmlns:xsd="http://www.w3.org/2001/XMLSchema" xmlns:xsi="http://www.w3.org/2001/XMLSchema-instance" xmlns="http://skjema.geonorge.no/SOSI/download/0.5">
          <supportsProjectionSelection>{fme:get-attribute("supportsProjectionSelection")}</supportsProjectionSelection>
          <supportsFormatSelection>{fme:get-attribute("supportsFormatSelection")}</supportsFormatSelection>
          <supportsPolygonSelection>{fme:get-attribute("supportsPolygonSelection")}</supportsPolygonSelection>
          <supportsAreaSelection>{fme:get-attribute("supportsAreaSelection")}</supportsAreaSelection>
          <_links xmlns="http://www.kxml.no/rest/1.0">
              <href>{fme:get-attribute("BASE_URL")}?request=projection&amp;UUID={fme:get-attribute("UUID")}</href>
              <rel>http://rel.geonorge.no/download/projection</rel>
          </_links>
          <_links xmlns="http://www.kxml.no/rest/1.0">
              <href>{fme:get-attribute("BASE_URL")}?request=format&amp;UUID={fme:get-attribute("UUID")}</href>
              <rel>http://rel.geonorge.no/download/format</rel>
          </_links>
          <_links xmlns="http://www.kxml.no/rest/1.0">
              <href>{fme:get-attribute("BASE_URL")}?request=area&amp;UUID={fme:get-attribute("UUID")}</href>
              <rel>http://rel.geonorge.no/download/area</rel>
          </_links>
      <!--    <_links xmlns="http://www.kxml.no/rest/1.0">
              <href>{fme:get-attribute("fme_server_base_url")}</href>
              <rel>http://rel.geonorge.no/download/order</rel>
          </_links> -->
      </Capabilities>
    OUTPUT_XML_HEADER = Yes
    RESULT_ATTRIBUTE = _result
    -> XMLFormatter
    -> XMLTemplater_Output
XMLTemplater_Output: Logger
    MAXFEATS = 20
    MESSAGE = Feature is:
    MAXCOORDS = 20
XMLFormatter
    REMOVE_EMPTY_ELEMENT = No
    REMOVE_ALL_COMMENT = No
    XML_ATTR_TEXT = _result
    NAMESPACE_CLEANUP = No
    LIST_NAME = _xml_error
    FORMATTING_CHOICE = Pretty-Print XML
    XML_INPUT_TYPE = Attribute Specifying XML Text
    INDENT_SIZE = 1
    COLLAPSE_EMPTY_ELEMENT = No
    SCHEMALOC_CLEANUP = No
    XML_OUTPUT_ATTR = _xml_output
    OUTPUT_ENCODING = utf-8
    WHITESPACE_HANDLING = Preserve all whitespace
    XML_OUTPUT_TYPE = Attribute
    REPLACE_TABS_WITH_SPACES = no
    PASSED -> text_line (writer TEXTLINE_1)
XMLTemplater_2
    VISIBLE_QUERY_VALIDATE = Yes
    ROOT_QUERY_EXPR:
      <ows:ExceptionReport xmlns:ows="http://www.opengis.net/ows/1.1" xmlns:xsi="http://www.w3.org/2001/XMLSchema-instance" xsi:schemaLocation="http://www.opengis.net/ows/1.1 http://schemas.opengis.net/ows/1.1.0/owsExceptionReport.xsd" version="2.0.0">
        <ows:Exception exceptionCode="InvalidParameterValue" locator="request">
          <ows:ExceptionText>No service for request type {fme:get-attribute("REQUEST")} is configured / active.</ows:ExceptionText>
        </ows:Exception>
      </ows:ExceptionReport>
    OUTPUT_XML_HEADER = Yes
    RESULT_ATTRIBUTE = _result
    -> XMLFormatter_2
XMLFormatter_2
    REMOVE_EMPTY_ELEMENT = No
    REMOVE_ALL_COMMENT = No
    XML_ATTR_TEXT = _result
    NAMESPACE_CLEANUP = No
    LIST_NAME = _xml_error
    FORMATTING_CHOICE = Pretty-Print XML
    XML_INPUT_TYPE = Attribute Specifying XML Text
    INDENT_SIZE = 1
    COLLAPSE_EMPTY_ELEMENT = No
    SCHEMALOC_CLEANUP = No
    XML_OUTPUT_ATTR = _xml_output
    OUTPUT_ENCODING = utf-8
    WHITESPACE_HANDLING = Preserve all whitespace
    XML_OUTPUT_TYPE = Attribute
    REPLACE_TABS_WITH_SPACES = no
    PASSED -> text_line (writer TEXTLINE_1)
text_line (writer TEXTLINE_1)
    attributes: text_line_data buffer

FME custom transformer FMEServerURLSplitter
This transformer is useful for breaking up the full URI request that is sent to FME Server. The transformer actually takes any URL and breaks it up into pieces, so it could be applied elsewhere.
With FME 2014 Server the entire request URL is now held in the FME_SERVER_REQUEST_URI parameter so that it can be used within the workspace. This is useful in cases where extra parameters are tacked onto a URL or the URL path doesn't end with .fmw.
This capability makes it possible for FME Server to be used to satisfy new types of requests where the full request cannot be known until runtime.
Input:
Request URI: the full URI request made to FME Server, in string or attribute form
Output
base_url - This is the entire URL up to the starts of URL parameters. 
fme_server_base_url - The FME Server base url. Is the same as above if the base_url ends at .fmw. This is only present if the url has .fmw in it. 
fme_server_extra_url_path - the additional components of the path if it is from FME Server. This is present if the base_url is different from the fme_server_base_url.
fme_server_extra_url{} list - fme_server_extra_url_path broken up into a list for convenience
url_raw_parameters - These are all the url parameters as one string.
num_parms - The number of URL parameters after they have been parsed out. 
decoded parameters - The parameters themselves are also parsed out and turned into FME attributes. 
Example
Given the url 
http://dondemo/fmejobsubmitter/webdump/PublishParameterDump.fmw/another/value?DestDataset_TEXTLINE=output.txt&opt_showresult=false&opt_servicemode=sync&anotherparm=here
base_url has value `http://dondemo/fmejobsubmitter/webdump/PublishParameterDump.fmw/another/value'
fme_server_base_url has value `http://dondemo/fmejobsubmitter/webdump/PublishParameterDump.fmw/'
fme_server_extra_url_path' has value `another/value'
fme_server_extra_url{0}' has value 'another'
fme_server_extra_url{1}' has value 'value'
url_raw_parameters' has value 'DestDataset_TEXTLINE=output.txt&opt_showresult=false&opt_servicemode=sync&anotherparm=here'
num_parms' has value '4'
DestDataset_TEXTLINE has value 'output.txt'
anotherparm has value 'here'
opt_servicemode has value 'sync'
opt_showresult has value 'false'
Copyright (c) 2014 Safe Software Inc.
Permission is granted to anyone, free of charge, to use, modify and distribute the object code form of this transformer for any purpose, subject to the following restrictions:
1) The origin of this transformer and associated FME(R) software must not be misrepresented.
2) This transformer may only be used in conjunction with a validly licensed copy of FME software.
THIS SOFTWARE IS PROVIDED BY SAFE SOFTWARE INC. "AS IS" AND ANY EXPRESS OR IMPLIED WARRANTIES, INCLUDING, BUT NOT LIMITED TO, THE IMPLIED WARRANTIES OF MERCHANTABILITY, NONINFRINGEMENT AND FITNESS FOR A PARTICULAR PURPOSE ARE DISCLAIMED. IN NO EVENT SHALL SAFE SOFTWARE INC. BE LIABLE FOR ANY DIRECT, INDIRECT, INCIDENTAL, SPECIAL, EXEMPLARY, OR CONSEQUENTIAL DAMAGES (INCLUDING, BUT NOT LIMITED TO, PROCUREMENT OF SUBSTITUTE GOODS OR SERVICES; LOSS OF USE, DATA, OR PROFITS; OR BUSINESS INTERRUPTION) HOWEVER CAUSED AND ON ANY THEORY OF LIABILITY, WHETHER IN CONTRACT, STRICT LIABILITY, OR TORT (INCLUDING NEGLIGENCE OR OTHERWISE) ARISING IN ANY WAY OUT OF THE USE OF THIS SOFTWARE, EVEN IF ADVISED OF THE POSSIBILITY OF SUCH DAMAGE.

Parameters:
- _FME_SERVER_REQUEST_URI =   # Request URI

AttributeSplitter_Input (input)
    -> AttributeSplitter
Output (output)

Bookmark: First split url up into two peices ("base url" and "parm string")
AttributeSplitter
    DELIMITER = ?
    LIST_NAME = _list
    ATTR_NAME = _FME_SERVER_REQUEST_URI
    TRIM_OPTION = Both
    DROP_EMPTY_PARTS = No
    -> AttributeRenamer
AttributeRenamer
    ATTR_LIST = _list{0},base_url,"",_list{1},url_raw_parameters,""
    -> AttributeSplitter_2

Bookmark: Check if Parms and build list
Note: Now we split the parm string into a list.
AttributeSplitter_2
    DELIMITER = &
    LIST_NAME = _paramList
    ATTR_NAME = url_raw_parameters
    TRIM_OPTION = Both
    DROP_EMPTY_PARTS = No
    -> TestFilter
TestFilter
    DEFAULT_VALUE = NoParameters
    TEST_LIST = BOOL_OP,OR,COMPOSITE_TEST,<Unused>,TEST_CLAUSE,"TEST _paramList{0} NOT_ATTRIBUTE_IS_EMPTY """"",Parameters
    Parameters -> ListElementCounter
    NoParameters -> Remove_Empty_Argument
Note: No Parms so remove attribute
Remove_Empty_Argument: AttributeRemover
    REMOVE_ATTRS = url_raw_parameters
    -> StringSearcher

Bookmark: Loop Initialization
ListElementCounter
    CNT_ATTR = num_parms
    LIST_NAME = _paramList{}
    -> InitializeCounter
InitializeCounter: Counter
    CNT_ATTR = currentListPos
    DOMAIN = AttributeCount
    SCOPE = Global
    START = 0
    -> AttributeCreator_2

Bookmark: Iterate over all the parameters that were set
Note: AttributeCreator_2 [AttributeCreator] / curListEntry = @Value(_paramList{@Value(currentListPos)})
AttributeLooper (input)
    -> AttributeCreator_2

Bookmark: Extract a value and build attribute
AttributeCreator_2
    ATTR_LIST = curListEntry,@Value(_paramList{@Value(currentListPos)})
    -> AttributeSplitter_3
AttributeSplitter_3
    DELIMITER = =
    LIST_NAME = paramEntry
    ATTR_NAME = curListEntry
    TRIM_OPTION = Both
    DROP_EMPTY_PARTS = No
    -> AttributeCreator
AttributeCreator
    ATTR_LIST = @Value(paramEntry{0}),@Value(paramEntry{1})
    -> IncrementCounter
IncrementCounter: Counter
    CNT_ATTR = currentListPos
    DOMAIN = AttributeCount
    SCOPE = Global
    START = 0
    -> TestForMoreParms

Bookmark: Another Iteration?
TestForMoreParms: TestFilter
    DEFAULT_VALUE = All Done
    TEST_LIST = BOOL_OP,OR,COMPOSITE_TEST,<Unused>,TEST_CLAUSE,"TEST @Value(currentListPos) < @Value(num_parms)",More Params
    More Params -> AttributeLooper (output)
    All Done -> StringSearcher
AttributeLooper (output)

Bookmark: Extract URL Path after the *.fmw.
StringSearcher
    REGEXP = ^(.*[.]fmw/)(.*)$
    MATCHED_RESULT_ATTR = _matched_characters
    STRING_TO_SEARCH = @Value(base_url)
    CASE = no
    MATCHED_PARTS_ATTR = _matched_parts
    MATCHED -> AttributeRenamer_2
    NOT_MATCHED -> AttributeRemover
AttributeRenamer_2
    ATTR_LIST = _matched_parts{0},fme_server_base_url,"",_matched_parts{1},fme_server_extra_url_path,""
    -> AttributeSplitter_4
AttributeSplitter_4
    DELIMITER = /
    LIST_NAME = fme_server_extra_url
    ATTR_NAME = fme_server_extra_url_path
    TRIM_OPTION = Both
    DROP_EMPTY_PARTS = No
    -> AttributeRemover
AttributeRemover
    LIST_ATTRS = _paramList{} _matched_parts{} paramEntry{} _list{}
    REMOVE_ATTRS = currentListPos,curListEntry,_matched_characters
    -> BulkAttributeRenamer
BulkAttributeRenamer
    CASE_CHANGE_TYPE = UPPERCASE
    PATTERN_ACTION_DISP = Change Case
    ATTRCHOICE = All Attributes
    -> Output (output)
