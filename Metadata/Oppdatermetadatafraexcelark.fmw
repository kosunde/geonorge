FME workspace Oppdatermetadatafraexcelark.fmw

Parameters:
- SourceDataset_POSTGRES = geonortst@nnridb504:5432/geonor01tst   # Connection
- SourceDataset_XLSXR = \\prosjektrom.statkart.no@SSL\DavWWWRoot\p\nynasjonalgeoportal\Referansegruppe\Distribusjonsløyper\Status dekningsoversikt pr datasett.xlsx   # Source Microsoft Excel File(s)
- DestDataset_POSTGRES = geonortst@nnridb504:5432/geonor01tst   # Connection

Readers:
- POSTGRES_1: POSTGRES from $(SourceDataset_POSTGRES)
- XLSXR_1: XLSXR from $(SourceDataset_XLSXR)

Writers:
- POSTGRES_2: POSTGRES to $(DestDataset_POSTGRES)

dekningsoversikt.dekningsoversikt_metadata (reader POSTGRES_1)
    attributes: dekningsoversikt_attrname text, UUID text, Hovedkategori text, Underkategori text, Navn text
    -> FeatureMerger [input 1]
Ark1 (reader XLSXR_1)
    attributes: Etat char(31), Datasett char(56), attributt i dekningsoversikttabellen char(29), Kildetype char(35), Oppdateringstype char(13), Oppdateringsfrekvens char(50), Merknad char(79), UUID char(37), DOK char(3)
    -> FeatureMerger [input 2]
FeatureMerger
    IGNORE_NULLS = No
    MERGE_TYPE = Attributes Only
    JOIN_KEYS = @Value(dekningsoversikt_attrname) @Value(attributt i dekningsoversikttabellen) AUTO
    SUPPLIERS_FIRST = No
    ATTR_CONFLICT_RES = Use Supplier
    PROCESS_DUPS = No
    ATTR_ACCUM_MODE = Merge Supplier
    MERGED -> AttributeRenamer
AttributeRenamer
    ATTR_LIST = Datasett,Navn,
    -> AttributeValueMapper
AttributeValueMapper
    DEFAULT_VALUE = 0
    LUT = JA,1
    SRC = DOK
    DIRECTION = Forward (Source To Destination)
    VAL_ATTR = DOK
    -> dekningsoversikt.dekningsoversikt_metadata (writer POSTGRES_2)
dekningsoversikt.dekningsoversikt_metadata (writer POSTGRES_2)
    attributes: dekningsoversikt_attrname text, UUID text, Hovedkategori text, Underkategori text, Navn text, DOK bool
