FME workspace TurOgFriluftsruter_wfs2postgis.fmw

Parameters:
- SourceDataset_SOSI = H:\Skfelles\Import_temadata\friluftsruter\Friluftsruter_84.sos   # Source SOSI File
- DestDataset_POSTGRES = geonor01tst   # Database
- CONFIG_FILE:   # Python Script
      #-------------------------------------------------------------------------------
      # Name:        GetConfigFile
      # Purpose:
      #
      # Author:      xsunknu
      #
      # Created:     21.08.2015
      # Copyright:   (c) xsunknu 2015
      # Licence:     <your licence>
      #-------------------------------------------------------------------------------
      
      import os, fme
      
      fmwdir = fme.macroValues['FME_MF_DIR']
      fmwfile = fme.macroValues['FME_MF_NAME']
      
      fmwfile = os.path.join(fmwdir, fmwfile)
      configfile = os.path.splitext(fmwfile)[0] + '_config.xml'
      
      return configfile
- PG_DB:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgdb').text
      
      return value
- COORDSYS_OUT = EPSG:4258   # Python Script

Readers:
- SOSI_1: SOSI from $(SourceDataset_SOSI)

Writers:
- POSTGIS_1: POSTGIS to $(PG_DB) in $(COORDSYS_OUT)
- POSTGRES_1: POSTGRES to $(DestDataset_POSTGRES)

BulkAttributeRenamer
    PATTERN_ACTION_DISP = Change Case
    ATTRCHOICE = All Attributes
    CASE_CHANGE_TYPE = lowercase
    -> AttributeRenamer2SOSI
AttributeRenamer2SOSI
    ATTR_LIST = annenrutetype,arutetype,,kommunenummer,kommune,,målemetode,malemetode,,målemetodehøyde,malemetodehoyde,,nøyaktighet,noyaktighet,,nøyaktighethøyde,h_noyaktighet,,rutefølger,rutefolger,,skøytetrase,skoytetrase,,spesialskiløypetype,spes_skiloypetype,,vedlikeholdsansvarlig,vedlikeh,,rutenummer,rutenr,,spesialfotrutetype,sfotrutetype,,friluftslivsområdetilrettelegging,fritilrettelegging,,løypepreparering,preparering,,kobling_id,link,,sosi_id,sosi_objid,
    -> Reprojector
Reprojector
    RASTER_CELL_SIZE = Preserve Cells
    SOURCE = Read from feature
    INTERPOLATION_TYPE_NAME = Nearest Neighbor
    DEST = $(COORDSYS_OUT)
    REPROJECTED -> Skilting_AttributeValueMapper
Skilting_AttributeValueMapper: AttributeValueMapper
    VAL_ATTR = skilting
    DEFAULT_VALUE = false
    LUT = JA,true,NEI,false
    DIRECTION = Forward (Source To Destination)
    SRC = skilting
    -> OBJID_Counter
OBJID_Counter: Counter
    DOMAIN = counter
    CNT_ATTR = objid
    SCOPE = Global
    START = 1
    -> LOKALID_UUIDGenerator
LOKALID_UUIDGenerator: UUIDGenerator
    UUID_ATTR = lokalid
    -> LengthCalculator
LengthCalculator
    DIM = 2
    MULT = 1
    LEN_ATTR = lengde
    -> DataFangstDato_NullAttributeMapper
DataFangstDato_NullAttributeMapper: NullAttributeMapper
    ATTRCHOICE = Selected Attributes
    ATTRLIST = datafangstdato
    SOURCE_ATTR_VAL = Empty "Missing (Selected Attributes Only)" Null
    NEW_VALUE = 1899-12-31
    NULL_TREATMENT = New Value
    -> Vedlikeh_NullAttributeMapper
Vedlikeh_NullAttributeMapper: NullAttributeMapper
    ATTRCHOICE = Selected Attributes
    ATTRLIST = vedlikeh
    SOURCE_ATTR_VAL = Empty "Missing (Selected Attributes Only)" Null
    NEW_VALUE = Ukjent
    NULL_TREATMENT = New Value
    -> Malemetode_NullAttributeMapper
Malemetode_NullAttributeMapper: NullAttributeMapper
    ATTRCHOICE = Selected Attributes
    ATTRLIST = malemetode
    SOURCE_ATTR_VAL = Empty "Missing (Selected Attributes Only)" Null
    NEW_VALUE = 99
    NULL_TREATMENT = New Value
    -> Noyaktighet_NullAttributeMapper
Noyaktighet_NullAttributeMapper: NullAttributeMapper
    ATTRCHOICE = Selected Attributes
    ATTRLIST = noyaktighet
    SOURCE_ATTR_VAL = Empty "Missing (Selected Attributes Only)" Null
    NEW_VALUE = 9999
    NULL_TREATMENT = New Value
    -> Empty2Null_NullAttributeMapper
Empty2Null_NullAttributeMapper: NullAttributeMapper
    ATTRCHOICE = Selected Attributes
    ATTRLIST = belysning frilufteierforhold fritilrettelegging kommune malemetodehoyde opparbeiding preparering rutebetydning rutebredde rutefolger rutetype rutevanskelighetsgrad ryddebredde sesong sfotrutetype skilting skoytetrase spes_skiloypetype spesialsykkelrutetype synbarhet tilgjengelighetsgruppe trafikkbelastning underlagstype
    SOURCE_ATTR_VAL = Empty "Missing (Selected Attributes Only)"
    NULL_TREATMENT = Null
    -> Empty2space_NullAttributeMapper
Empty2space_NullAttributeMapper: NullAttributeMapper
    ATTRCHOICE = Selected Attributes
    ATTRLIST = rutemerking
    SOURCE_ATTR_VAL = Empty "Missing (Selected Attributes Only)" Null
    NEW_VALUE = UKJ
    NULL_TREATMENT = New Value
    -> Fritilrettelegging_NullAttributeMapper
Fritilrettelegging_NullAttributeMapper: NullAttributeMapper
    ATTRCHOICE = Selected Attributes
    ATTRLIST = fritilrettelegging
    SOURCE_ATTR_VAL = Null Empty "Missing (Selected Attributes Only)"
    NEW_VALUE = 40
    NULL_TREATMENT = New Value
    -> Kommune_StringPadder
Kommune_StringPadder: StringPadder
    PADCHAR = 0
    SRC_ATTRS = kommune
    SIDE = Left
    BLANK_ATTRIBUTE = No
    WIDTH = 4
    -> 2DForcer
2DForcer
    2D -> Opparbeiding_FeatureMerger [input 1]
OPPARBEIDING_SOSI_BulkAttributeRenamer: BulkAttributeRenamer
    PATTERN_ACTION_DISP = Change Case
    ATTRCHOICE = All Attributes
    CASE_CHANGE_TYPE = lowercase
    -> Opparbeiding_FeatureMerger [input 2]
Opparbeiding_FeatureMerger: FeatureMerger
    ATTR_ACCUM_MODE = Merge Supplier
    PROCESS_DUPS = No
    JOIN_KEYS = @Value(sosi_guid) @Value(sosi_parent_guid) STRING
    MERGE_TYPE = Attributes Only
    ATTR_CONFLICT_RES = Use Requestor
    IGNORE_NULLS = No
    SUPPLIERS_FIRST = No
    LIST_NAME = _list_opparbeiding
    MERGED -> Opparbeiding_ListConcatenator
    NOT_MERGED -> Opparbeiding_AttributeCreator
Opparbeiding_ListConcatenator: ListConcatenator
    VAL_ATTR = _concatenated_opparbeiding
    LIST_ATTR = _list_opparbeiding{}.opparbeiding
    SEP = ,
    DROP_EMPTY_PARTS = Yes
    -> Opparbeiding_StringConcatenator
Opparbeiding_StringConcatenator: StringConcatenator
    VAL_ATTR = _streng_opparbeiding
    PARM_LINE = @Value(opparbeiding),@Value(_concatenated_opparbeiding)
    ACTION = Create New Attribute
    -> Sfotrute_FeatureMerger [input 1]
Opparbeiding_AttributeCreator: AttributeCreator
    ATTR_LIST = _streng_opparbeiding,@Value(opparbeiding)
    -> Sfotrute_FeatureMerger [input 1]
SFOTRUTE_SOSI_BulkAttributeRenamer: BulkAttributeRenamer
    PATTERN_ACTION_DISP = Change Case
    ATTRCHOICE = All Attributes
    CASE_CHANGE_TYPE = lowercase
    -> Sfotrute_FeatureMerger [input 2]
Sfotrute_FeatureMerger: FeatureMerger
    ATTR_ACCUM_MODE = Merge Supplier
    PROCESS_DUPS = No
    JOIN_KEYS = @Value(sosi_guid) @Value(sosi_parent_guid) STRING
    MERGE_TYPE = Attributes Only
    ATTR_CONFLICT_RES = Use Requestor
    IGNORE_NULLS = No
    SUPPLIERS_FIRST = No
    LIST_NAME = _list_sfotrutetype
    MERGED -> Sfotrute_ListConcatenator
    NOT_MERGED -> Sfotrute_AttributeCreator
Sfotrute_ListConcatenator: ListConcatenator
    VAL_ATTR = _concatenated_sfotrutetype
    LIST_ATTR = _list_sfotrutetype{}.sfotrutetype
    SEP = ,
    DROP_EMPTY_PARTS = Yes
    -> Sfotrutetype_StringConcatenator
Sfotrutetype_StringConcatenator: StringConcatenator
    VAL_ATTR = _streng_sfotrutetype
    PARM_LINE = @Value(sfotrutetype),@Value(_concatenated_sfotrutetype)
    ACTION = Create New Attribute
    -> Tilgjengelighetsgruppe_FeatureMerger [input 1]
Sfotrute_AttributeCreator: AttributeCreator
    ATTR_LIST = _streng_sfotrutetype,@Value(sfotrutetype)
    -> Tilgjengelighetsgruppe_FeatureMerger [input 1]
TILGJENELIGHETSGRUPPE_BulkAttributeRenamer: BulkAttributeRenamer
    PATTERN_ACTION_DISP = Change Case
    ATTRCHOICE = All Attributes
    CASE_CHANGE_TYPE = lowercase
    -> Tilgjengelighetsgruppe_FeatureMerger [input 2]
Tilgjengelighetsgruppe_FeatureMerger: FeatureMerger
    ATTR_ACCUM_MODE = Merge Supplier
    PROCESS_DUPS = No
    JOIN_KEYS = @Value(sosi_guid) @Value(sosi_parent_guid) STRING
    MERGE_TYPE = Attributes Only
    ATTR_CONFLICT_RES = Use Requestor
    IGNORE_NULLS = No
    SUPPLIERS_FIRST = No
    LIST_NAME = _list_tilgjengelighetsgruppe
    MERGED -> Tilgjengelighetsgruppe_ListConcatenator
    NOT_MERGED -> Tilgjengelighetsgruppe_AttributeCreator
Tilgjengelighetsgruppe_ListConcatenator: ListConcatenator
    VAL_ATTR = _concatenated_tilgjengelighetsgruppe
    LIST_ATTR = _list_tilgjengelighetsgruppe{}.tilgjengelighetsgruppe
    SEP = ,
    DROP_EMPTY_PARTS = Yes
    -> Tilgjengelighetsgruppe_StringConcatenator
Tilgjengelighetsgruppe_StringConcatenator: StringConcatenator
    VAL_ATTR = _streng_tilgjengelighetsgruppe
    PARM_LINE = @Value(tilgjengelighetsgruppe),@Value(_concatenated_tilgjengelighetsgruppe)
    ACTION = Create New Attribute
    -> Mergers_AttributeRemover
Tilgjengelighetsgruppe_AttributeCreator: AttributeCreator
    ATTR_LIST = _streng_tilgjengelighetsgruppe,@Value(tilgjengelighetsgruppe)
    -> Mergers_AttributeRemover
Mergers_AttributeRemover: AttributeRemover
    LIST_ATTRS = _list_opparbeiding{} _list_sfotrutetype{} _list_tilgjengelighetsgruppe{}
    REMOVE_ATTRS = _concatenated_opparbeiding,_concatenated_sfotrutetype,_concatenated_tilgjengelighetsgruppe,opparbeiding,sfotrutetype,sosi_parent_guid,tilgjengelighetsgruppe
    -> FeatureTypeFilter
FeatureTypeFilter
    ATTRIBUTES = <BLANK>,<UNFILTERED>,AnnenRute,Fotrute,FriluftslivTilrettelegging,Skiloype,Sykkelrute
    FriluftslivTilrettelegging -> turogfriluftsruter.friluftslivtilrettelegging (writer POSTGIS_1)
    AnnenRute -> ar_Opparbeiding_Tester
    Sykkelrute -> turogfriluftsruter.sykkelrute (writer POSTGIS_1)
    Skiloype -> turogfriluftsruter.skiloype (writer POSTGIS_1)
    Fotrute -> turogfriluftsruter.fotrute (writer POSTGIS_1)
    AnnenRute -> turogfriluftsruter.annenrute (writer POSTGIS_1)
    AnnenRute -> ar_tilretteleggingsgruppe_Tester
    Fotrute -> fr_Opparbeiding_Tester
    Fotrute -> fr_Sfotrutetype_Tester
    Fotrute -> fr_Tilgjengelighetsgruppe_Tester
    Skiloype -> sl_Opparbeiding_Tester
    Skiloype -> sl_Tilgjengelighetsgruppe_Tester
ar_Opparbeiding_Tester: Tester
    TEST_CLAUSE = TEST _streng_opparbeiding NOT_ATTRIBUTE_VALUE_NULL ""
    BOOL_OP = OR
    TEST_MODE = Automatic
    TEST_DESCRIPTION = ""
    PASSED -> ar_Opparbeiding_AttributeSplitter
ar_Opparbeiding_AttributeSplitter: AttributeSplitter
    ATTR_NAME = _streng_opparbeiding
    DELIMITER = ,
    TRIM_OPTION = Both
    LIST_NAME = _list_opparbeiding
    DROP_EMPTY_PARTS = Yes
    -> ar_Opparbeiding_ListExploder
ar_Opparbeiding_ListExploder: ListExploder
    INDEX_ATTR = _element_index
    ATTR_ACCUM_MODE = Merge Incoming List
    LIST_ATTR = _list_opparbeiding{}
    ATTR_CONFLICT_RES = Use Original
    LIST_FOUND -> turogfriluftsruter.annenrute_opparbeiding (writer POSTGRES_1)
ar_tilretteleggingsgruppe_Tester: Tester
    TEST_CLAUSE = TEST _streng_tilgjengelighetsgruppe NOT_ATTRIBUTE_VALUE_NULL ""
    BOOL_OP = OR
    TEST_MODE = Automatic
    TEST_DESCRIPTION = ""
    PASSED -> ar_Tilretteleggingsgruppe_AttributeSplitter
ar_Tilretteleggingsgruppe_AttributeSplitter: AttributeSplitter
    ATTR_NAME = _streng_tilgjengelighetsgruppe
    DELIMITER = ,
    TRIM_OPTION = Both
    LIST_NAME = _list_tilretteleggingsgruppe
    DROP_EMPTY_PARTS = Yes
    -> ar_Tilgjengelighetsgruppe_ListExploder
ar_Tilgjengelighetsgruppe_ListExploder: ListExploder
    INDEX_ATTR = _element_index
    ATTR_ACCUM_MODE = Merge Incoming List
    LIST_ATTR = _list_tilretteleggingsgruppe{}
    ATTR_CONFLICT_RES = Use Original
    LIST_FOUND -> turogfriluftsruter.annenrute_tilgjengelighetsgruppe (writer POSTGRES_1)
fr_Opparbeiding_Tester: Tester
    TEST_CLAUSE = TEST _streng_opparbeiding NOT_ATTRIBUTE_VALUE_NULL ""
    BOOL_OP = OR
    TEST_MODE = Automatic
    TEST_DESCRIPTION = ""
    PASSED -> fr_Opparbeiding_AttributeSplitter
fr_Opparbeiding_AttributeSplitter: AttributeSplitter
    ATTR_NAME = _streng_opparbeiding
    DELIMITER = ,
    TRIM_OPTION = Both
    LIST_NAME = _list_opparbeiding
    DROP_EMPTY_PARTS = Yes
    -> fr_Opparbeiding_ListExploder
fr_Opparbeiding_ListExploder: ListExploder
    INDEX_ATTR = _element_index
    ATTR_ACCUM_MODE = Merge Incoming List
    LIST_ATTR = _list_opparbeiding{}
    ATTR_CONFLICT_RES = Use Original
    LIST_FOUND -> turogfriluftsruter.fotrute_opparbeiding (writer POSTGRES_1)
fr_Sfotrutetype_Tester: Tester
    TEST_CLAUSE = TEST _streng_sfotrutetype NOT_ATTRIBUTE_VALUE_NULL ""
    BOOL_OP = OR
    TEST_MODE = Automatic
    TEST_DESCRIPTION = ""
    PASSED -> fr_Sfotrutetype_AttributeSplitter
fr_Sfotrutetype_AttributeSplitter: AttributeSplitter
    ATTR_NAME = _streng_sfotrutetype
    DELIMITER = ,
    TRIM_OPTION = Both
    LIST_NAME = _list_sfotrutetype
    DROP_EMPTY_PARTS = Yes
    -> fr_Sfotrutetype_ListExploder
fr_Sfotrutetype_ListExploder: ListExploder
    INDEX_ATTR = _element_index
    ATTR_ACCUM_MODE = Merge Incoming List
    LIST_ATTR = _list_sfotrutetype{}
    ATTR_CONFLICT_RES = Use Original
    LIST_FOUND -> turogfriluftsruter.fotrute_sfotrutetype (writer POSTGRES_1)
fr_Tilgjengelighetsgruppe_Tester: Tester
    TEST_CLAUSE = TEST _streng_tilgjengelighetsgruppe NOT_ATTRIBUTE_VALUE_NULL ""
    BOOL_OP = OR
    TEST_MODE = Automatic
    TEST_DESCRIPTION = ""
    PASSED -> fr_Tilgjengelighetsgruppe_AttributeSplitter
fr_Tilgjengelighetsgruppe_AttributeSplitter: AttributeSplitter
    ATTR_NAME = _streng_tilgjengelighetsgruppe
    DELIMITER = ,
    TRIM_OPTION = Both
    LIST_NAME = _list_tilgjengelighetsgruppe
    DROP_EMPTY_PARTS = Yes
    -> fr_Tilgjengelighetsgruppe_ListExploder
fr_Tilgjengelighetsgruppe_ListExploder: ListExploder
    INDEX_ATTR = _element_index
    ATTR_ACCUM_MODE = Merge Incoming List
    LIST_ATTR = _list_tilgjengelighetsgruppe{}
    ATTR_CONFLICT_RES = Use Original
    LIST_FOUND -> turogfriluftsruter.fotrute_tilgjengelighetsgruppe (writer POSTGRES_1)
sl_Opparbeiding_Tester: Tester
    TEST_CLAUSE = TEST _streng_opparbeiding NOT_ATTRIBUTE_VALUE_NULL ""
    BOOL_OP = OR
    TEST_MODE = Automatic
    TEST_DESCRIPTION = ""
    PASSED -> sl_Opparbeiding_AttributeSplitter
sl_Opparbeiding_AttributeSplitter: AttributeSplitter
    ATTR_NAME = _streng_opparbeiding
    DELIMITER = ,
    TRIM_OPTION = Both
    LIST_NAME = _list_opparbeiding
    DROP_EMPTY_PARTS = Yes
    -> sl_Opparbeiding_ListExploder
sl_Opparbeiding_ListExploder: ListExploder
    INDEX_ATTR = _element_index
    ATTR_ACCUM_MODE = Merge Incoming List
    LIST_ATTR = _list_opparbeiding{}
    ATTR_CONFLICT_RES = Use Original
    LIST_FOUND -> turogfriluftsruter.skiloype_opparbeiding (writer POSTGRES_1)
sl_Tilgjengelighetsgruppe_Tester: Tester
    TEST_CLAUSE = TEST _streng_tilgjengelighetsgruppe NOT_ATTRIBUTE_VALUE_NULL ""
    BOOL_OP = OR
    TEST_MODE = Automatic
    TEST_DESCRIPTION = ""
    PASSED -> sl_Tilgjengelighetsgruppe_AttributeSplitter
sl_Tilgjengelighetsgruppe_AttributeSplitter: AttributeSplitter
    ATTR_NAME = _streng_tilgjengelighetsgruppe
    DELIMITER = ,
    TRIM_OPTION = Both
    LIST_NAME = _list_tilgjengelighetsgruppe
    DROP_EMPTY_PARTS = Yes
    -> sl_Tilgjengelighetsgruppe_ListExploder
sl_Tilgjengelighetsgruppe_ListExploder: ListExploder
    INDEX_ATTR = _element_index
    ATTR_ACCUM_MODE = Merge Incoming List
    LIST_ATTR = _list_tilgjengelighetsgruppe{}
    ATTR_CONFLICT_RES = Use Original
    LIST_FOUND -> turogfriluftsruter.skiloype_tilgjengelighetsgruppe (writer POSTGRES_1)
STATUS_SOSI_BulkAttributeRenamer: BulkAttributeRenamer [off]
    PATTERN_ACTION_DISP = Change Case
    ATTRCHOICE = All Attributes
    CASE_CHANGE_TYPE = lowercase
SOSI_Relationshipclasses_BulkAttributeRenamer: BulkAttributeRenamer [off]
    PATTERN_ACTION_DISP = Add String Prefix
    ATTRCHOICE = All Attributes

Bookmark: SOSI-kildedata
AnnenRute (reader SOSI_1)
    attributes: SOSI_id SOSI_int32, RUTEMERKING SOSI_char(2), DATAFANGSTDATO SOSI_datetime, KOBLING_ID SOSI_char(255), NOYAKTIGHET SOSI_number(6,0), MALEMETODE SOSI_int16, SKILTING SOSI_char(3), VEDLIKEH SOSI_char(35), NAVN SOSI_char(60), RUTENR SOSI_char(100), OPPHAV SOSI_char(255), INFORMASJON SOSI_char(255), ARUTETYPE SOSI_char(50), OBJTYPE SOSI_char(32), OPPDATERINGSDATO SOSI_datetime
    -> BulkAttributeRenamer
Fotrute (reader SOSI_1)
    attributes: SOSI_id SOSI_int32, RUTEMERKING SOSI_char(2), LINK SOSI_char(255), DATAFANGSTDATO SOSI_datetime, H_MALEMETODE SOSI_int16, KOBLING_ID SOSI_char(255), TRAFIKKBELASTNING SOSI_int16, NOYAKTIGHET SOSI_number(6,0), TILGJENGELIGHETSGRUPPE SOSI_int16, SYNBARHET SOSI_int16, STATUS SOSI_char(2), MEDIUM SOSI_char(1), OPPARBEIDING SOSI_int16, RUTETYPE SOSI_int16, KOMM SOSI_char(4), MALEMETODE SOSI_int16, SKILTING SOSI_char(3), VEDLIKEH SOSI_char(35), SOSI_guid SOSI_char(36), NAVN SOSI_char(60), RUTEBETYDNING SOSI_int16, UNDERLAGSTYPE SOSI_int16, RUTENR SOSI_char(100), OPPHAV SOSI_char(255), FRILUFTEIERFORHOLD SOSI_int16, SESONG SOSI_char(25), INFORMASJON SOSI_char(255), SFOTRUTETYPE SOSI_char(2), RUTEFOLGER SOSI_char(2), OBJTYPE SOSI_char(32),
      H_NOYAKTIGHET SOSI_number(6,0), OPPDATERINGSDATO SOSI_datetime, BELYSNING SOSI_int16, RUTEBREDDE SOSI_int16, STIGNING SOSI_int16, RUTEVANSKELIGHETSGRAD SOSI_char(25)
    -> BulkAttributeRenamer
FriluftslivTilrettelegging (reader SOSI_1)
    attributes: SOSI_id SOSI_int32, LINK SOSI_char(255), DATAFANGSTDATO SOSI_datetime, KOBLING_ID SOSI_char(255), NOYAKTIGHET SOSI_number(6,0), SYNBARHET SOSI_int16, KOMM SOSI_char(4), MALEMETODE SOSI_int16, FRITILRETTELEGGING SOSI_int16, VEDLIKEH SOSI_char(35), OPPHAV SOSI_char(255), INFORMASJON SOSI_char(255), OBJTYPE SOSI_char(32), OPPDATERINGSDATO SOSI_datetime, ID SOSI_char(70)
    -> BulkAttributeRenamer
Skiloype (reader SOSI_1)
    attributes: SOSI_id SOSI_int32, RUTEMERKING SOSI_char(2), DATAFANGSTDATO SOSI_datetime, H_MALEMETODE SOSI_int16, KOBLING_ID SOSI_char(255), NOYAKTIGHET SOSI_number(6,0), SYNBARHET SOSI_int16, OPPARBEIDING SOSI_int16, RYDDEBREDDE SOSI_int16, KOMM SOSI_char(4), SKOYTETRASE SOSI_char(3), SPES_SKILOYPETYPE SOSI_char(2), MALEMETODE SOSI_int16, SKILTING SOSI_char(3), VEDLIKEH SOSI_char(35), PREPARERING SOSI_char(3), NAVN SOSI_char(60), UNDERLAGSTYPE SOSI_int16, RUTENR SOSI_char(100), OPPHAV SOSI_char(255), FRILUFTEIERFORHOLD SOSI_int16, INFORMASJON SOSI_char(255), RUTEFOLGER SOSI_char(2), OBJTYPE SOSI_char(32), H_NOYAKTIGHET SOSI_number(6,0), OPPDATERINGSDATO SOSI_datetime, BELYSNING SOSI_int16, RUTEBREDDE SOSI_int16, RUTEVANSKELIGHETSGRAD SOSI_char(25)
    -> BulkAttributeRenamer
Sykkelrute (reader SOSI_1)
    attributes: SOSI_id SOSI_int32, RUTEMERKING SOSI_char(2), DATAFANGSTDATO SOSI_datetime, H_MALEMETODE SOSI_int16, KOBLING_ID SOSI_char(255), SPESIALSYKKELRUTETYPE SOSI_char(100), NOYAKTIGHET SOSI_number(6,0), TILGJENGELIGHETSGRUPPE SOSI_int16, SYNBARHET SOSI_int16, KOMM SOSI_char(4), MALEMETODE SOSI_int16, SKILTING SOSI_char(3), VEDLIKEH SOSI_char(35), NAVN SOSI_char(60), UNDERLAGSTYPE SOSI_int16, RUTENR SOSI_char(100), OPPHAV SOSI_char(255), FRILUFTEIERFORHOLD SOSI_int16, INFORMASJON SOSI_char(255), RUTEFOLGER SOSI_char(2), OBJTYPE SOSI_char(32), H_NOYAKTIGHET SOSI_number(6,0), OPPDATERINGSDATO SOSI_datetime, BELYSNING SOSI_int16, RUTEVANSKELIGHETSGRAD SOSI_char(25)
    -> BulkAttributeRenamer
OPPARBEIDING_SOSI (reader SOSI_1)
    attributes: OPPARBEIDING SOSI_int16, SOSI_parent_guid SOSI_char(36)
    -> OPPARBEIDING_SOSI_BulkAttributeRenamer
SFOTRUTETYPE_SOSI (reader SOSI_1)
    attributes: SFOTRUTETYPE SOSI_char(2), SOSI_parent_guid SOSI_char(36)
    -> SFOTRUTE_SOSI_BulkAttributeRenamer
TILGJENGELIGHETSGRUPPE_SOSI (reader SOSI_1)
    attributes: TILGJENGELIGHETSGRUPPE SOSI_int16, SOSI_parent_guid SOSI_char(36)
    -> TILGJENELIGHETSGRUPPE_BulkAttributeRenamer
STATUS_SOSI (reader SOSI_1) [off]
    attributes: STATUS SOSI_char(2), SOSI_parent_guid SOSI_char(36)
    -> STATUS_SOSI_BulkAttributeRenamer
SOSI_RelationshipClasses (reader SOSI_1) [off]
    attributes: FeatureClass SOSI_char(100), GeometryType SOSI_char(32), Table SOSI_char(100)
    -> SOSI_Relationshipclasses_BulkAttributeRenamer

Bookmark: Måldata PostGIS
turogfriluftsruter.annenrute (writer POSTGIS_1) [off]
    attributes: objid serial,PRIKEY, objtype varchar(32), arutetype varchar(80), vedlikeh varchar(80), frilufteierforhold varchar(80), belysning varchar(80), rutemerking varchar(80), skilting bool, rutefolger varchar(80), rutebredde varchar(80), opparbeiding varchar(80), rutebetydning varchar(80), rutevanskelighetsgrad varchar(80), underlagstype varchar(80), lengde int4, stigning int4, tilgjengelighetsgruppe varchar(80), rutetype varchar(80), navn varchar(80), rutenr varchar(80), lokalid uuid, datafangstdato timestamp, oppdateringsdato timestamp, malemetode varchar(80), noyaktighet int4, synbarhet varchar(80), malemetodehoyde varchar(80), h_noyaktighet int4, opphav varchar(80), kommune varchar(80),
      informasjon varchar(80), link varchar(80)
turogfriluftsruter.fotrute (writer POSTGIS_1) [off]
    attributes: objid serial,PRIKEY, objtype varchar(32), sfotrutetype varchar(80), sesong varchar(80), vedlikeh varchar(80), frilufteierforhold varchar(80), belysning varchar(80), rutemerking varchar(80), skilting bool, rutefolger varchar(80), rutebredde varchar(80), opparbeiding varchar(80), rutebetydning varchar(80), rutevanskelighetsgrad varchar(80), underlagstype varchar(80), lengde int4, stigning int4, tilgjengelighetsgruppe varchar(80), rutetype varchar(80), navn varchar(80), rutenr varchar(80), lokalid uuid, datafangstdato timestamp, oppdateringsdato timestamp, malemetode varchar(80), noyaktighet int4, synbarhet varchar(80), malemetodehoyde varchar(80), h_noyaktighet int4, opphav varchar(80),
      kommune varchar(80), informasjon varchar(80), link varchar(80)
turogfriluftsruter.friluftslivtilrettelegging (writer POSTGIS_1) [off]
    attributes: objid serial,PRIKEY, objtype varchar(32), vedlikeh varchar(80), fritilrettelegging varchar(80), lokalid uuid, datafangstdato timestamp, oppdateringsdato timestamp, malemetode varchar(80), noyaktighet int4, synbarhet varchar(80), malemetodehoyde varchar(80), h_noyaktighet int4, opphav varchar(80), kommune varchar(80), informasjon varchar(80), link varchar(80)
turogfriluftsruter.skiloype (writer POSTGIS_1) [off]
    attributes: objid int4,PRIKEY, objtype varchar(32), spes_skiloypetype varchar(80), preparering varchar(80), ryddebredde varchar(80), antallskispor int4, skoytetrase bool, vedlikeh varchar(80), frilufteierforhold varchar(80), belysning varchar(80), rutemerking varchar(80), skilting bool, rutefolger varchar(80), rutebredde varchar(80), opparbeiding varchar(80), rutebetydning varchar(80), rutevanskelighetsgrad varchar(80), underlagstype varchar(80), lengde int4, stigning int4, tilgjengelighetsgruppe varchar(80), rutetype varchar(80), navn varchar(80), rutenr varchar(80), lokalid uuid, datafangstdato timestamp, oppdateringsdato timestamp, malemetode varchar(80), noyaktighet int4, synbarhet varchar(80),
      malemetodehoyde varchar(80), h_noyaktighet int4, opphav varchar(80), kommune varchar(80), informasjon varchar(80), link varchar(80)
turogfriluftsruter.sykkelrute (writer POSTGIS_1) [off]
    attributes: objid serial,PRIKEY, objtype varchar(32), spesialsykkelrutetype varchar(80), trafikkbelastning varchar(80), vedlikeh varchar(80), frilufteierforhold varchar(80), belysning varchar(80), rutemerking varchar(80), skilting bool, rutefolger varchar(80), rutebredde varchar(80), opparbeiding varchar(80), rutebetydning varchar(80), rutevanskelighetsgrad varchar(80), underlagstype varchar(80), lengde int4, stigning int4, tilgjengelighetsgruppe varchar(80), rutetype varchar(80), navn varchar(80), rutenr varchar(80), lokalid uuid, datafangstdato timestamp, oppdateringsdato timestamp, malemetode varchar(80), noyaktighet int4, synbarhet varchar(80), malemetodehoyde varchar(80), h_noyaktighet int4, opphav varchar(80),
      kommune varchar(80), informasjon varchar(80), link varchar(80)

Bookmark: Måldata PostgreSQL
turogfriluftsruter.annenrute_opparbeiding (writer POSTGRES_1) [off]
    attributes: objid int4,PRIKEY, opparbeiding int4
turogfriluftsruter.annenrute_tilgjengelighetsgruppe (writer POSTGRES_1) [off]
    attributes: objid int4,PRIKEY, tilgjengelighetsgruppe int4
turogfriluftsruter.fotrute_opparbeiding (writer POSTGRES_1) [off]
    attributes: objid int4,PRIKEY, opparbeiding int4
turogfriluftsruter.fotrute_sfotrutetype (writer POSTGRES_1) [off]
    attributes: objid int4,PRIKEY, sfotrutetype varchar(80)
turogfriluftsruter.fotrute_tilgjengelighetsgruppe (writer POSTGRES_1) [off]
    attributes: objid int4,PRIKEY, tilgjengelighetsgruppe int4
turogfriluftsruter.skiloype_opparbeiding (writer POSTGRES_1) [off]
    attributes: objid int4,PRIKEY, opparbeiding int4
turogfriluftsruter.skiloype_tilgjengelighetsgruppe (writer POSTGRES_1) [off]
    attributes: objid int4,PRIKEY, tilgjengelighetsgruppe int4
turogfriluftsruter.sykkelrute_opparbeiding (writer POSTGRES_1) [off]
    attributes: objid int4,PRIKEY, opparbeiding int4
turogfriluftsruter.sykkelrute_tilgjengelighetsgruppe (writer POSTGRES_1) [off]
    attributes: objid int4,PRIKEY, tilgjengelighetsgruppe int4
