FME workspace postgis2sosi_Test.fmw

Parameters:
- SourceDataset_POSTGIS = geonorutv@localhost:5432/geonorutv   # Connection
- DestDataset_SOSI = $(FME_MF_DIR)Postgis2SOSI_Test.sos   # Destination SOSI File

Readers:
- POSTGIS_1: POSTGIS from $(SourceDataset_POSTGIS)

Writers:
- SOSI_1: SOSI to $(DestDataset_SOSI) in EPSG:4258

turogfriluftsruter.friluftslivtilrettelegging (reader POSTGIS_1) [off]
    attributes: objid int4,PRIKEY, objtype varchar(32), vedlikeh varchar(80), fritilrettelegging varchar(80), lokalid uuid,PRIKEY, datafangstdato timestamp, oppdateringsdato timestamp, malemetode varchar(80), noyaktighet int4, synbarhet varchar(80), malemetodehoyde varchar(80), h_noyaktighet int4, opphav varchar(80), kommune varchar(80), informasjon varchar(80), link varchar(80)
    -> turogfriluftsruter.friluftslivtilrettelegging (writer SOSI_1)
turogfriluftsruter.friluftslivtilrettelegging (writer SOSI_1)
    attributes: objid SOSI_int32, objtype SOSI_varchar(32), vedlikeh SOSI_varchar(80), fritilrettelegging SOSI_varchar(80), lokalid SOSI_buffer, datafangstdato SOSI_datetime, oppdateringsdato SOSI_datetime, malemetode SOSI_varchar(80), noyaktighet SOSI_int32, synbarhet SOSI_varchar(80), malemetodehoyde SOSI_varchar(80), h_noyaktighet SOSI_int32, opphav SOSI_varchar(80), kommune SOSI_varchar(80), informasjon SOSI_varchar(80), link SOSI_varchar(80)
turogfriluftsruter.annenrute (reader POSTGIS_1) [off]
    attributes: objid int4,PRIKEY, objtype varchar(32), arutetype varchar(80), vedlikeh varchar(80), frilufteierforhold varchar(80), belysning varchar(80), rutemerking varchar(80), skilting bool, rutefolger varchar(80), rutebredde varchar(80), opparbeiding varchar(80), rutebetydning varchar(80), rutevanskelighetsgrad varchar(80), underlagstype varchar(80), lengde int4, stigning int4, tilgjengelighetsgruppe varchar(80), rutetype varchar(80), navn varchar(80), rutenr varchar(80), lokalid uuid,PRIKEY, datafangstdato timestamp, oppdateringsdato timestamp, malemetode varchar(80), noyaktighet int4, synbarhet varchar(80), malemetodehoyde varchar(80), h_noyaktighet int4, opphav varchar(80), kommune varchar(80),
      informasjon varchar(80), link varchar(80)
    -> turogfriluftsruter.annenrute (writer SOSI_1)
turogfriluftsruter.annenrute (writer SOSI_1)
    attributes: objid SOSI_int32, objtype SOSI_varchar(32), arutetype SOSI_varchar(80), vedlikeh SOSI_varchar(80), frilufteierforhold SOSI_varchar(80), belysning SOSI_varchar(80), rutemerking SOSI_varchar(80), skilting SOSI_boolean, rutefolger SOSI_varchar(80), rutebredde SOSI_varchar(80), opparbeiding SOSI_varchar(80), rutebetydning SOSI_varchar(80), rutevanskelighetsgrad SOSI_varchar(80), underlagstype SOSI_varchar(80), lengde SOSI_int32, stigning SOSI_int32, tilgjengelighetsgruppe SOSI_varchar(80), rutetype SOSI_varchar(80), navn SOSI_varchar(80), rutenr SOSI_varchar(80), lokalid SOSI_buffer, datafangstdato SOSI_datetime, oppdateringsdato SOSI_datetime, malemetode SOSI_varchar(80), noyaktighet SOSI_int32, synbarhet SOSI_varchar(80), malemetodehoyde SOSI_varchar(80), h_noyaktighet SOSI_int32, opphav SOSI_varchar(80), kommune SOSI_varchar(80),
      informasjon SOSI_varchar(80), link SOSI_varchar(80)
turogfriluftsruter.skiloype (reader POSTGIS_1) [off]
    attributes: objid int4,PRIKEY, objtype varchar(32), spes_skiloypetype varchar(80), preparering varchar(80), ryddebredde varchar(80), antallskispor int4, skoytetrase bool, vedlikeh varchar(80), frilufteierforhold varchar(80), belysning varchar(80), rutemerking varchar(80), skilting bool, rutefolger varchar(80), rutebredde varchar(80), opparbeiding varchar(80), rutebetydning varchar(80), rutevanskelighetsgrad varchar(80), underlagstype varchar(80), lengde int4, stigning int4, tilgjengelighetsgruppe varchar(80), rutetype varchar(80), navn varchar(80), rutenr varchar(80), lokalid uuid,PRIKEY, datafangstdato timestamp, oppdateringsdato timestamp, malemetode varchar(80), noyaktighet int4, synbarhet varchar(80),
      malemetodehoyde varchar(80), h_noyaktighet int4, opphav varchar(80), kommune varchar(80), informasjon varchar(80), link varchar(80)
    -> turogfriluftsruter.skiloype (writer SOSI_1)
turogfriluftsruter.skiloype (writer SOSI_1)
    attributes: objid SOSI_int32, objtype SOSI_varchar(32), spes_skiloypetype SOSI_varchar(80), preparering SOSI_varchar(80), ryddebredde SOSI_varchar(80), antallskispor SOSI_int32, skoytetrase SOSI_boolean, vedlikeh SOSI_varchar(80), frilufteierforhold SOSI_varchar(80), belysning SOSI_varchar(80), rutemerking SOSI_varchar(80), skilting SOSI_boolean, rutefolger SOSI_varchar(80), rutebredde SOSI_varchar(80), opparbeiding SOSI_varchar(80), rutebetydning SOSI_varchar(80), rutevanskelighetsgrad SOSI_varchar(80), underlagstype SOSI_varchar(80), lengde SOSI_int32, stigning SOSI_int32, tilgjengelighetsgruppe SOSI_varchar(80), rutetype SOSI_varchar(80), navn SOSI_varchar(80), rutenr SOSI_varchar(80), lokalid SOSI_buffer, datafangstdato SOSI_datetime, oppdateringsdato SOSI_datetime, malemetode SOSI_varchar(80), noyaktighet SOSI_int32, synbarhet SOSI_varchar(80),
      malemetodehoyde SOSI_varchar(80), h_noyaktighet SOSI_int32, opphav SOSI_varchar(80), kommune SOSI_varchar(80), informasjon SOSI_varchar(80), link SOSI_varchar(80)
turogfriluftsruter.fotrute (reader POSTGIS_1)
    attributes: objid int4,PRIKEY, objtype varchar(32), sfotrutetype varchar(80), sesong varchar(80), vedlikeh varchar(80), frilufteierforhold varchar(80), belysning varchar(80), rutemerking varchar(80), skilting bool, rutefolger varchar(80), rutebredde varchar(80), opparbeiding varchar(80), rutebetydning varchar(80), rutevanskelighetsgrad varchar(80), underlagstype varchar(80), lengde int4, stigning int4, tilgjengelighetsgruppe varchar(80), rutetype varchar(80), navn varchar(80), rutenr varchar(80), lokalid uuid,PRIKEY, datafangstdato timestamp, oppdateringsdato timestamp, malemetode varchar(80), noyaktighet int4, synbarhet varchar(80), malemetodehoyde varchar(80), h_noyaktighet int4, opphav varchar(80),
      kommune varchar(80), informasjon varchar(80), link varchar(80)
    -> AttributeValueMapper
AttributeValueMapper
    DIRECTION = Forward (Source To Destination)
    LUT = t,JA,f,NEI
    SRC = skilting
    VAL_ATTR = skilting
    -> turogfriluftsruter.fotrute (writer SOSI_1)
turogfriluftsruter.fotrute (writer SOSI_1)
    attributes: objid SOSI_int32, objtype SOSI_varchar(32), sfotrutetype SOSI_varchar(80), sesong SOSI_varchar(80), vedlikeh SOSI_varchar(80), frilufteierforhold SOSI_varchar(80), belysning SOSI_varchar(80), rutemerking SOSI_varchar(80), skilting SOSI_boolean, rutefolger SOSI_varchar(80), rutebredde SOSI_varchar(80), opparbeiding SOSI_varchar(80), rutebetydning SOSI_varchar(80), rutevanskelighetsgrad SOSI_varchar(80), underlagstype SOSI_varchar(80), lengde SOSI_int32, stigning SOSI_int32, tilgjengelighetsgruppe SOSI_varchar(80), rutetype SOSI_varchar(80), navn SOSI_varchar(80), rutenr SOSI_varchar(80), lokalid SOSI_buffer, datafangstdato SOSI_datetime, oppdateringsdato SOSI_datetime, malemetode SOSI_varchar(80), noyaktighet SOSI_int32, synbarhet SOSI_varchar(80), malemetodehoyde SOSI_varchar(80), h_noyaktighet SOSI_int32, opphav SOSI_varchar(80),
      kommune SOSI_varchar(80), informasjon SOSI_varchar(80), link SOSI_varchar(80)
turogfriluftsruter.sykkelrute (reader POSTGIS_1) [off]
    attributes: objid int4,PRIKEY, objtype varchar(32), spesialsykkelrutetype varchar(80), trafikkbelastning varchar(80), vedlikeh varchar(80), frilufteierforhold varchar(80), belysning varchar(80), rutemerking varchar(80), skilting bool, rutefolger varchar(80), rutebredde varchar(80), opparbeiding varchar(80), rutebetydning varchar(80), rutevanskelighetsgrad varchar(80), underlagstype varchar(80), lengde int4, stigning int4, tilgjengelighetsgruppe varchar(80), rutetype varchar(80), navn varchar(80), rutenr varchar(80), lokalid uuid,PRIKEY, datafangstdato timestamp, oppdateringsdato timestamp, malemetode varchar(80), noyaktighet int4, synbarhet varchar(80), malemetodehoyde varchar(80), h_noyaktighet int4, opphav varchar(80),
      kommune varchar(80), informasjon varchar(80), link varchar(80)
    -> turogfriluftsruter.sykkelrute (writer SOSI_1)
turogfriluftsruter.sykkelrute (writer SOSI_1)
    attributes: objid SOSI_int32, objtype SOSI_varchar(32), spesialsykkelrutetype SOSI_varchar(80), trafikkbelastning SOSI_varchar(80), vedlikeh SOSI_varchar(80), frilufteierforhold SOSI_varchar(80), belysning SOSI_varchar(80), rutemerking SOSI_varchar(80), skilting SOSI_boolean, rutefolger SOSI_varchar(80), rutebredde SOSI_varchar(80), opparbeiding SOSI_varchar(80), rutebetydning SOSI_varchar(80), rutevanskelighetsgrad SOSI_varchar(80), underlagstype SOSI_varchar(80), lengde SOSI_int32, stigning SOSI_int32, tilgjengelighetsgruppe SOSI_varchar(80), rutetype SOSI_varchar(80), navn SOSI_varchar(80), rutenr SOSI_varchar(80), lokalid SOSI_buffer, datafangstdato SOSI_datetime, oppdateringsdato SOSI_datetime, malemetode SOSI_varchar(80), noyaktighet SOSI_int32, synbarhet SOSI_varchar(80), malemetodehoyde SOSI_varchar(80), h_noyaktighet SOSI_int32, opphav SOSI_varchar(80),
      kommune SOSI_varchar(80), informasjon SOSI_varchar(80), link SOSI_varchar(80)
