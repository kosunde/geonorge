FME workspace TurOgFriluftsruter_postgis2sosi.fmw
# Copyright: (c) xgrimor 2015
# Licence: <your licence>
Shutdown Python:
      # -*- coding: utf-8 -*-
      #-------------------------------------------------------------------------------
      # Name:        zipfiles.py
      # Purpose:     Pakker filer i output folderen
      #
      # Author:      xsunknu
      #
      # Created:     18.09.2015
      # Copyright:   (c) xsunknu 2015
      # Licence:     <your licence>
      #-------------------------------------------------------------------------------

      import sys, os, zipfile, fme

      def zip(sosifile, zfile):
          from os.path import basename

          # Lager korresponderende zip-fil av SOSI-fil
          if os.path.isfile(zfile):
              os.remove(zfile)

          zf = zipfile.ZipFile(zfile, "w", zipfile.ZIP_DEFLATED)

          # Ønsker ikke full sti inn i ZIP-filen
          arcname = basename(sosifile)

          # ZIP-formatet støtter ikke non-ascii tegn
          # Erstatter AØÅæøå med ascii-tegn
          arcname = arcname.replace('\xc6', 'E')
          arcname = arcname.replace('\xd8', 'O')
          arcname = arcname.replace('\xc5', 'A')
          arcname = arcname.replace('\xe6', 'e')
          arcname = arcname.replace('\xf8', 'o')
          arcname = arcname.replace('\xe5', 'a')

          zf.write(sosifile, arcname)
          zf.close()
          os.remove(sosifile)

          return

      def main():

          # Kjøres ikke på FME Server, da FME Server selv sørger for pakkingen
          if not 'FME_SERVER_DEST_DIR' in fme.macroValues:
              if 'FANOUT_FOLDER' in fme.macroValues:
                  logger = open(fme.logFileName, 'a')
                  path = fme.macroValues['FANOUT_FOLDER']
                  for dirpath, dnames, fnames in os.walk(path):
                      for f in fnames:
                          if f.endswith(".sos"):
                              # Scanner gjennom alle SOSI-filer
                              sosifile = os.path.join(path, f)
                              zfile = os.path.splitext(sosifile)[0] + '.zip'
                              if os.path.isfile(zfile):

                                  # Korresponderende ZIP-fil finnes, sjekker timestamps
                                  sositstamp = os.stat(sosifile).st_mtime
                                  ziptstamp = os.stat(zfile).st_mtime

                                  if sositstamp > ziptstamp:
                                      # SOSI-fil er nyere enn ZIP-fila, ZIP-fila oppdateres
                                      # SOSI-fila slettes
                                      try:
                                          zip(sosifile, zfile)
                                      except:
      #                                    print 'Kunne ikke pakke: ' + sosifile
                                          logger.write('Kunne ikke pakke: ' + sosifile + '\n')
                                  else:
                                      # SOSI-fila er eldre enn ZIP-fila
                                      # SOSI-fila slettes
                                      try:
                                          os.remove(sosifile)
                                      except:
      #                                    print 'Kunne ikke slette: ' + sosifile
                                          logger.write('Kunne ikke slette: ' + sosifile + '\n')
                              else:
                                  # ZIP-fila eksisterer ikke og lages
                                  # SOSI-fila slettes
                                  try:
                                      zip(sosifile, zfile)
                                  except:
      #                                print 'Kunne ikke pakke: ' + sosifile
                                      logger.write('Kunne ikke pakke: ' + sosifile + '\n')

                  logger.close()

      if __name__ == '__main__':
          main()

Parameters:
- KNR =   # Kommune(r)
- FNR = 20   # Fylke(r)
- CLIPPERCOORDS =   # Clipper coordinates
- CLIPPER_EPSG_CODE =   # Clipper EPSG code
- CLIPPER_FILE =   # "" Clipper file (any format)
- OUTPUT_EPSG_CODE = 25835   # Output EPSG code
- FANOUT = Fylker   # Fanout områder
- CONFIG_FILE:   # Python Script
      #-------------------------------------------------------------------------------
      # Name:        GetConfigFile
      # Purpose:
      #
      # Author:      xsunknu
      #
      # Created:     21.08.2015
      # Copyright:   (c) xsunknu 2015
      # Licence:     <your licence>
      #-------------------------------------------------------------------------------
      
      import os, fme
      
      fmwdir = fme.macroValues['FME_MF_DIR']
      fmwfile = fme.macroValues['FME_MF_NAME']
      
      fmwfile = os.path.join(fmwdir, fmwfile)
      configfile = os.path.splitext(fmwfile)[0] + '_config.xml'
      
      return configfile
- PG_PWD:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgpwd').text
      
      return value
- PG_USER:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pguser').text
      
      return value
- PG_HOST:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pghost').text
      
      return value
- PG_DB:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgdb').text
      
      return value
- SOSI_FILE = turogfriluftsruter   # SOSI file 
- FIXEDCLIPPERCOORDS:   # Python Script
      #-------------------------------------------------------------------------------
      # Name:        FixClipperCoords
      # Purpose:
      #
      # Author:      xsunknu
      #
      # Created:     21.08.2015
      # Copyright:   (c) xsunknu 2015
      # Licence:     <your licence>
      #-------------------------------------------------------------------------------
      
      import fme
      clippercoords = fme.macroValues['CLIPPERCOORDS']
      
      if clippercoords == '':
          clippercoords = '1 1'
      
      return clippercoords
- DESTCOORDSYS:   # Python Script
      #-------------------------------------------------------------------------------
      # Name:        SetCoordinateSystem
      # Purpose:
      #
      # Author:      xsunknu
      #
      # Created:     21.08.2015
      # Copyright:   (c) xsunknu 2015
      # Licence:     <your licence>
      #-------------------------------------------------------------------------------
      
      import os, fme
      
      EPSGvalue = fme.macroValues['OUTPUT_EPSG_CODE']
      EPSGcode  = 'EPSG:' + EPSGvalue
      
      return EPSGcode
- CLIPPERCOORDSYS:   # Python Script
      #-------------------------------------------------------------------------------
      # Name:        SetCoordinateSystem
      # Purpose:
      #
      # Author:      xsunknu
      #
      # Created:     21.08.2015
      # Copyright:   (c) xsunknu 2015
      # Licence:     <your licence>
      #-------------------------------------------------------------------------------
      
      import os, fme
      
      EPSGvalue = fme.macroValues['CLIPPER_EPSG_CODE']
      EPSGcode  = 'EPSG:' + EPSGvalue
      
      return EPSGcode
- LOG_FILE:   # Python Script
      #-------------------------------------------------------------------------------
      # Name:        GetConfigFile
      # Purpose:
      #
      # Author:      xsunknu
      #
      # Created:     21.08.2015
      # Copyright:   (c) xsunknu 2015
      # Licence:     <your licence>
      #-------------------------------------------------------------------------------
      
      import os, uuid, fme
      
      fmwdir = fme.macroValues['FME_MF_DIR']
      fmwfile = fme.macroValues['FME_MF_NAME']
      
      logdir = os.path.join(fmwdir, 'log')
      if not os.path.isdir(logdir):
          os.mkdir(logdir)
      
      logfile = os.path.splitext(fmwfile)[0] + '_' + str(uuid.uuid1()).replace('-','') + '.log'
      logfile = os.path.join(logdir, logfile)
      
      return logfile
- FANOUT_FOLDER:   # Python Script
      #-------------------------------------------------------------------------------
      # Name:        GetConfigFile
      # Purpose:
      #
      # Author:      xsunknu
      #
      # Created:     21.08.2015
      # Copyright:   (c) xsunknu 2015
      # Licence:     <your licence>
      #-------------------------------------------------------------------------------
      
      import os, fme
      from xml.etree import ElementTree as ET
      
      if 'FME_SERVER_DEST_DIR' in fme.macroValues:
          value = fme.macroValues['FME_SERVER_DEST_DIR']
      else:
          #Read XML config file
          configtree = ET.parse(fme.macroValues['CONFIG_FILE'])
          configdoc = configtree.getroot()
          value = configdoc.find('destdir').text
      
      return value

Readers:
- POSTGIS_1: POSTGIS from $(PG_DB)
- POSTGIS_2: POSTGIS from $(PG_DB)
- POSTGRES_1: POSTGRES from $(PG_DB)

Writers:
- SOSI_1: SOSI to D:\GeoNorge\TurOgFriluftsruter\turogfriluftsruter.sos

CreateClipper
    DESTCOORDSYS = $(DESTCOORDSYS)
    CLIPPERCOORDS = $(FIXEDCLIPPERCOORDS)
    CLIPPERCOORDSYS = $(CLIPPERCOORDSYS)
    reprojectBboxESRI_REPROJECTED_2 -> Clipper [input 1]
ClipperAttributeCreator: AttributeCreator
    ATTR_LIST = _clippercoords,$(CLIPPERCOORDS),_clipper_file,$(CLIPPER_FILE),_fnr,$(FNR),_knr,$(KNR)
    -> ClipperTester
ClipperTester: TestFilter
    TEST_LIST:
      BOOL_OP,AND,COMPOSITE_TEST,<Unused>,TEST_CLAUSE,"TEST _clipper_file ATTRIBUTE_IS_EMPTY """"
      TEST _clippercoords ATTRIBUTE_IS_EMPTY """"
      TEST _fnr ATTRIBUTE_IS_EMPTY """"
      TEST _knr ATTRIBUTE_IS_EMPTY """"",Landsdekkende,BOOL_OP,AND,COMPOSITE_TEST,<Unused>,TEST_CLAUSE,"TEST _clipper_file ATTRIBUTE_IS_EMPTY """"
      TEST _clippercoords ATTRIBUTE_IS_EMPTY """"
      TEST _fnr NOT_ATTRIBUTE_IS_EMPTY """"
      TEST _knr ATTRIBUTE_IS_EMPTY """"",Fylkesvis,BOOL_OP,AND,COMPOSITE_TEST,<Unused>,TEST_CLAUSE,"TEST _clipper_file ATTRIBUTE_IS_EMPTY """"
      TEST _clippercoords ATTRIBUTE_IS_EMPTY """"
      TEST _fnr ATTRIBUTE_IS_EMPTY """"
      TEST _knr NOT_ATTRIBUTE_IS_EMPTY """"",Kommunevis
    DEFAULT_VALUE = <UNFILTERED>
    Landsdekkende -> Destination_Reprojector
    Fylkesvis -> Clipper [input 2]
    Kommunevis -> Clipper [input 2]
Note: Clipper klipper datakilden mot det, eller de, valgte klippeobjektene: / - Kommuner og/eller fylker / - Polygon(er) spesifisert i en klippefil / - Et fritt valgt polygon basert på inntastede koordinater
Clipper
    CLIPPED_ATTR = _clipped
    BOUNDARY_CASES = Treat as Inside
    CREATE_AGGREGATES = Yes
    PRESERVE_CLIPPEE_EXTENTS = No
    CLIP_TYPE = Multiple Clippers
    ATTR_CONFLICT_RES = Use Clippee
    ATTR_ACCUM_MODE = Merge Clipper
    INSIDE -> Destination_Reprojector
Note: Reprojiserer data til / ut-koordinatsystem.
Destination_Reprojector: Reprojector
    SOURCE = Read from feature
    RASTER_CELL_SIZE = Preserve Cells
    DEST = $(DESTCOORDSYS)
    INTERPOLATION_TYPE_NAME = Nearest Neighbor
    REPROJECTED -> Skilting_AttributeValueMapper
Skilting_AttributeValueMapper: AttributeValueMapper
    DEFAULT_VALUE = NEI
    SRC = skilting
    VAL_ATTR = skilting
    DIRECTION = Forward (Source To Destination)
    LUT = f,NEI,t,JA
    -> Skoytetrase_AttributeValueMapper
Skoytetrase_AttributeValueMapper: AttributeValueMapper
    DEFAULT_VALUE = NEI
    SRC = skoytetrase
    VAL_ATTR = skoytetrase
    DIRECTION = Forward (Source To Destination)
    LUT = f,NEI,t,JA
    -> SOSIfile_AttributeCreator
Note: Legger til en del attributter: / - SosiFile: settes til verdien av parameter SOSI_FILE og brukes til 'fanout' på datafil / for å kunne klare å henvise til $[FME_SERVER_OUTPUT_DIR] / - dataeier: settes til "Statens kartverk - Miljødirektoratet" og kan benyttes videre. / - fylkesnr: inneholder fylkesnummeret for objektet / - komm: tilsvarer fylkesnr, men denne inneholder kommunenummer
SOSIfile_AttributeCreator: AttributeCreator
    ATTR_LIST = sosifile,"FME_CONDITIONAL:DEFAULT_VALUE'Friluftsliv_$(OUTPUT_EPSG_CODE)_$(SOSI_FILE)_SOSI'BOOL_OP;OR;COMPOSITE_TEST;<Unused>;TEST $(FANOUT) LIKE Kommuner'Friluftsliv_@PadLeft(@Value(kommuneid),4,0)_@Value(knavn)_$(OUTPUT_EPSG_CODE)_$(SOSI_FILE)_SOSI'BOOL_OP;OR;COMPOSITE_TEST;<Unused>;TEST $(FANOUT) LIKE Fylker'Friluftsliv_@PadLeft(@Value(fylkeid),2,0)_@Value(fnavn)_$(OUTPUT_EPSG_CODE)_$(SOSI_FILE)_SOSI'BOOL_OP;OR;COMPOSITE_TEST;<Unused>;TEST $(FANOUT) LIKE Norge'Friluftsliv_0000_Norge_$(OUTPUT_EPSG_CODE)_$(SOSI_FILE)_SOSI'FME_NUM_CONDITIONS4___",dataeier,Statens kartverk - Miljødirektoratet,fylkesnr,@Value(fylkeid),komm,"FME_CONDITIONAL:DEFAULT_VALUE'@PadLeft(@Value(kommuneid),4,0)'BOOL_OP;OR;COMPOSITE_TEST;<Unused>;TEST kommuneid ATTRIBUTE_IS_MISSING _FME_BLANK_STRING_'FME_NULL_VALUE'FME_NUM_CONDITIONS2___"
    -> FeatureTypeFilter
FeatureTypeFilter
    ATTRIBUTES = turogfriluftsruter.annenrute,turogfriluftsruter.fotrute,turogfriluftsruter.friluftslivtilrettelegging,turogfriluftsruter.skiloype,turogfriluftsruter.sykkelrute,<BLANK>,<UNFILTERED>
    turogfriluftsruter.friluftslivtilrettelegging -> turogfriluftsruter.friluftslivtilrettelegging (writer SOSI_1)
    turogfriluftsruter.annenrute -> Annenrute_tilgjengelighetsgruppe_FeatureMerger [input 1]
    turogfriluftsruter.fotrute -> Fotrute_tilgjengelighetsgruppe_FeatureMerger [input 1]
    turogfriluftsruter.skiloype -> Skiloype_opparbeiding_FeatureMerger [input 1]
    turogfriluftsruter.sykkelrute -> Sykkelrute_opparbeiding_FeatureMerger [input 1]

Bookmark: Fylke og/eller kommune clippers
admingrense.fylkeflate (reader POSTGIS_1)
    attributes: fylkeid int4, navn varchar(80)
    -> FylkesnavnRenamer
FylkesnavnRenamer: AttributeRenamer
    ATTR_LIST = navn,fnavn,
    -> HeleNorge_AttributeCreator
    -> Fylkeid_Tester
HeleNorge_AttributeCreator: AttributeCreator
    ATTR_LIST = _clippercoords,$(CLIPPERCOORDS),_clipper_file,$(CLIPPER_FILE),_fnr,$(FNR),_knr,$(KNR)
    -> HeleNorge_Tester
HeleNorge_Tester: Tester
    BOOL_OP = AND
    TEST_MODE = Automatic
    TEST_CLAUSE:
      TEST _clipper_file ATTRIBUTE_IS_EMPTY ""
      TEST _clippercoords ATTRIBUTE_IS_EMPTY ""
      TEST _fnr ATTRIBUTE_IS_EMPTY ""
      TEST _knr ATTRIBUTE_IS_EMPTY ""
    TEST_DESCRIPTION = ""
    PASSED -> AdminFlateReprojector
Fylkeid_Tester: Tester
    BOOL_OP = OR
    TEST_MODE = Automatic
    TEST_CLAUSE = TEST @Value(fylkeid) IN $(FNR)
    TEST_DESCRIPTION = ""
    PASSED -> AdminFlateReprojector
admingrense.kommuneflate (reader POSTGIS_1)
    attributes: kommuneid int4, navn varchar(80)
    -> KommuneNavnRenamer
KommuneNavnRenamer: AttributeRenamer
    ATTR_LIST = navn,knavn,
    -> kommuneid_Tester
kommuneid_Tester: Tester
    BOOL_OP = OR
    TEST_MODE = Automatic
    TEST_CLAUSE = TEST @Value(kommuneid) IN $(KNR)
    TEST_DESCRIPTION = ""
    PASSED -> AdminFlateReprojector
AdminFlateReprojector: Reprojector
    SOURCE = Read from feature
    RASTER_CELL_SIZE = Preserve Cells
    DEST = EPSG:4258
    INTERPOLATION_TYPE_NAME = Nearest Neighbor
    REPROJECTED -> Clipper [input 1]

Bookmark: Clipper file (any format)
Creator
    GEOMTYPE = Geometry Object
    NUM = 1
    CREATED -> ClipperFile_FeatureReader
ClipperFile_FeatureReader: FeatureReader
    COMBINE_GEOM = Use Result
    FORMAT = GENERIC
    INTERACT = <No Spatial Filter>
    GENERIC_REAL_FORMAT = GUESS_FROM_EXTENSION
    DATASET = $(CLIPPER_FILE)
    OUTPUT_FEATURES_DISPLAY = Based on Connections
    ATTR_ACCUM_MODE = Only Use Result
    FEATURETYPES_RADIO = FEATURETYPES
    ATTRIBUTES = NewFeatureType,
    <OTHER> -> ClipperFileReprojector
ClipperFileReprojector: Reprojector
    SOURCE = Read from feature
    RASTER_CELL_SIZE = Preserve Cells
    DEST = EPSG:4258
    INTERPOLATION_TYPE_NAME = Nearest Neighbor
    REPROJECTED -> Clipper [input 1]

Bookmark: PostGIS kildedata
turogfriluftsruter.skiloype (reader POSTGIS_2)
    attributes: objid int4,PRIKEY, objtype varchar(32), spes_skiloypetype varchar(80), preparering varchar(80), ryddebredde varchar(80), antallskispor int4, skoytetrase bool, vedlikeh varchar(80), frilufteierforhold varchar(80), belysning varchar(80), rutemerking varchar(80), skilting bool, rutefolger varchar(80), rutebredde varchar(80), opparbeiding varchar(80), rutebetydning varchar(80), rutevanskelighetsgrad varchar(80), underlagstype varchar(80), lengde int4, stigning int4, tilgjengelighetsgruppe varchar(80), rutetype varchar(80), navn varchar(80), rutenr varchar(80), lokalid uuid,PRIKEY, datafangstdato timestamp, oppdateringsdato timestamp, malemetode varchar(80), noyaktighet int4, synbarhet varchar(80),
      malemetodehoyde varchar(80), h_noyaktighet int4, opphav varchar(80), kommune varchar(80), informasjon varchar(80), link varchar(80)
    -> ClipperAttributeCreator
turogfriluftsruter.sykkelrute (reader POSTGIS_2)
    attributes: objid int4,PRIKEY, objtype varchar(32), spesialsykkelrutetype varchar(80), trafikkbelastning varchar(80), vedlikeh varchar(80), frilufteierforhold varchar(80), belysning varchar(80), rutemerking varchar(80), skilting bool, rutefolger varchar(80), rutebredde varchar(80), opparbeiding varchar(80), rutebetydning varchar(80), rutevanskelighetsgrad varchar(80), underlagstype varchar(80), lengde int4, stigning int4, tilgjengelighetsgruppe varchar(80), rutetype varchar(80), navn varchar(80), rutenr varchar(80), lokalid uuid,PRIKEY, datafangstdato timestamp, oppdateringsdato timestamp, malemetode varchar(80), noyaktighet int4, synbarhet varchar(80), malemetodehoyde varchar(80), h_noyaktighet int4, opphav varchar(80),
      kommune varchar(80), informasjon varchar(80), link varchar(80)
    -> ClipperAttributeCreator
turogfriluftsruter.friluftslivtilrettelegging (reader POSTGIS_2)
    attributes: objid int4,PRIKEY, objtype varchar(32), vedlikeh varchar(80), fritilrettelegging varchar(80), lokalid uuid,PRIKEY, datafangstdato timestamp, oppdateringsdato timestamp, malemetode varchar(80), noyaktighet int4, synbarhet varchar(80), malemetodehoyde varchar(80), h_noyaktighet int4, opphav varchar(80), kommune varchar(80), informasjon varchar(80), link varchar(80)
    -> ClipperAttributeCreator
turogfriluftsruter.fotrute (reader POSTGIS_2)
    attributes: objid int4,PRIKEY, objtype varchar(32), sfotrutetype varchar(80), sesong varchar(80), vedlikeh varchar(80), frilufteierforhold varchar(80), belysning varchar(80), rutemerking varchar(80), skilting bool, rutefolger varchar(80), rutebredde varchar(80), opparbeiding varchar(80), rutebetydning varchar(80), rutevanskelighetsgrad varchar(80), underlagstype varchar(80), lengde int4, stigning int4, tilgjengelighetsgruppe varchar(80), rutetype varchar(80), navn varchar(80), rutenr varchar(80), lokalid uuid,PRIKEY, datafangstdato timestamp, oppdateringsdato timestamp, malemetode varchar(80), noyaktighet int4, synbarhet varchar(80), malemetodehoyde varchar(80), h_noyaktighet int4, opphav varchar(80),
      kommune varchar(80), informasjon varchar(80), link varchar(80)
    -> ClipperAttributeCreator
turogfriluftsruter.annenrute (reader POSTGIS_2)
    attributes: objid int4,PRIKEY, objtype varchar(32), arutetype varchar(80), vedlikeh varchar(80), frilufteierforhold varchar(80), belysning varchar(80), rutemerking varchar(80), skilting bool, rutefolger varchar(80), rutebredde varchar(80), opparbeiding varchar(80), rutebetydning varchar(80), rutevanskelighetsgrad varchar(80), underlagstype varchar(80), lengde int4, stigning int4, tilgjengelighetsgruppe varchar(80), rutetype varchar(80), navn varchar(80), rutenr varchar(80), lokalid uuid,PRIKEY, datafangstdato timestamp, oppdateringsdato timestamp, malemetode varchar(80), noyaktighet int4, synbarhet varchar(80), malemetodehoyde varchar(80), h_noyaktighet int4, opphav varchar(80), kommune varchar(80),
      informasjon varchar(80), link varchar(80)
    -> ClipperAttributeCreator

Bookmark: Måldata SOSI
turogfriluftsruter.friluftslivtilrettelegging (writer SOSI_1)
    attributes: objid SOSI_int32, objtype SOSI_varchar(32), vedlikeh SOSI_varchar(80), fritilrettelegging SOSI_varchar(80), lokalid SOSI_buffer, datafangstdato SOSI_datetime, oppdateringsdato SOSI_datetime, malemetode SOSI_varchar(80), noyaktighet SOSI_int32, synbarhet SOSI_varchar(80), malemetodehoyde SOSI_varchar(80), h_noyaktighet SOSI_int32, opphav SOSI_varchar(80), kommune SOSI_varchar(80), informasjon SOSI_varchar(80), link SOSI_varchar(80)
turogfriluftsruter.annenrute (writer SOSI_1)
    attributes: objid SOSI_int32, objtype SOSI_varchar(32), arutetype SOSI_varchar(80), vedlikeh SOSI_varchar(80), frilufteierforhold SOSI_varchar(80), belysning SOSI_varchar(80), rutemerking SOSI_varchar(80), skilting SOSI_boolean, rutefolger SOSI_varchar(80), rutebredde SOSI_varchar(80), _ar_list_opparbeiding{}.opparbeiding SOSI_varchar(80), rutebetydning SOSI_varchar(80), rutevanskelighetsgrad SOSI_varchar(80), underlagstype SOSI_varchar(80), lengde SOSI_int32, stigning SOSI_int32, _ar_list_tilgjengelighetsgruppe{}.tilgjengelighetsgruppe SOSI_varchar(80), rutetype SOSI_varchar(80), navn SOSI_varchar(80), rutenr SOSI_varchar(80), lokalid SOSI_buffer, datafangstdato SOSI_datetime, oppdateringsdato SOSI_datetime, malemetode SOSI_varchar(80), noyaktighet SOSI_int32, synbarhet SOSI_varchar(80), malemetodehoyde SOSI_varchar(80), h_noyaktighet SOSI_int32, opphav SOSI_varchar(80), kommune SOSI_varchar(80),
      informasjon SOSI_varchar(80), link SOSI_varchar(80)
turogfriluftsruter.fotrute (writer SOSI_1)
    attributes: objid SOSI_int32, objtype SOSI_varchar(32), _fr_list_sfotrutetype{}.sfotrutetype SOSI_varchar(80), sesong SOSI_varchar(80), vedlikeh SOSI_varchar(80), frilufteierforhold SOSI_varchar(80), belysning SOSI_varchar(80), rutemerking SOSI_varchar(80), skilting SOSI_boolean, rutefolger SOSI_varchar(80), rutebredde SOSI_varchar(80), _fr_list_opparbeiding{}.opparbeiding SOSI_varchar(80), rutebetydning SOSI_varchar(80), rutevanskelighetsgrad SOSI_varchar(80), underlagstype SOSI_varchar(80), lengde SOSI_int32, stigning SOSI_int32, _fr_list_tilgjengelighetsgruppe{}.tilgjengelighetsgruppe SOSI_varchar(80), rutetype SOSI_varchar(80), navn SOSI_varchar(80), rutenr SOSI_varchar(80), lokalid SOSI_buffer, datafangstdato SOSI_datetime, oppdateringsdato SOSI_datetime, malemetode SOSI_varchar(80), noyaktighet SOSI_int32, synbarhet SOSI_varchar(80), malemetodehoyde SOSI_varchar(80), h_noyaktighet SOSI_int32, opphav SOSI_varchar(80),
      kommune SOSI_varchar(80), informasjon SOSI_varchar(80), link SOSI_varchar(80)
turogfriluftsruter.skiloype (writer SOSI_1)
    attributes: objid SOSI_int32, objtype SOSI_varchar(32), spes_skiloypetype SOSI_varchar(80), preparering SOSI_varchar(80), ryddebredde SOSI_varchar(80), antallskispor SOSI_int32, skoytetrase SOSI_boolean, vedlikeh SOSI_varchar(80), frilufteierforhold SOSI_varchar(80), belysning SOSI_varchar(80), rutemerking SOSI_varchar(80), skilting SOSI_boolean, rutefolger SOSI_varchar(80), rutebredde SOSI_varchar(80), _sl_list_opparbeiding{}.opparbeiding SOSI_varchar(80), rutebetydning SOSI_varchar(80), rutevanskelighetsgrad SOSI_varchar(80), underlagstype SOSI_varchar(80), lengde SOSI_int32, stigning SOSI_int32, _sl_list_tilgjengelighetsgruppe{}.tilgjengelighetsgruppe SOSI_varchar(80), rutetype SOSI_varchar(80), navn SOSI_varchar(80), rutenr SOSI_varchar(80), lokalid SOSI_buffer, datafangstdato SOSI_datetime, oppdateringsdato SOSI_datetime, malemetode SOSI_varchar(80), noyaktighet SOSI_int32, synbarhet SOSI_varchar(80),
      malemetodehoyde SOSI_varchar(80), h_noyaktighet SOSI_int32, opphav SOSI_varchar(80), kommune SOSI_varchar(80), informasjon SOSI_varchar(80), link SOSI_varchar(80)
turogfriluftsruter.sykkelrute (writer SOSI_1)
    attributes: objid SOSI_int32, objtype SOSI_varchar(32), spesialsykkelrutetype SOSI_varchar(80), trafikkbelastning SOSI_varchar(80), vedlikeh SOSI_varchar(80), frilufteierforhold SOSI_varchar(80), belysning SOSI_varchar(80), rutemerking SOSI_varchar(80), skilting SOSI_boolean, rutefolger SOSI_varchar(80), rutebredde SOSI_varchar(80), _sr_list_opparbeiding{}.opparbeiding SOSI_varchar(80), rutebetydning SOSI_varchar(80), rutevanskelighetsgrad SOSI_varchar(80), underlagstype SOSI_varchar(80), lengde SOSI_int32, stigning SOSI_int32, _sr_list_tilgjengelighetsgruppe{}.tilgjengelighetsgruppe SOSI_varchar(80), rutetype SOSI_varchar(80), navn SOSI_varchar(80), rutenr SOSI_varchar(80), lokalid SOSI_buffer, datafangstdato SOSI_datetime, oppdateringsdato SOSI_datetime, malemetode SOSI_varchar(80), noyaktighet SOSI_int32, synbarhet SOSI_varchar(80), malemetodehoyde SOSI_varchar(80), h_noyaktighet SOSI_int32, opphav SOSI_varchar(80),
      kommune SOSI_varchar(80), informasjon SOSI_varchar(80), link SOSI_varchar(80)

Bookmark: Annenrute koblingstabeller
turogfriluftsruter.annenrute_opparbeiding (reader POSTGRES_1)
    attributes: objid int4,PRIKEY, opparbeiding int4
    -> Annenrute_opparbeiding_FeatureMerger [input 2]
turogfriluftsruter.annenrute_tilgjengelighetsgruppe (reader POSTGRES_1)
    attributes: objid int4,PRIKEY, tilgjengelighetsgruppe int4
    -> Annenrute_tilgjengelighetsgruppe_FeatureMerger [input 2]

Bookmark: Joiner inn felter med [0..*] multiplisitet for Annenrute
Annenrute_tilgjengelighetsgruppe_FeatureMerger: FeatureMerger
    IGNORE_NULLS = No
    JOIN_KEYS = @Value(objid) @Value(objid) NUM
    SUPPLIERS_FIRST = No
    MERGE_TYPE = Attributes Only
    ATTR_ACCUM_MODE = Merge Supplier
    ATTR_CONFLICT_RES = Use Requestor
    PROCESS_DUPS = No
    LIST_NAME = _ar_list_tilgjengelighetsgruppe
    MERGED -> Annenrute_opparbeiding_FeatureMerger [input 1]
    NOT_MERGED -> Annenrute_opparbeiding_FeatureMerger [input 1]
Annenrute_opparbeiding_FeatureMerger: FeatureMerger
    IGNORE_NULLS = No
    JOIN_KEYS = @Value(objid) @Value(objid) NUM
    SUPPLIERS_FIRST = No
    MERGE_TYPE = Attributes Only
    ATTR_ACCUM_MODE = Merge Supplier
    ATTR_CONFLICT_RES = Use Requestor
    PROCESS_DUPS = No
    LIST_NAME = _ar_list_opparbeiding
    MERGED -> turogfriluftsruter.annenrute (writer SOSI_1)
    NOT_MERGED -> turogfriluftsruter.annenrute (writer SOSI_1)

Bookmark: Fotrute koblingstabeller
turogfriluftsruter.fotrute_opparbeiding (reader POSTGRES_1)
    attributes: objid int4,PRIKEY, opparbeiding int4
    -> _fr_opparbeiding_FeatureMerger [input 2]
turogfriluftsruter.fotrute_sfotrutetype (reader POSTGRES_1)
    attributes: objid int4,PRIKEY, sfotrutetype varchar(80)
    -> _fr_sfotrutetype_FeatureMerger [input 2]
turogfriluftsruter.fotrute_tilgjengelighetsgruppe (reader POSTGRES_1)
    attributes: objid int4,PRIKEY, tilgjengelighetsgruppe int4
    -> Fotrute_tilgjengelighetsgruppe_FeatureMerger [input 2]

Bookmark: Joiner inn felter med [0..*] multiplisitet for Fotruter
Fotrute_tilgjengelighetsgruppe_FeatureMerger: FeatureMerger
    IGNORE_NULLS = No
    JOIN_KEYS = @Value(objid) @Value(objid) NUM
    SUPPLIERS_FIRST = No
    MERGE_TYPE = Attributes Only
    ATTR_ACCUM_MODE = Merge Supplier
    ATTR_CONFLICT_RES = Use Requestor
    PROCESS_DUPS = No
    LIST_NAME = _fr_list_tilgjengelighetsgruppe
    MERGED -> _fr_sfotrutetype_FeatureMerger [input 1]
    NOT_MERGED -> _fr_sfotrutetype_FeatureMerger [input 1]
_fr_sfotrutetype_FeatureMerger: FeatureMerger
    IGNORE_NULLS = No
    JOIN_KEYS = @Value(objid) @Value(objid) NUM
    SUPPLIERS_FIRST = No
    MERGE_TYPE = Attributes Only
    ATTR_ACCUM_MODE = Merge Supplier
    ATTR_CONFLICT_RES = Use Requestor
    PROCESS_DUPS = No
    LIST_NAME = _fr_list_sfotrutetype
    MERGED -> _fr_opparbeiding_FeatureMerger [input 1]
    NOT_MERGED -> _fr_opparbeiding_FeatureMerger [input 1]
_fr_opparbeiding_FeatureMerger: FeatureMerger
    IGNORE_NULLS = No
    JOIN_KEYS = @Value(objid) @Value(objid) NUM
    SUPPLIERS_FIRST = No
    MERGE_TYPE = Attributes Only
    ATTR_ACCUM_MODE = Merge Supplier
    ATTR_CONFLICT_RES = Use Requestor
    PROCESS_DUPS = No
    LIST_NAME = _fr_list_opparbeiding
    MERGED -> turogfriluftsruter.fotrute (writer SOSI_1)
    NOT_MERGED -> turogfriluftsruter.fotrute (writer SOSI_1)

Bookmark: Skiloype koblingstabeller
turogfriluftsruter.skiloype_opparbeiding (reader POSTGRES_1)
    attributes: objid int4,PRIKEY, opparbeiding int4
    -> Skiloype_opparbeiding_FeatureMerger [input 2]
turogfriluftsruter.skiloype_tilgjengelighetsgruppe (reader POSTGRES_1)
    attributes: objid int4,PRIKEY, tilgjengelighetsgruppe int4
    -> Skiloype_tilghengelighetsgruppe_FeatureMerger [input 2]

Bookmark: Joiner inn felter med [0..*] multiplisitet for Skiløype
Skiloype_opparbeiding_FeatureMerger: FeatureMerger
    IGNORE_NULLS = No
    JOIN_KEYS = @Value(objid) @Value(objid) NUM
    SUPPLIERS_FIRST = No
    MERGE_TYPE = Attributes Only
    ATTR_ACCUM_MODE = Merge Supplier
    ATTR_CONFLICT_RES = Use Requestor
    PROCESS_DUPS = No
    LIST_NAME = _sl_list_opparbeiding
    MERGED -> Skiloype_tilghengelighetsgruppe_FeatureMerger [input 1]
    NOT_MERGED -> Skiloype_tilghengelighetsgruppe_FeatureMerger [input 1]
Skiloype_tilghengelighetsgruppe_FeatureMerger: FeatureMerger
    IGNORE_NULLS = No
    JOIN_KEYS = @Value(objid) @Value(objid) STRING
    SUPPLIERS_FIRST = No
    MERGE_TYPE = Attributes Only
    ATTR_ACCUM_MODE = Merge Supplier
    ATTR_CONFLICT_RES = Use Requestor
    PROCESS_DUPS = No
    LIST_NAME = _sl_list_tilgjengelighetsgruppe
    MERGED -> turogfriluftsruter.skiloype (writer SOSI_1)
    NOT_MERGED -> turogfriluftsruter.skiloype (writer SOSI_1)

Bookmark: Sykkelrute koblingstabeller
turogfriluftsruter.sykkelrute_opparbeiding (reader POSTGRES_1)
    attributes: objid int4,PRIKEY, opparbeiding int4
    -> Sykkelrute_opparbeiding_FeatureMerger [input 2]
turogfriluftsruter.sykkelrute_tilgjengelighetsgruppe (reader POSTGRES_1)
    attributes: objid int4,PRIKEY, tilgjengelighetsgruppe int4
    -> Sykkelrute_tilgjengelighetsgruppe_FeatureMerger [input 2]

Bookmark: Joiner inn felter med [0..*] multiplisitet for Sykkelrute
Sykkelrute_opparbeiding_FeatureMerger: FeatureMerger
    IGNORE_NULLS = No
    JOIN_KEYS = @Value(objid) @Value(objid) NUM
    SUPPLIERS_FIRST = No
    MERGE_TYPE = Attributes Only
    ATTR_ACCUM_MODE = Merge Supplier
    ATTR_CONFLICT_RES = Use Requestor
    PROCESS_DUPS = No
    LIST_NAME = _sr_list_opparbeiding
    MERGED -> Sykkelrute_tilgjengelighetsgruppe_FeatureMerger [input 1]
    NOT_MERGED -> Sykkelrute_tilgjengelighetsgruppe_FeatureMerger [input 1]
Sykkelrute_tilgjengelighetsgruppe_FeatureMerger: FeatureMerger
    IGNORE_NULLS = No
    JOIN_KEYS = @Value(objid) @Value(objid) NUM
    SUPPLIERS_FIRST = No
    MERGE_TYPE = Attributes Only
    ATTR_ACCUM_MODE = Merge Supplier
    ATTR_CONFLICT_RES = Use Requestor
    PROCESS_DUPS = No
    LIST_NAME = _sr_list_tilgjengelighetsgruppe
    MERGED -> turogfriluftsruter.sykkelrute (writer SOSI_1)
    NOT_MERGED -> turogfriluftsruter.sykkelrute (writer SOSI_1)

FME custom transformer CreateClipper

Parameters:
- CLIPPERCOORDS = 253577 6650999 253577 6651246 253763 6651246 253763 6650999 253577 6650999   # Clipper Coordinate List
- CLIPPERCOORDSYS = EPSG:25833   # Clipper Coordinate System
- DESTCOORDSYS = "ESRIWKT|ETRS_1989_UTM_Zone_35N|PROJCS["ETRS_1989_UTM_Zone_35N",GEOGCS["GCS_ETRS_1989",DATUM["D_ETRS_1989",SPHEROID["GRS_1980",6378137.0,298.257222101]],PRIMEM["Greenwich",0.0],UNIT["Degree",0.0174532925199433]],PROJECTION["Transverse_Mercator"],PARAMETER["False_Easting",500000.0],PARAMETER["False_Northing",0.0],PARAMETER["Central_Meridian",27.0],PARAMETER["Scale_Factor",0.9996],PARAMETER["Latitude_Of_Origin",0.0],UNIT["Meter",1.0]]"   # Destination Coordinate System

Note: Creating geometry from / the Clipper coords
Creator
    GEOMTYPE = 2D Coordinate List
    COORDSYS = $(CLIPPERCOORDSYS)
    NUM = 1
    COORDS = $(CLIPPERCOORDS)
    CREATED -> BoundingBoxAccumulator
Note: Calculating the bounding / box (envelope) from the geometry
BoundingBoxAccumulator
    TOPFER_INDEX = No
    BOUNDING_BOX -> SpatialFilter [input 1]
    ORIGINAL -> SpatialFilter [input 2]
Note: If the geometry is equal to its / own bounding box - it is a rectangle!
SpatialFilter
    PREDATTR = _predicate
    MERGE_ATTRS = No
    PREDICATES = EQUALS
    BASE_TYPE = Single Base
    PASS_CRITERIA = Pass Against One Base
    CURVE_BOUNDARY_RULE_PARAM = Default Rule
    USE_BOUNDING_BOX = No
    PASSED -> Reprojector
    FAILED -> Reprojector_2
Note: If rectangle, reproject the / geometry to the destination / coordinate system
Reprojector
    SOURCE = Read from feature
    STROKE_ARCS = Yes
    RASTER_CELL_SIZE = Preserve Cells
    DEST = $(DESTCOORDSYS)
    INTERPOLATION_TYPE_NAME = Nearest Neighbor
    REPROJECTED -> BoundingBoxAccumulator_2
Note: Then calculate the bounding / box from the projected geoemtry
BoundingBoxAccumulator_2
    TOPFER_INDEX = No
    BOUNDING_BOX -> Reprojector_3
Note: Reproject the geometry back to / the DB coordsys (LL/EUREF89)
Reprojector_3
    SOURCE = Read from feature
    STROKE_ARCS = Yes
    RASTER_CELL_SIZE = Preserve Cells
    DEST = EPSG:4258
    INTERPOLATION_TYPE_NAME = Nearest Neighbor
    REPROJECTED -> GeometryFilter
Note: Reproject clipper to / the DB coordsys (LL/EUREF89)
Reprojector_2
    SOURCE = Read from feature
    STROKE_ARCS = Yes
    RASTER_CELL_SIZE = Preserve Cells
    DEST = EPSG:4258
    INTERPOLATION_TYPE_NAME = Nearest Neighbor
    REPROJECTED -> GeometryFilter
Note: Getting rid of dummies
GeometryFilter
    GEOM_PORT_NAMES = Area
    BREAK_AGG = No
    AREA -> reprojectBboxESRI_REPROJECTED_2 (output)
    <UNFILTERED> -> reprojectBboxESRI_REPROJECTED_2 (output)
reprojectBboxESRI_REPROJECTED_2 (output)
