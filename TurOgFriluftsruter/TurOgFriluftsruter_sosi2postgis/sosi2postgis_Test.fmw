FME workspace sosi2postgis_Test.fmw

Parameters:
- SourceDataset_SOSI = D:\LokaleDatakopier\Friluftsruter_84.sos   # Source SOSI File
- DestDataset_POSTGIS = geonorutv@localhost:5432/geonorutv   # Connection

Readers:
- SOSI_1: SOSI from $(SourceDataset_SOSI)

Writers:
- POSTGIS_1: POSTGIS to $(DestDataset_POSTGIS)

AnnenRute (reader SOSI_1)
    attributes: SOSI_id SOSI_int32, RUTEMERKING SOSI_char(3), DATAFANGSTDATO SOSI_datetime, KOBLING_ID SOSI_char(255), NOYAKTIGHET SOSI_number(6,0), MALEMETODE SOSI_int16, SKILTING SOSI_char(3), VEDLIKEH SOSI_char(35), NAVN SOSI_char(60), RUTENR SOSI_char(100), OPPHAV SOSI_char(255), INFORMASJON SOSI_char(255), ARUTETYPE SOSI_char(50), OBJTYPE SOSI_char(32), OPPDATERINGSDATO SOSI_datetime
    -> AnnenRute (writer POSTGIS_1)
AnnenRute (writer POSTGIS_1)
    attributes: sosi_id int4, rutemerking char(3), datafangstdato time, kobling_id char(255), noyaktighet numeric(6,0), malemetode int2, skilting char(3), vedlikeh char(35), navn char(60), rutenr char(100), opphav char(255), informasjon char(255), arutetype char(50), objtype char(32), oppdateringsdato time
Fotrute (reader SOSI_1)
    attributes: SOSI_id SOSI_int32, RUTEMERKING SOSI_char(3), LINK SOSI_char(255), DATAFANGSTDATO SOSI_datetime, H_MALEMETODE SOSI_int16, KOBLING_ID SOSI_char(255), TRAFIKKBELASTNING SOSI_int16, NOYAKTIGHET SOSI_number(6,0), TILGJENGELIGHETSGRUPPE SOSI_int16, SYNBARHET SOSI_int16, STATUS SOSI_char(2), MEDIUM SOSI_char(1), OPPARBEIDING SOSI_int16, RUTETYPE SOSI_int16, KOMM SOSI_char(4), MALEMETODE SOSI_int16, SKILTING SOSI_char(3), VEDLIKEH SOSI_char(35), SOSI_guid SOSI_char(36), NAVN SOSI_char(60), RUTEBETYDNING SOSI_int16, UNDERLAGSTYPE SOSI_int16, RUTENR SOSI_char(100), OPPHAV SOSI_char(255), FRILUFTEIERFORHOLD SOSI_int16, SESONG SOSI_char(25), INFORMASJON SOSI_char(255), SFOTRUTETYPE SOSI_char(2), RUTEFOLGER SOSI_char(2), OBJTYPE SOSI_char(32),
      H_NOYAKTIGHET SOSI_number(6,0), OPPDATERINGSDATO SOSI_datetime, BELYSNING SOSI_int16, RUTEBREDDE SOSI_int16, STIGNING SOSI_int16, RUTEVANSKELIGHETSGRAD SOSI_char(25)
    -> Fotrute (writer POSTGIS_1)
Fotrute (writer POSTGIS_1)
    attributes: sosi_id int4, rutemerking char(3), link char(255), datafangstdato time, h_malemetode int2, kobling_id char(255), trafikkbelastning int2, noyaktighet numeric(6,0), tilgjengelighetsgruppe int2, synbarhet int2, status char(2), medium char(1), opparbeiding int2, rutetype int2, komm char(4), malemetode int2, skilting char(3), vedlikeh char(35), sosi_guid char(36), navn char(60), rutebetydning int2, underlagstype int2, rutenr char(100), opphav char(255), frilufteierforhold int2, sesong char(25), informasjon char(255), sfotrutetype char(2), rutefolger char(2), objtype char(32),
      h_noyaktighet numeric(6,0), oppdateringsdato time, belysning int2, rutebredde int2, stigning int2, rutevanskelighetsgrad char(25)
FriluftslivTilrettelegging (reader SOSI_1)
    attributes: SOSI_id SOSI_int32, LINK SOSI_char(255), DATAFANGSTDATO SOSI_datetime, KOBLING_ID SOSI_char(255), NOYAKTIGHET SOSI_number(6,0), SYNBARHET SOSI_int16, KOMM SOSI_char(4), MALEMETODE SOSI_int16, FRITILRETTELEGGING SOSI_int16, VEDLIKEH SOSI_char(35), OPPHAV SOSI_char(255), INFORMASJON SOSI_char(255), OBJTYPE SOSI_char(32), OPPDATERINGSDATO SOSI_datetime, ID SOSI_char(70)
    -> FriluftslivTilrettelegging (writer POSTGIS_1)
FriluftslivTilrettelegging (writer POSTGIS_1)
    attributes: sosi_id int4, link char(255), datafangstdato time, kobling_id char(255), noyaktighet numeric(6,0), synbarhet int2, komm char(4), malemetode int2, fritilrettelegging int2, vedlikeh char(35), opphav char(255), informasjon char(255), objtype char(32), oppdateringsdato time, id char(70)
SFOTRUTETYPE_SOSI (reader SOSI_1)
    attributes: SFOTRUTETYPE SOSI_char(2), SOSI_parent_guid SOSI_char(36)
    -> SFOTRUTETYPE_SOSI (writer POSTGIS_1)
SFOTRUTETYPE_SOSI (writer POSTGIS_1)
    attributes: sfotrutetype char(2), sosi_parent_guid char(36)
OPPARBEIDING_SOSI (reader SOSI_1)
    attributes: OPPARBEIDING SOSI_int16, SOSI_parent_guid SOSI_char(36)
    -> OPPARBEIDING_SOSI (writer POSTGIS_1)
OPPARBEIDING_SOSI (writer POSTGIS_1)
    attributes: opparbeiding int2, sosi_parent_guid char(36)
STATUS_SOSI (reader SOSI_1)
    attributes: STATUS SOSI_char(2), SOSI_parent_guid SOSI_char(36)
    -> STATUS_SOSI (writer POSTGIS_1)
STATUS_SOSI (writer POSTGIS_1)
    attributes: status char(2), sosi_parent_guid char(36)
Sykkelrute (reader SOSI_1)
    attributes: SOSI_id SOSI_int32, RUTEMERKING SOSI_char(3), DATAFANGSTDATO SOSI_datetime, H_MALEMETODE SOSI_int16, KOBLING_ID SOSI_char(255), SPESIALSYKKELRUTETYPE SOSI_char(100), NOYAKTIGHET SOSI_number(6,0), TILGJENGELIGHETSGRUPPE SOSI_int16, SYNBARHET SOSI_int16, KOMM SOSI_char(4), MALEMETODE SOSI_int16, SKILTING SOSI_char(3), VEDLIKEH SOSI_char(35), NAVN SOSI_char(60), UNDERLAGSTYPE SOSI_int16, RUTENR SOSI_char(100), OPPHAV SOSI_char(255), FRILUFTEIERFORHOLD SOSI_int16, INFORMASJON SOSI_char(255), RUTEFOLGER SOSI_char(2), OBJTYPE SOSI_char(32), H_NOYAKTIGHET SOSI_number(6,0), OPPDATERINGSDATO SOSI_datetime, BELYSNING SOSI_int16, RUTEVANSKELIGHETSGRAD SOSI_char(25)
    -> Sykkelrute (writer POSTGIS_1)
Sykkelrute (writer POSTGIS_1)
    attributes: sosi_id int4, rutemerking char(3), datafangstdato time, h_malemetode int2, kobling_id char(255), spesialsykkelrutetype char(100), noyaktighet numeric(6,0), tilgjengelighetsgruppe int2, synbarhet int2, komm char(4), malemetode int2, skilting char(3), vedlikeh char(35), navn char(60), underlagstype int2, rutenr char(100), opphav char(255), frilufteierforhold int2, informasjon char(255), rutefolger char(2), objtype char(32), h_noyaktighet numeric(6,0), oppdateringsdato time, belysning int2, rutevanskelighetsgrad char(25)
SOSI_RelationshipClasses (reader SOSI_1)
    attributes: FeatureClass SOSI_char(100), GeometryType SOSI_char(32), Table SOSI_char(100)
    -> SOSI_RelationshipClasses (writer POSTGIS_1)
SOSI_RelationshipClasses (writer POSTGIS_1)
    attributes: featureclass char(100), geometrytype char(32), table char(100)
Skiloype (reader SOSI_1)
    attributes: SOSI_id SOSI_int32, RUTEMERKING SOSI_char(3), DATAFANGSTDATO SOSI_datetime, H_MALEMETODE SOSI_int16, KOBLING_ID SOSI_char(255), NOYAKTIGHET SOSI_number(6,0), SYNBARHET SOSI_int16, OPPARBEIDING SOSI_int16, RYDDEBREDDE SOSI_int16, KOMM SOSI_char(4), SKOYTETRASE SOSI_char(3), SPES_SKILOYPETYPE SOSI_char(2), MALEMETODE SOSI_int16, SKILTING SOSI_char(3), VEDLIKEH SOSI_char(35), PREPARERING SOSI_char(3), NAVN SOSI_char(60), UNDERLAGSTYPE SOSI_int16, RUTENR SOSI_char(100), OPPHAV SOSI_char(255), FRILUFTEIERFORHOLD SOSI_int16, INFORMASJON SOSI_char(255), RUTEFOLGER SOSI_char(2), OBJTYPE SOSI_char(32), LOYPEPREPARERING SOSI_char(255), H_NOYAKTIGHET SOSI_number(6,0), OPPDATERINGSDATO SOSI_datetime, BELYSNING SOSI_int16, RUTEBREDDE SOSI_int16, RUTEVANSKELIGHETSGRAD SOSI_char(25)
    -> Skiloype (writer POSTGIS_1)
Skiloype (writer POSTGIS_1)
    attributes: sosi_id int4, rutemerking char(3), datafangstdato time, h_malemetode int2, kobling_id char(255), noyaktighet numeric(6,0), synbarhet int2, opparbeiding int2, ryddebredde int2, komm char(4), skoytetrase char(3), spes_skiloypetype char(2), malemetode int2, skilting char(3), vedlikeh char(35), preparering char(3), navn char(60), underlagstype int2, rutenr char(100), opphav char(255), frilufteierforhold int2, informasjon char(255), rutefolger char(2), objtype char(32), loypepreparering char(255), h_noyaktighet numeric(6,0), oppdateringsdato time, belysning int2, rutebredde int2, rutevanskelighetsgrad char(25)
