FME workspace TurOgFriluftsruter_sosi2postgis.fmw

Parameters:
- CONFIG_FILE:   # Python Script
      #-------------------------------------------------------------------------------
      # Name:        GetConfigFile
      # Purpose:
      #
      # Author:      xsunknu
      #
      # Created:     21.08.2015
      # Copyright:   (c) xsunknu 2015
      # Licence:     <your licence>
      #-------------------------------------------------------------------------------
      
      import os, fme
      
      fmwdir = fme.macroValues['FME_MF_DIR']
      fmwfile = fme.macroValues['FME_MF_NAME']
      
      fmwfile = os.path.join(fmwdir, fmwfile)
      configfile = os.path.splitext(fmwfile)[0] + '_config.xml'
      
      return configfile
- PG_DB:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgdb').text
      
      return value
- COORDSYS_OUT:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('sr').text
      
      return value
- SOSI_IN:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('sosiin').text
      
      return value
- LOG_FILE:   # Python Script
      #-------------------------------------------------------------------------------
      # Name:        GetConfigFile
      # Purpose:
      #
      # Author:      xsunknu
      #
      # Created:     21.08.2015
      # Copyright:   (c) xsunknu 2015
      # Licence:     <your licence>
      #-------------------------------------------------------------------------------
      
      import os, uuid, fme
      
      fmwdir = fme.macroValues['FME_MF_DIR']
      fmwfile = fme.macroValues['FME_MF_NAME']
      
      logdir = os.path.join(fmwdir, 'log')
      if not os.path.isdir(logdir):
          os.mkdir(logdir)
      
      logfile = os.path.splitext(fmwfile)[0] + '_' + str(uuid.uuid1()).replace('-','') + '.log'
      logfile = os.path.join(logdir, logfile)
      
      return logfile

Readers:
- SOSI_1: SOSI from $(SOSI_IN)

Writers:
- POSTGIS_1: POSTGIS to $(PG_DB) in $(COORDSYS_OUT)
- POSTGRES_1: POSTGRES to $(PG_DB)

Note: Håndeter relaterte data for attributter hvor multiplisiteten er satt lik [0..*]. / Disse attributtene må legges i egne tabeller koblet mot hovedtabellen.
Note: Fjerner unødvendige, midlertidige, felt
Mergers_AttributeRemover: AttributeRemover
    LIST_ATTRS = _list_opparbeiding{} _list_sfotrutetype{} _list_tilgjengelighetsgruppe{}
    REMOVE_ATTRS = _concatenated_opparbeiding,_concatenated_sfotrutetype,_concatenated_tilgjengelighetsgruppe,opparbeiding,sfotrutetype,sosi_parent_guid,tilgjengelighetsgruppe
    -> FeatureTypeFilter
Note: Splitter data for skriving basert på featuretype
FeatureTypeFilter
    ATTRIBUTES = <BLANK>,<UNFILTERED>,AnnenRute,Fotrute,FriluftslivTilrettelegging,Skiloype,Sykkelrute
    FriluftslivTilrettelegging -> turogfriluftsruter.friluftslivtilrettelegging (writer POSTGIS_1)
    AnnenRute -> ar_Opparbeiding_Tester
    Sykkelrute -> turogfriluftsruter.sykkelrute (writer POSTGIS_1)
    Skiloype -> turogfriluftsruter.skiloype (writer POSTGIS_1)
    Fotrute -> turogfriluftsruter.fotrute (writer POSTGIS_1)
    AnnenRute -> turogfriluftsruter.annenrute (writer POSTGIS_1)
    AnnenRute -> ar_tilretteleggingsgruppe_Tester
    Fotrute -> fr_Opparbeiding_Tester
    Fotrute -> fr_Sfotrutetype_Tester
    Fotrute -> fr_Tilgjengelighetsgruppe_Tester
    Skiloype -> sl_Opparbeiding_Tester
    Skiloype -> sl_Tilgjengelighetsgruppe_Tester
    Sykkelrute -> sr_Opparbeiding_Tester
    Sykkelrute -> sr_Tilgjengelighetsgruppe_Tester

Bookmark: SOSI-kildedata
AnnenRute (reader SOSI_1)
    attributes: SOSI_id SOSI_int32, RUTEMERKING SOSI_char(2), DATAFANGSTDATO SOSI_datetime, KOBLING_ID SOSI_char(255), NOYAKTIGHET SOSI_number(6,0), MALEMETODE SOSI_int16, SKILTING SOSI_char(3), VEDLIKEH SOSI_char(35), NAVN SOSI_char(60), RUTENR SOSI_char(100), OPPHAV SOSI_char(255), INFORMASJON SOSI_char(255), ARUTETYPE SOSI_char(50), OBJTYPE SOSI_char(32), OPPDATERINGSDATO SOSI_datetime
    -> BulkAttributeRenamer
Fotrute (reader SOSI_1)
    attributes: SOSI_id SOSI_int32, RUTEMERKING SOSI_char(2), LINK SOSI_char(255), DATAFANGSTDATO SOSI_datetime, H_MALEMETODE SOSI_int16, KOBLING_ID SOSI_char(255), TRAFIKKBELASTNING SOSI_int16, NOYAKTIGHET SOSI_number(6,0), TILGJENGELIGHETSGRUPPE SOSI_int16, SYNBARHET SOSI_int16, STATUS SOSI_char(2), MEDIUM SOSI_char(1), OPPARBEIDING SOSI_int16, RUTETYPE SOSI_int16, KOMM SOSI_char(4), MALEMETODE SOSI_int16, SKILTING SOSI_char(3), VEDLIKEH SOSI_char(35), SOSI_guid SOSI_char(36), NAVN SOSI_char(60), RUTEBETYDNING SOSI_int16, UNDERLAGSTYPE SOSI_int16, RUTENR SOSI_char(100), OPPHAV SOSI_char(255), FRILUFTEIERFORHOLD SOSI_int16, SESONG SOSI_char(25), INFORMASJON SOSI_char(255), SFOTRUTETYPE SOSI_char(2), RUTEFOLGER SOSI_char(2), OBJTYPE SOSI_char(32),
      H_NOYAKTIGHET SOSI_number(6,0), OPPDATERINGSDATO SOSI_datetime, BELYSNING SOSI_int16, RUTEBREDDE SOSI_int16, STIGNING SOSI_int16, RUTEVANSKELIGHETSGRAD SOSI_char(25)
    -> BulkAttributeRenamer
FriluftslivTilrettelegging (reader SOSI_1)
    attributes: SOSI_id SOSI_int32, LINK SOSI_char(255), DATAFANGSTDATO SOSI_datetime, KOBLING_ID SOSI_char(255), NOYAKTIGHET SOSI_number(6,0), SYNBARHET SOSI_int16, KOMM SOSI_char(4), MALEMETODE SOSI_int16, FRITILRETTELEGGING SOSI_int16, VEDLIKEH SOSI_char(35), OPPHAV SOSI_char(255), INFORMASJON SOSI_char(255), OBJTYPE SOSI_char(32), OPPDATERINGSDATO SOSI_datetime, ID SOSI_char(70)
    -> BulkAttributeRenamer
Skiloype (reader SOSI_1)
    attributes: SOSI_id SOSI_int32, RUTEMERKING SOSI_char(2), DATAFANGSTDATO SOSI_datetime, H_MALEMETODE SOSI_int16, KOBLING_ID SOSI_char(255), NOYAKTIGHET SOSI_number(6,0), SYNBARHET SOSI_int16, OPPARBEIDING SOSI_int16, RYDDEBREDDE SOSI_int16, KOMM SOSI_char(4), SKOYTETRASE SOSI_char(3), SPES_SKILOYPETYPE SOSI_char(2), MALEMETODE SOSI_int16, SKILTING SOSI_char(3), VEDLIKEH SOSI_char(35), PREPARERING SOSI_char(3), NAVN SOSI_char(60), UNDERLAGSTYPE SOSI_int16, RUTENR SOSI_char(100), OPPHAV SOSI_char(255), FRILUFTEIERFORHOLD SOSI_int16, INFORMASJON SOSI_char(255), RUTEFOLGER SOSI_char(2), OBJTYPE SOSI_char(32), H_NOYAKTIGHET SOSI_number(6,0), OPPDATERINGSDATO SOSI_datetime, BELYSNING SOSI_int16, RUTEBREDDE SOSI_int16, RUTEVANSKELIGHETSGRAD SOSI_char(25), ANTALLSKISPOR SOSI_int16
    -> BulkAttributeRenamer
Sykkelrute (reader SOSI_1)
    attributes: SOSI_id SOSI_int32, RUTEMERKING SOSI_char(2), DATAFANGSTDATO SOSI_datetime, H_MALEMETODE SOSI_int16, KOBLING_ID SOSI_char(255), SPESIALSYKKELRUTETYPE SOSI_char(100), NOYAKTIGHET SOSI_number(6,0), TILGJENGELIGHETSGRUPPE SOSI_int16, SYNBARHET SOSI_int16, KOMM SOSI_char(4), MALEMETODE SOSI_int16, SKILTING SOSI_char(3), VEDLIKEH SOSI_char(35), NAVN SOSI_char(60), UNDERLAGSTYPE SOSI_int16, RUTENR SOSI_char(100), OPPHAV SOSI_char(255), FRILUFTEIERFORHOLD SOSI_int16, INFORMASJON SOSI_char(255), RUTEFOLGER SOSI_char(2), OBJTYPE SOSI_char(32), H_NOYAKTIGHET SOSI_number(6,0), OPPDATERINGSDATO SOSI_datetime, BELYSNING SOSI_int16, RUTEVANSKELIGHETSGRAD SOSI_char(25)
    -> BulkAttributeRenamer
OPPARBEIDING_SOSI (reader SOSI_1)
    attributes: OPPARBEIDING SOSI_int16, SOSI_parent_guid SOSI_char(36)
    -> OPPARBEIDING_SOSI_BulkAttributeRenamer
SFOTRUTETYPE_SOSI (reader SOSI_1)
    attributes: SFOTRUTETYPE SOSI_char(2), SOSI_parent_guid SOSI_char(36)
    -> SFOTRUTE_SOSI_BulkAttributeRenamer
TILGJENGELIGHETSGRUPPE_SOSI (reader SOSI_1)
    attributes: TILGJENGELIGHETSGRUPPE SOSI_int16, SOSI_parent_guid SOSI_char(36)
    -> TILGJENELIGHETSGRUPPE_BulkAttributeRenamer
STATUS_SOSI (reader SOSI_1) [off]
    attributes: STATUS SOSI_char(2), SOSI_parent_guid SOSI_char(36)
    -> STATUS_SOSI_BulkAttributeRenamer
SOSI_RelationshipClasses (reader SOSI_1) [off]
    attributes: FeatureClass SOSI_char(100), GeometryType SOSI_char(32), Table SOSI_char(100)
    -> SOSI_Relationshipclasses_BulkAttributeRenamer

Bookmark: feltnavn til små bokstaver
BulkAttributeRenamer
    ATTRCHOICE = All Attributes
    CASE_CHANGE_TYPE = lowercase
    PATTERN_ACTION_DISP = Change Case
    -> AttributeRenamer2SOSI
OPPARBEIDING_SOSI_BulkAttributeRenamer: BulkAttributeRenamer
    ATTRCHOICE = All Attributes
    CASE_CHANGE_TYPE = lowercase
    PATTERN_ACTION_DISP = Change Case
    -> Opparbeiding_FeatureMerger [input 2]
SFOTRUTE_SOSI_BulkAttributeRenamer: BulkAttributeRenamer
    ATTRCHOICE = All Attributes
    CASE_CHANGE_TYPE = lowercase
    PATTERN_ACTION_DISP = Change Case
    -> Sfotrute_FeatureMerger [input 2]
TILGJENELIGHETSGRUPPE_BulkAttributeRenamer: BulkAttributeRenamer
    ATTRCHOICE = All Attributes
    CASE_CHANGE_TYPE = lowercase
    PATTERN_ACTION_DISP = Change Case
    -> Tilgjengelighetsgruppe_FeatureMerger [input 2]
STATUS_SOSI_BulkAttributeRenamer: BulkAttributeRenamer [off]
    ATTRCHOICE = All Attributes
    CASE_CHANGE_TYPE = lowercase
    PATTERN_ACTION_DISP = Change Case
SOSI_Relationshipclasses_BulkAttributeRenamer: BulkAttributeRenamer [off]
    ATTRCHOICE = All Attributes
    PATTERN_ACTION_DISP = Add String Prefix

Bookmark: Tilrettelegger attributtdata og håndterer endringer i geometri
AttributeRenamer2SOSI
    ATTR_LIST = h_malemetode,malemetodehoyde,,komm,kommune,
    -> Skilting_AttributeValueMapper
Skilting_AttributeValueMapper: AttributeValueMapper
    DIRECTION = Forward (Source To Destination)
    DEFAULT_VALUE = false
    LUT = JA,true,NEI,false
    VAL_ATTR = skilting
    SRC = skilting
    -> OBJID_Counter
OBJID_Counter: Counter
    START = 1
    CNT_ATTR = objid
    DOMAIN = counter
    SCOPE = Global
    -> LOKALID_UUIDGenerator
LOKALID_UUIDGenerator: UUIDGenerator
    UUID_ATTR = lokalid
    -> Skoytetrase_AttributeValueMapper
Skoytetrase_AttributeValueMapper: AttributeValueMapper
    DIRECTION = Forward (Source To Destination)
    DEFAULT_VALUE = false
    LUT = JA,true,NEI,false
    VAL_ATTR = skoytetrase
    SRC = skoytetrase
    -> 2DForcer
2DForcer
    2D -> DataFangstDato_NullAttributeMapper
DataFangstDato_NullAttributeMapper: NullAttributeMapper
    ATTRCHOICE = Selected Attributes
    ATTRLIST = datafangstdato
    NEW_VALUE = 1899-12-31
    SOURCE_ATTR_VAL = Empty "Missing (Selected Attributes Only)" Null
    NULL_TREATMENT = New Value
    -> Vedlikeh_NullAttributeMapper
Vedlikeh_NullAttributeMapper: NullAttributeMapper
    ATTRCHOICE = Selected Attributes
    ATTRLIST = vedlikeh
    NEW_VALUE = Ukjent
    SOURCE_ATTR_VAL = Empty "Missing (Selected Attributes Only)" Null
    NULL_TREATMENT = New Value
    -> Malemetode_NullAttributeMapper
Malemetode_NullAttributeMapper: NullAttributeMapper
    ATTRCHOICE = Selected Attributes
    ATTRLIST = malemetode
    NEW_VALUE = 99
    SOURCE_ATTR_VAL = Empty "Missing (Selected Attributes Only)" Null
    NULL_TREATMENT = New Value
    -> Noyaktighet_NullAttributeMapper
Noyaktighet_NullAttributeMapper: NullAttributeMapper
    ATTRCHOICE = Selected Attributes
    ATTRLIST = noyaktighet
    NEW_VALUE = 9999
    SOURCE_ATTR_VAL = Empty "Missing (Selected Attributes Only)" Null
    NULL_TREATMENT = New Value
    -> Empty2Null_NullAttributeMapper
Empty2Null_NullAttributeMapper: NullAttributeMapper
    ATTRCHOICE = Selected Attributes
    ATTRLIST = belysning frilufteierforhold fritilrettelegging malemetodehoyde opparbeiding preparering rutebetydning rutebredde rutefolger rutetype rutevanskelighetsgrad ryddebredde sesong sfotrutetype skilting skoytetrase spes_skiloypetype spesialsykkelrutetype synbarhet tilgjengelighetsgruppe trafikkbelastning underlagstype kommune
    SOURCE_ATTR_VAL = Empty "Missing (Selected Attributes Only)"
    NULL_TREATMENT = Null
    -> Empty2space_NullAttributeMapper
Empty2space_NullAttributeMapper: NullAttributeMapper
    ATTRCHOICE = Selected Attributes
    ATTRLIST = rutemerking
    NEW_VALUE = UKJ
    SOURCE_ATTR_VAL = Empty "Missing (Selected Attributes Only)" Null
    NULL_TREATMENT = New Value
    -> Fritilrettelegging_NullAttributeMapper
Fritilrettelegging_NullAttributeMapper: NullAttributeMapper
    ATTRCHOICE = Selected Attributes
    ATTRLIST = fritilrettelegging
    NEW_VALUE = 40
    SOURCE_ATTR_VAL = Null Empty "Missing (Selected Attributes Only)"
    NULL_TREATMENT = New Value
    -> Kommune_StringPadder
Kommune_StringPadder: StringPadder
    WIDTH = 4
    SRC_ATTRS = kommune
    PADCHAR = 0
    BLANK_ATTRIBUTE = No
    SIDE = Left
    -> Reprojector
Reprojector
    RASTER_CELL_SIZE = Preserve Cells
    INTERPOLATION_TYPE_NAME = Nearest Neighbor
    DEST = $(COORDSYS_OUT)
    SOURCE = Read from feature
    REPROJECTED -> Opparbeiding_FeatureMerger [input 1]

Bookmark: Merger inn relaterte data for ..OPPARBEIDING
Opparbeiding_FeatureMerger: FeatureMerger
    ATTR_ACCUM_MODE = Merge Supplier
    PROCESS_DUPS = No
    LIST_NAME = _list_opparbeiding
    MERGE_TYPE = Attributes Only
    JOIN_KEYS = @Value(sosi_guid) @Value(sosi_parent_guid) STRING
    IGNORE_NULLS = No
    ATTR_CONFLICT_RES = Use Requestor
    SUPPLIERS_FIRST = No
    MERGED -> Opparbeiding_ListConcatenator
    NOT_MERGED -> Opparbeiding_AttributeCreator
Opparbeiding_ListConcatenator: ListConcatenator
    LIST_ATTR = _list_opparbeiding{}.opparbeiding
    VAL_ATTR = _concatenated_opparbeiding
    SEP = ,
    DROP_EMPTY_PARTS = Yes
    -> Opparbeiding_StringConcatenator
Opparbeiding_StringConcatenator: StringConcatenator
    PARM_LINE = @Value(opparbeiding),@Value(_concatenated_opparbeiding)
    ACTION = Create New Attribute
    VAL_ATTR = _streng_opparbeiding
    -> Sfotrute_FeatureMerger [input 1]
Opparbeiding_AttributeCreator: AttributeCreator
    ATTR_LIST = _streng_opparbeiding,@Value(opparbeiding)
    -> Sfotrute_FeatureMerger [input 1]

Bookmark: Merger inn relaterte data for ..SFOTRUTE
Sfotrute_FeatureMerger: FeatureMerger
    ATTR_ACCUM_MODE = Merge Supplier
    PROCESS_DUPS = No
    LIST_NAME = _list_sfotrutetype
    MERGE_TYPE = Attributes Only
    JOIN_KEYS = @Value(sosi_guid) @Value(sosi_parent_guid) STRING
    IGNORE_NULLS = No
    ATTR_CONFLICT_RES = Use Requestor
    SUPPLIERS_FIRST = No
    MERGED -> Sfotrute_ListConcatenator
    NOT_MERGED -> Sfotrute_AttributeCreator
Sfotrute_ListConcatenator: ListConcatenator
    LIST_ATTR = _list_sfotrutetype{}.sfotrutetype
    VAL_ATTR = _concatenated_sfotrutetype
    SEP = ,
    DROP_EMPTY_PARTS = Yes
    -> Sfotrutetype_StringConcatenator
Sfotrutetype_StringConcatenator: StringConcatenator
    PARM_LINE = @Value(sfotrutetype),@Value(_concatenated_sfotrutetype)
    ACTION = Create New Attribute
    VAL_ATTR = _streng_sfotrutetype
    -> Tilgjengelighetsgruppe_FeatureMerger [input 1]
Sfotrute_AttributeCreator: AttributeCreator
    ATTR_LIST = _streng_sfotrutetype,@Value(sfotrutetype)
    -> Tilgjengelighetsgruppe_FeatureMerger [input 1]

Bookmark: Merger inn relaterte data for ..TILGJENGELIGHETSGRUPPE
Tilgjengelighetsgruppe_FeatureMerger: FeatureMerger
    ATTR_ACCUM_MODE = Merge Supplier
    PROCESS_DUPS = No
    LIST_NAME = _list_tilgjengelighetsgruppe
    MERGE_TYPE = Attributes Only
    JOIN_KEYS = @Value(sosi_guid) @Value(sosi_parent_guid) STRING
    IGNORE_NULLS = No
    ATTR_CONFLICT_RES = Use Requestor
    SUPPLIERS_FIRST = No
    MERGED -> Tilgjengelighetsgruppe_ListConcatenator
    NOT_MERGED -> Tilgjengelighetsgruppe_AttributeCreator
Tilgjengelighetsgruppe_ListConcatenator: ListConcatenator
    LIST_ATTR = _list_tilgjengelighetsgruppe{}.tilgjengelighetsgruppe
    VAL_ATTR = _concatenated_tilgjengelighetsgruppe
    SEP = ,
    DROP_EMPTY_PARTS = Yes
    -> Tilgjengelighetsgruppe_StringConcatenator
Tilgjengelighetsgruppe_StringConcatenator: StringConcatenator
    PARM_LINE = @Value(tilgjengelighetsgruppe),@Value(_concatenated_tilgjengelighetsgruppe)
    ACTION = Create New Attribute
    VAL_ATTR = _streng_tilgjengelighetsgruppe
    -> Mergers_AttributeRemover
Tilgjengelighetsgruppe_AttributeCreator: AttributeCreator
    ATTR_LIST = _streng_tilgjengelighetsgruppe,@Value(tilgjengelighetsgruppe)
    -> Mergers_AttributeRemover

Bookmark: Skrivere for data med geometri (PostGIS)
turogfriluftsruter.annenrute (writer POSTGIS_1)
    attributes: objid serial,PRIKEY, objtype varchar(32), arutetype varchar(80), vedlikeh varchar(80), frilufteierforhold varchar(80), belysning varchar(80), rutemerking varchar(80), skilting bool, rutefolger varchar(80), rutebredde varchar(80), opparbeiding varchar(80), rutebetydning varchar(80), rutevanskelighetsgrad varchar(80), underlagstype varchar(80), lengde int4, stigning int4, tilgjengelighetsgruppe varchar(80), rutetype varchar(80), navn varchar(80), rutenr varchar(80), lokalid uuid, datafangstdato timestamp, oppdateringsdato timestamp, malemetode varchar(80), noyaktighet int4, synbarhet varchar(80), malemetodehoyde varchar(80), h_noyaktighet int4, opphav varchar(80), kommune varchar(80),
      informasjon varchar(80), link varchar(80)
turogfriluftsruter.fotrute (writer POSTGIS_1)
    attributes: objid serial,PRIKEY, objtype varchar(32), sfotrutetype varchar(80), sesong varchar(80), vedlikeh varchar(80), frilufteierforhold varchar(80), belysning varchar(80), rutemerking varchar(80), skilting bool, rutefolger varchar(80), rutebredde varchar(80), opparbeiding varchar(80), rutebetydning varchar(80), rutevanskelighetsgrad varchar(80), underlagstype varchar(80), lengde int4, stigning int4, tilgjengelighetsgruppe varchar(80), rutetype varchar(80), navn varchar(80), rutenr varchar(80), lokalid uuid, datafangstdato timestamp, oppdateringsdato timestamp, malemetode varchar(80), noyaktighet int4, synbarhet varchar(80), malemetodehoyde varchar(80), h_noyaktighet int4, opphav varchar(80),
      kommune varchar(80), informasjon varchar(80), link varchar(80)
turogfriluftsruter.friluftslivtilrettelegging (writer POSTGIS_1)
    attributes: objid serial,PRIKEY, objtype varchar(32), vedlikeh varchar(80), fritilrettelegging varchar(80), lokalid uuid, datafangstdato timestamp, oppdateringsdato timestamp, malemetode varchar(80), noyaktighet int4, synbarhet varchar(80), malemetodehoyde varchar(80), h_noyaktighet int4, opphav varchar(80), kommune varchar(80), informasjon varchar(80), link varchar(80)
turogfriluftsruter.skiloype (writer POSTGIS_1)
    attributes: objid int4,PRIKEY, objtype varchar(32), spes_skiloypetype varchar(80), preparering varchar(80), ryddebredde varchar(80), antallskispor int4, skoytetrase bool, vedlikeh varchar(80), frilufteierforhold varchar(80), belysning varchar(80), rutemerking varchar(80), skilting bool, rutefolger varchar(80), rutebredde varchar(80), opparbeiding varchar(80), rutebetydning varchar(80), rutevanskelighetsgrad varchar(80), underlagstype varchar(80), lengde int4, stigning int4, tilgjengelighetsgruppe varchar(80), rutetype varchar(80), navn varchar(80), rutenr varchar(80), lokalid uuid, datafangstdato timestamp, oppdateringsdato timestamp, malemetode varchar(80), noyaktighet int4, synbarhet varchar(80),
      malemetodehoyde varchar(80), h_noyaktighet int4, opphav varchar(80), kommune varchar(80), informasjon varchar(80), link varchar(80)
turogfriluftsruter.sykkelrute (writer POSTGIS_1)
    attributes: objid serial,PRIKEY, objtype varchar(32), spesialsykkelrutetype varchar(80), trafikkbelastning varchar(80), vedlikeh varchar(80), frilufteierforhold varchar(80), belysning varchar(80), rutemerking varchar(80), skilting bool, rutefolger varchar(80), rutebredde varchar(80), opparbeiding varchar(80), rutebetydning varchar(80), rutevanskelighetsgrad varchar(80), underlagstype varchar(80), lengde int4, stigning int4, tilgjengelighetsgruppe varchar(80), rutetype varchar(80), navn varchar(80), rutenr varchar(80), lokalid uuid, datafangstdato timestamp, oppdateringsdato timestamp, malemetode varchar(80), noyaktighet int4, synbarhet varchar(80), malemetodehoyde varchar(80), h_noyaktighet int4, opphav varchar(80),
      kommune varchar(80), informasjon varchar(80), link varchar(80)

Bookmark: Håndterer relaterte data for AndreRuter
ar_Opparbeiding_Tester: Tester
    TEST_CLAUSE = TEST _streng_opparbeiding NOT_ATTRIBUTE_VALUE_NULL ""
    TEST_MODE = Automatic
    TEST_DESCRIPTION = ""
    BOOL_OP = OR
    PASSED -> ar_Opparbeiding_AttributeSplitter
ar_Opparbeiding_AttributeSplitter: AttributeSplitter
    LIST_NAME = _list_ar_opparbeiding
    TRIM_OPTION = Both
    ATTR_NAME = _streng_opparbeiding
    DELIMITER = ,
    DROP_EMPTY_PARTS = Yes
    -> ar_Opparbeiding_ListExploder
ar_Opparbeiding_ListExploder: ListExploder
    INDEX_ATTR = _element_index
    LIST_ATTR = _list_ar_opparbeiding{}
    ATTR_CONFLICT_RES = Use Original
    ATTR_ACCUM_MODE = Merge Incoming List
    LIST_FOUND -> ar_Opparbeiding_AttributeCreator
ar_Opparbeiding_AttributeCreator: AttributeCreator
    ATTR_LIST = opparbeiding,@Value(_list_ar_opparbeiding)
    -> turogfriluftsruter.annenrute_opparbeiding (writer POSTGRES_1)
ar_tilretteleggingsgruppe_Tester: Tester
    TEST_CLAUSE = TEST _streng_tilgjengelighetsgruppe NOT_ATTRIBUTE_VALUE_NULL ""
    TEST_MODE = Automatic
    TEST_DESCRIPTION = ""
    BOOL_OP = OR
    PASSED -> ar_Tilretteleggingsgruppe_AttributeSplitter
ar_Tilretteleggingsgruppe_AttributeSplitter: AttributeSplitter
    LIST_NAME = _list_ar_tilgjengelinhetsgruppe
    TRIM_OPTION = Both
    ATTR_NAME = _streng_tilgjengelighetsgruppe
    DELIMITER = ,
    DROP_EMPTY_PARTS = Yes
    -> ar_Tilgjengelighetsgruppe_ListExploder
ar_Tilgjengelighetsgruppe_ListExploder: ListExploder
    INDEX_ATTR = _element_index
    LIST_ATTR = _list_ar_tilgjengelinhetsgruppe{}
    ATTR_CONFLICT_RES = Use Original
    ATTR_ACCUM_MODE = Merge Incoming List
    LIST_FOUND -> ar_Tilgjengelighetsgruppe_AttributeCreator
ar_Tilgjengelighetsgruppe_AttributeCreator: AttributeCreator
    ATTR_LIST = tilgjengelighetsgruppe,@Value(_list_ar_tilgjengelinhetsgruppe)
    -> turogfriluftsruter.annenrute_tilgjengelighetsgruppe (writer POSTGRES_1)

Bookmark: Skrivere for data uten geometri (PostgreSQL)
turogfriluftsruter.annenrute_opparbeiding (writer POSTGRES_1)
    attributes: objid int4,PRIKEY, opparbeiding int4
turogfriluftsruter.annenrute_tilgjengelighetsgruppe (writer POSTGRES_1)
    attributes: objid int4,PRIKEY, tilgjengelighetsgruppe int4
turogfriluftsruter.fotrute_opparbeiding (writer POSTGRES_1)
    attributes: objid int4,PRIKEY, opparbeiding int4
turogfriluftsruter.fotrute_sfotrutetype (writer POSTGRES_1)
    attributes: objid int4,PRIKEY, sfotrutetype varchar(80)
turogfriluftsruter.fotrute_tilgjengelighetsgruppe (writer POSTGRES_1)
    attributes: objid int4,PRIKEY, tilgjengelighetsgruppe int4
turogfriluftsruter.skiloype_opparbeiding (writer POSTGRES_1)
    attributes: objid int4,PRIKEY, opparbeiding int4
turogfriluftsruter.skiloype_tilgjengelighetsgruppe (writer POSTGRES_1)
    attributes: objid int4,PRIKEY, tilgjengelighetsgruppe int4
turogfriluftsruter.sykkelrute_opparbeiding (writer POSTGRES_1)
    attributes: objid int4,PRIKEY, opparbeiding int4
turogfriluftsruter.sykkelrute_tilgjengelighetsgruppe (writer POSTGRES_1)
    attributes: objid int4,PRIKEY, tilgjengelighetsgruppe int4

Bookmark: Håndterer relaterte data for Fotruter
fr_Opparbeiding_Tester: Tester
    TEST_CLAUSE = TEST _streng_opparbeiding NOT_ATTRIBUTE_VALUE_NULL ""
    TEST_MODE = Automatic
    TEST_DESCRIPTION = ""
    BOOL_OP = OR
    PASSED -> fr_Opparbeiding_AttributeSplitter
fr_Opparbeiding_AttributeSplitter: AttributeSplitter
    LIST_NAME = _list_fr_opparbeiding
    TRIM_OPTION = Both
    ATTR_NAME = _streng_opparbeiding
    DELIMITER = ,
    DROP_EMPTY_PARTS = Yes
    -> fr_Opparbeiding_ListExploder
fr_Opparbeiding_ListExploder: ListExploder
    INDEX_ATTR = _element_index
    LIST_ATTR = _list_fr_opparbeiding{}
    ATTR_CONFLICT_RES = Use Original
    ATTR_ACCUM_MODE = Merge Incoming List
    LIST_FOUND -> fr_Opparbeiding_AttributeCreator
fr_Opparbeiding_AttributeCreator: AttributeCreator
    ATTR_LIST = opparbeiding,@Value(_list_fr_opparbeiding)
    -> turogfriluftsruter.fotrute_opparbeiding (writer POSTGRES_1)
fr_Sfotrutetype_Tester: Tester
    TEST_CLAUSE = TEST _streng_sfotrutetype NOT_ATTRIBUTE_VALUE_NULL ""
    TEST_MODE = Automatic
    TEST_DESCRIPTION = ""
    BOOL_OP = OR
    PASSED -> fr_Sfotrutetype_AttributeSplitter
fr_Sfotrutetype_AttributeSplitter: AttributeSplitter
    LIST_NAME = _list_fr_sfotrutetype
    TRIM_OPTION = Both
    ATTR_NAME = _streng_sfotrutetype
    DELIMITER = ,
    DROP_EMPTY_PARTS = Yes
    -> fr_Sfotrutetype_ListExploder
fr_Sfotrutetype_ListExploder: ListExploder
    INDEX_ATTR = _element_index
    LIST_ATTR = _list_fr_sfotrutetype{}
    ATTR_CONFLICT_RES = Use Original
    ATTR_ACCUM_MODE = Merge Incoming List
    LIST_FOUND -> fr_Sfotrutetype_AttributeCreator
fr_Sfotrutetype_AttributeCreator: AttributeCreator
    ATTR_LIST = sfotrutetype,@Value(_list_fr_sfotrutetype)
    -> turogfriluftsruter.fotrute_sfotrutetype (writer POSTGRES_1)
fr_Tilgjengelighetsgruppe_Tester: Tester
    TEST_CLAUSE = TEST _streng_tilgjengelighetsgruppe NOT_ATTRIBUTE_VALUE_NULL ""
    TEST_MODE = Automatic
    TEST_DESCRIPTION = ""
    BOOL_OP = OR
    PASSED -> fr_Tilgjengelighetsgruppe_AttributeSplitter
fr_Tilgjengelighetsgruppe_AttributeSplitter: AttributeSplitter
    LIST_NAME = _list_fr_tilgjengelighetsgruppe
    TRIM_OPTION = Both
    ATTR_NAME = _streng_tilgjengelighetsgruppe
    DELIMITER = ,
    DROP_EMPTY_PARTS = Yes
    -> fr_Tilgjengelighetsgruppe_ListExploder
fr_Tilgjengelighetsgruppe_ListExploder: ListExploder
    INDEX_ATTR = _element_index
    LIST_ATTR = _list_fr_tilgjengelighetsgruppe{}
    ATTR_CONFLICT_RES = Use Original
    ATTR_ACCUM_MODE = Merge Incoming List
    LIST_FOUND -> fr_Tilgjengelighetsgruppe_AttributeCreator
fr_Tilgjengelighetsgruppe_AttributeCreator: AttributeCreator
    ATTR_LIST = tilgjengelighetsgruppe,@Value(_list_fr_tilgjengelighetsgruppe)
    -> turogfriluftsruter.fotrute_tilgjengelighetsgruppe (writer POSTGRES_1)

Bookmark: Håndterer relaterte data for Skiløyper
sl_Opparbeiding_Tester: Tester
    TEST_CLAUSE = TEST _streng_opparbeiding NOT_ATTRIBUTE_VALUE_NULL ""
    TEST_MODE = Automatic
    TEST_DESCRIPTION = ""
    BOOL_OP = OR
    PASSED -> sl_Opparbeiding_AttributeSplitter
sl_Opparbeiding_AttributeSplitter: AttributeSplitter
    LIST_NAME = _list_sl_opparbeiding
    TRIM_OPTION = Both
    ATTR_NAME = _streng_opparbeiding
    DELIMITER = ,
    DROP_EMPTY_PARTS = Yes
    -> sl_Opparbeiding_ListExploder
sl_Opparbeiding_ListExploder: ListExploder
    INDEX_ATTR = _element_index
    LIST_ATTR = _list_sl_opparbeiding{}
    ATTR_CONFLICT_RES = Use Original
    ATTR_ACCUM_MODE = Merge Incoming List
    LIST_FOUND -> sl_Opparbeiding_AttributeCreator
sl_Opparbeiding_AttributeCreator: AttributeCreator
    ATTR_LIST = opparbeiding,@Value(_list_sl_opparbeiding)
    -> turogfriluftsruter.skiloype_opparbeiding (writer POSTGRES_1)
sl_Tilgjengelighetsgruppe_Tester: Tester
    TEST_CLAUSE = TEST _streng_tilgjengelighetsgruppe NOT_ATTRIBUTE_VALUE_NULL ""
    TEST_MODE = Automatic
    TEST_DESCRIPTION = ""
    BOOL_OP = OR
    PASSED -> sl_Tilgjengelighetsgruppe_AttributeSplitter
sl_Tilgjengelighetsgruppe_AttributeSplitter: AttributeSplitter
    LIST_NAME = _list_sl_tilgjengelighetsgruppe
    TRIM_OPTION = Both
    ATTR_NAME = _streng_tilgjengelighetsgruppe
    DELIMITER = ,
    DROP_EMPTY_PARTS = Yes
    -> sl_Tilgjengelighetsgruppe_ListExploder
sl_Tilgjengelighetsgruppe_ListExploder: ListExploder
    INDEX_ATTR = _element_index
    LIST_ATTR = _list_sl_tilgjengelighetsgruppe{}
    ATTR_CONFLICT_RES = Use Original
    ATTR_ACCUM_MODE = Merge Incoming List
    LIST_FOUND -> sl_Tilgjengelighetsgruppe_AttributeCreator
sl_Tilgjengelighetsgruppe_AttributeCreator: AttributeCreator
    ATTR_LIST = tilgjengelighetsgruppe,@Value(_list_sl_tilgjengelighetsgruppe)
    -> turogfriluftsruter.skiloype_tilgjengelighetsgruppe (writer POSTGRES_1)

Bookmark: Håndterer relaterte data for Sykkelryter
sr_Opparbeiding_Tester: Tester
    TEST_CLAUSE = TEST _streng_opparbeiding NOT_ATTRIBUTE_VALUE_NULL ""
    TEST_MODE = Automatic
    TEST_DESCRIPTION = ""
    BOOL_OP = OR
    PASSED -> sr_Opparbeiding_AttributeSplitter
sr_Opparbeiding_AttributeSplitter: AttributeSplitter
    LIST_NAME = _list_sr_opparbeiding
    TRIM_OPTION = Both
    ATTR_NAME = _streng_opparbeiding
    DELIMITER = ,
    DROP_EMPTY_PARTS = Yes
    -> sr_Opparbeiding_ListExploder
sr_Opparbeiding_ListExploder: ListExploder
    INDEX_ATTR = _element_index
    LIST_ATTR = _list_sr_opparbeiding{}
    ATTR_CONFLICT_RES = Use Original
    ATTR_ACCUM_MODE = Merge Incoming List
    LIST_FOUND -> sr_Opparbeiding_AttributeCreator
sr_Opparbeiding_AttributeCreator: AttributeCreator
    ATTR_LIST = opparbeiding,@Value(_list_sr_opparbeiding)
    -> turogfriluftsruter.sykkelrute_opparbeiding (writer POSTGRES_1)
sr_Tilgjengelighetsgruppe_Tester: Tester
    TEST_CLAUSE = TEST _streng_tilgjengelighetsgruppe NOT_ATTRIBUTE_VALUE_NULL ""
    TEST_MODE = Automatic
    TEST_DESCRIPTION = ""
    BOOL_OP = OR
    PASSED -> sr_Tilgjengelighetsgruppe_AttributeSplitter
sr_Tilgjengelighetsgruppe_AttributeSplitter: AttributeSplitter
    LIST_NAME = _list_sr_tilgjengelighetsgruppe
    TRIM_OPTION = Both
    ATTR_NAME = _streng_tilgjengelighetsgruppe
    DELIMITER = ,
    DROP_EMPTY_PARTS = Yes
    -> sr_Tilgjengelighetsgruppe_ListExploder
sr_Tilgjengelighetsgruppe_ListExploder: ListExploder
    INDEX_ATTR = _element_index
    LIST_ATTR = _list_sr_tilgjengelighetsgruppe{}
    ATTR_CONFLICT_RES = Use Original
    ATTR_ACCUM_MODE = Merge Incoming List
    LIST_FOUND -> sr_Tilgjengelighetsgruppe_AttributeCreator
sr_Tilgjengelighetsgruppe_AttributeCreator: AttributeCreator
    ATTR_LIST = tilgjengelighetsgruppe,@Value(_list_sr_tilgjengelighetsgruppe)
    -> turogfriluftsruter.sykkelrute_tilgjengelighetsgruppe (writer POSTGRES_1)
