FME workspace TurOgFriluftsruter_postgis2gml.fmw
# Copyright: (c) xgrimor 2015
# Licence: <your licence>
Shutdown Python:
      # -*- coding: utf-8 -*-
      #-------------------------------------------------------------------------------
      # Name:        zipfiles.py
      # Purpose:     Pakker filer i output folderen
      #
      # Author:      xsunknu
      #
      # Created:     18.09.2015
      # Copyright:   (c) xsunknu 2015
      # Licence:     <your licence>
      #-------------------------------------------------------------------------------

      import sys, os, zipfile, fme

      def zip(gmlfile, zfile):
          from os.path import basename

          # Lager korresponderende zip-fil av GML-fil
          if os.path.isfile(zfile):
              os.remove(zfile)

          zf = zipfile.ZipFile(zfile, "w", zipfile.ZIP_DEFLATED)

          # Ønsker ikke full sti inn i ZIP-filen
          arcname = basename(gmlfile)

          # ZIP-formatet støtter ikke non-ascii tegn
          # Erstatter AØÅæøå med ascii-tegn
          arcname = arcname.replace('\xc6', 'E')
          arcname = arcname.replace('\xd8', 'O')
          arcname = arcname.replace('\xc5', 'A')
          arcname = arcname.replace('\xe6', 'e')
          arcname = arcname.replace('\xf8', 'o')
          arcname = arcname.replace('\xe5', 'a')

          zf.write(gmlfile, arcname)
          zf.close()
          os.remove(gmlfile)

          return

      def main():

          # Kjøres ikke på FME Server, da FME Server selv sørger for pakkingen
          if not 'FME_SERVER_DEST_DIR' in fme.macroValues:
              if 'FANOUT_FOLDER' in fme.macroValues:
                  logger = open(fme.logFileName, 'a')
                  path = fme.macroValues['FANOUT_FOLDER']
                  for dirpath, dnames, fnames in os.walk(path):
                      for f in fnames:
                          if f.endswith(".gml"):
                              # Scanner gjennom alle GML-filer
                              gmlfile = os.path.join(path, f)
                              zfile = os.path.splitext(gmlfile)[0] + '.zip'
                              if os.path.isfile(zfile):

                                  # Korresponderende ZIP-fil finnes, sjekker timestamps
                                  gmltstamp = os.stat(gmlfile).st_mtime
                                  ziptstamp = os.stat(zfile).st_mtime

                                  if gmltstamp > ziptstamp:
                                      # GML-fil er nyere enn ZIP-fila, ZIP-fila oppdateres
                                      # GML-fila slettes
                                      try:
                                          zip(gmlfile, zfile)
                                      except:
      #                                    print 'Kunne ikke pakke: ' + gmlfile
                                          logger.write('Kunne ikke pakke: ' + gmlfile + '\n')
                                  else:
                                      # GML-fila er eldre enn ZIP-fila
                                      # GML-fila slettes
                                      try:
                                          os.remove(gmlfile)
                                      except:
      #                                    print 'Kunne ikke slette: ' + gmlfile
                                          logger.write('Kunne ikke slette: ' + gmlfile + '\n')
                              else:
                                  # ZIP-fila eksisterer ikke og lages
                                  # GML-fila slettes
                                  try:
                                      zip(gmlfile, zfile)
                                  except:
      #                                print 'Kunne ikke pakke: ' + gmlfile
                                      logger.write('Kunne ikke pakke: ' + gmlfile + '\n')

                  logger.close()

      if __name__ == '__main__':
          main()

Parameters:
- KNR =   # Kommune(r)
- FNR =   # Fylke(r)
- CLIPPERCOORDS =   # Clipper coordinates
- CLIPPER_EPSG_CODE =   # Clipper EPSG code
- CLIPPER_FILE =   # "" Clipper file (any format)
- OUTPUT_EPSG_CODE = 25833   # Output EPSG code
- FANOUT =   # Fanout områder
- CONFIG_FILE:   # Python Script
      #-------------------------------------------------------------------------------
      # Name:        GetConfigFile
      # Purpose:
      #
      # Author:      xsunknu
      #
      # Created:     21.08.2015
      # Copyright:   (c) xsunknu 2015
      # Licence:     <your licence>
      #-------------------------------------------------------------------------------
      
      import os, fme
      
      fmwdir = fme.macroValues['FME_MF_DIR']
      fmwfile = fme.macroValues['FME_MF_NAME']
      
      fmwfile = os.path.join(fmwdir, fmwfile)
      configfile = os.path.splitext(fmwfile)[0] + '_config.xml'
      
      return configfile
- PG_PWD:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgpwd').text
      
      return value
- PG_USER:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pguser').text
      
      return value
- PG_HOST:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pghost').text
      
      return value
- PG_DB:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgdb').text
      
      return value
- GML_FILE = turogfriluftsruter   # gml file 
- FIXEDCLIPPERCOORDS:   # Python Script
      #-------------------------------------------------------------------------------
      # Name:        FixClipperCoords
      # Purpose:
      #
      # Author:      xsunknu
      #
      # Created:     21.08.2015
      # Copyright:   (c) xsunknu 2015
      # Licence:     <your licence>
      #-------------------------------------------------------------------------------
      
      import fme
      clippercoords = fme.macroValues['CLIPPERCOORDS']
      
      if clippercoords == '':
          clippercoords = '1 1'
      
      return clippercoords
- DESTCOORDSYS:   # Python Script
      #-------------------------------------------------------------------------------
      # Name:        SetCoordinateSystem
      # Purpose:
      #
      # Author:      xsunknu
      #
      # Created:     21.08.2015
      # Copyright:   (c) xsunknu 2015
      # Licence:     <your licence>
      #-------------------------------------------------------------------------------
      
      import os, fme
      
      EPSGvalue = fme.macroValues['OUTPUT_EPSG_CODE']
      EPSGcode  = 'EPSG:' + EPSGvalue
      
      return EPSGcode
- CLIPPERCOORDSYS:   # Python Script
      #-------------------------------------------------------------------------------
      # Name:        SetCoordinateSystem
      # Purpose:
      #
      # Author:      xsunknu
      #
      # Created:     21.08.2015
      # Copyright:   (c) xsunknu 2015
      # Licence:     <your licence>
      #-------------------------------------------------------------------------------
      
      import os, fme
      
      EPSGvalue = fme.macroValues['CLIPPER_EPSG_CODE']
      EPSGcode  = 'EPSG:' + EPSGvalue
      
      return EPSGcode
- LOG_FILE:   # Python Script
      #-------------------------------------------------------------------------------
      # Name:        GetConfigFile
      # Purpose:
      #
      # Author:      xsunknu
      #
      # Created:     21.08.2015
      # Copyright:   (c) xsunknu 2015
      # Licence:     <your licence>
      #-------------------------------------------------------------------------------
      
      import os, uuid, fme
      
      fmwdir = fme.macroValues['FME_MF_DIR']
      fmwfile = fme.macroValues['FME_MF_NAME']
      
      logdir = os.path.join(fmwdir, 'log')
      if not os.path.isdir(logdir):
          os.mkdir(logdir)
      
      logfile = os.path.splitext(fmwfile)[0] + '_' + str(uuid.uuid1()).replace('-','') + '.log'
      logfile = os.path.join(logdir, logfile)
      
      return logfile
- FANOUT_FOLDER:   # Python Script
      #-------------------------------------------------------------------------------
      # Name:        GetConfigFile
      # Purpose:
      #
      # Author:      xsunknu
      #
      # Created:     21.08.2015
      # Copyright:   (c) xsunknu 2015
      # Licence:     <your licence>
      #-------------------------------------------------------------------------------
      
      import os, fme
      from xml.etree import ElementTree as ET
      
      if 'FME_SERVER_DEST_DIR' in fme.macroValues:
          value = fme.macroValues['FME_SERVER_DEST_DIR']
      else:
          #Read XML config file
          configtree = ET.parse(fme.macroValues['CONFIG_FILE'])
          configdoc = configtree.getroot()
          value = configdoc.find('destdir').text
      
      return value
- SPATIAL_FILTER:   # Python Script
      #-------------------------------------------------------------------------------
      # Name:        SetSpatialFilter
      # Purpose:
      #
      # Author:      xsunknu
      #
      # Created:     21.08.2015
      # Copyright:   (c) xsunknu 2015
      # Licence:     <your licence>
      #-------------------------------------------------------------------------------
      
      import fme
      
      spatialfilter = 'Intersects'
      
      knr = fme.macroValues['KNR']
      fnr = fme.macroValues['FNR']
      coords = fme.macroValues['CLIPPERCOORDS']
      file = fme.macroValues['CLIPPER_FILE']
      
      if knr == '' and fnr == '' and coords == '' and file == '':
          spatialfilter = '<No Spatial Filter>'
      
      return spatialfilter
- DestDataset_GML_3 = $(FME_MF_DIR)turogfriluftsruter.gml   # Destination Geography Markup Language (GML) File

Readers:
- POSTGIS_1: POSTGIS from $(PG_DB)
- POSTGRES_1: POSTGRES from $(PG_DB)

Writers:
- GML_1: GML to $(DestDataset_GML_3)

CreateClipper
    CLIPPERCOORDSYS = $(CLIPPERCOORDSYS)
    DESTCOORDSYS = $(DESTCOORDSYS)
    CLIPPERCOORDS = $(FIXEDCLIPPERCOORDS)
    reprojectBboxESRI_REPROJECTED_2 -> Clipper [input 1]
    reprojectBboxESRI_REPROJECTED_2 -> FeatureReader
FeatureReader
    POSTGIS_USE_SEARCH_ENVELOPE = NO
    POSTGIS_HOST = nnridb504
    ATTR_CONFLICT_RES = Use Result
    POSTGIS_DISABLE_COLLECTION_SPLITTING = yes
    OUTPUT_FEATURES_DISPLAY = Based on Connections
    INTERACT = $(SPATIAL_FILTER)
    POSTGIS_QUERY_FEATURE_TYPES_FOR_MERGE_FILTERS = Yes
    FEATURETYPES = turogfriluftsruter.annenrute turogfriluftsruter.fotrute turogfriluftsruter.friluftslivtilrettelegging turogfriluftsruter.skiloype turogfriluftsruter.sykkelrute
    FORMAT = POSTGIS
    POSTGIS_USE_TRUE_POSTGIS_TYPES = yes
    ATTRIBUTES = turogfriluftsruter.annenrute,"objid,objtype,arutetype,vedlikeh,frilufteierforhold,belysning,rutemerking,skilting,rutefolger,rutebredde,opparbeiding,rutebetydning,rutevanskelighetsgrad,underlagstype,lengde,stigning,tilgjengelighetsgruppe,rutetype,navn,rutenr,lokalid,datafangstdato,oppdateringsdato,malemetode,noyaktighet,synbarhet,malemetodehoyde,h_noyaktighet,opphav,kommune,informasjon,link",turogfriluftsruter.fotrute,"objid,objtype,sfotrutetype,sesong,vedlikeh,frilufteierforhold,belysning,rutemerking,skilting,rutefolger,rutebredde,opparbeiding,rutebetydning,rutevanskelighetsgrad,underlagstype,lengde,stigning,tilgjengelighetsgruppe,rutetype,navn,rutenr,lokalid,datafangstdato,oppdateringsdato,malemetode,noyaktighet,synbarhet,malemetodehoyde,h_noyaktighet,opphav,kommune,informasjon,link",turogfriluftsruter.friluftslivtilrettelegging,"objid,objtype,vedlikeh,fritilrettelegging,lokalid,datafangstdato,oppdateringsdato,malemetode,noyaktighet,synbarhet,malemetodehoyde,h_noyaktighet,opphav,kommune,informasjon,link",turogfriluftsruter.skiloype,"objid,objtype,spes_skiloypetype,preparering,ryddebredde,antallskispor,skoytetrase,vedlikeh,frilufteierforhold,belysning,rutemerking,skilting,rutefolger,rutebredde,opparbeiding,rutebetydning,rutevanskelighetsgrad,underlagstype,lengde,stigning,tilgjengelighetsgruppe,rutetype,navn,rutenr,lokalid,datafangstdato,oppdateringsdato,malemetode,noyaktighet,synbarhet,malemetodehoyde,h_noyaktighet,opphav,kommune,informasjon,link",turogfriluftsruter.sykkelrute,"objid,objtype,spesialsykkelrutetype,trafikkbelastning,vedlikeh,frilufteierforhold,belysning,rutemerking,skilting,rutefolger,rutebredde,opparbeiding,rutebetydning,rutevanskelighetsgrad,underlagstype,lengde,stigning,tilgjengelighetsgruppe,rutetype,navn,rutenr,lokalid,datafangstdato,oppdateringsdato,malemetode,noyaktighet,synbarhet,malemetodehoyde,h_noyaktighet,opphav,kommune,informasjon,link"
    POSTGIS_USER_NAME = geonortst
    ATTR_ACCUM_MODE = Merge Initiator and Result
    DATASET = geonor01tst
    POSTGIS_CLIP_TO_ENVELOPE = NO
    FEATURETYPES_RADIO = FEATURETYPES
    POSTGIS_SCHEMALIST = turogfriluftsruter
    POSTGIS_PORT = 5432
    COMBINE_GEOM = Use Result
    POSTGIS_PASSWORD =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
    turogfriluftsruter.sykkelrute -> AttributeCreator_12
    turogfriluftsruter.skiloype -> AttributeCreator_12
    turogfriluftsruter.friluftslivtilrettelegging -> AttributeCreator_12
    turogfriluftsruter.fotrute -> AttributeCreator_12
    turogfriluftsruter.annenrute -> AttributeCreator_12
AttributeCreator_12
    ATTR_LIST = _clippercoords,$(CLIPPERCOORDS),_clipper_file,$(CLIPPER_FILE),_fnr,$(FNR),_knr,$(KNR)
    -> TestFilter
TestFilter
    TEST_LIST:
      BOOL_OP,AND,COMPOSITE_TEST,<Unused>,TEST_CLAUSE,"TEST _clipper_file ATTRIBUTE_IS_EMPTY """"
      TEST _clippercoords ATTRIBUTE_IS_EMPTY """"
      TEST _fnr ATTRIBUTE_IS_EMPTY """"
      TEST _knr ATTRIBUTE_IS_EMPTY """"",Landsdekkende,BOOL_OP,AND,COMPOSITE_TEST,<Unused>,TEST_CLAUSE,"TEST _clipper_file ATTRIBUTE_IS_EMPTY """"
      TEST _clippercoords ATTRIBUTE_IS_EMPTY """"
      TEST _fnr NOT_ATTRIBUTE_IS_EMPTY """"
      TEST _knr ATTRIBUTE_IS_EMPTY """"",Fylkesvis,BOOL_OP,AND,COMPOSITE_TEST,<Unused>,TEST_CLAUSE,"TEST _clipper_file ATTRIBUTE_IS_EMPTY """"
      TEST _clippercoords ATTRIBUTE_IS_EMPTY """"
      TEST _fnr ATTRIBUTE_IS_EMPTY """"
      TEST _knr NOT_ATTRIBUTE_IS_EMPTY """"",Kommunevis
    DEFAULT_VALUE = <UNFILTERED>
    <UNFILTERED> -> Clipper [input 2]
    Landsdekkende -> Destination_Reprojector
    Fylkesvis -> Destination_Reprojector
    Kommunevis -> Destination_Reprojector
Note: Clipper klipper datakilden mot det, eller de, valgte klippeobjektene: / - Kommuner og/eller fylker / - Polygon(er) spesifisert i en klippefil / - Et fritt valgt polygon basert på inntastede koordinater
Clipper
    BOUNDARY_CASES = Treat as Inside
    ATTR_ACCUM_MODE = Merge Clipper
    ATTR_CONFLICT_RES = Use Clippee
    PRESERVE_CLIPPEE_EXTENTS = No
    CREATE_AGGREGATES = Yes
    CLIP_TYPE = Multiple Clippers
    CLIPPED_ATTR = _clipped
    INSIDE -> Destination_Reprojector
Note: Reprojiserer data til / ut-koordinatsystem.
Destination_Reprojector: Reprojector
    INTERPOLATION_TYPE_NAME = Nearest Neighbor
    RASTER_CELL_SIZE = Preserve Cells
    SOURCE = Read from feature
    DEST = $(DESTCOORDSYS)
    REPROJECTED -> UUIDGenerator
UUIDGenerator
    UUID_ATTR = gml_id
    -> AttributeCreator
AttributeCreator
    ATTR_LIST = gml_id,ID@Value(gml_id)
    -> Skilting_AttributeValueMapper
Skilting_AttributeValueMapper: AttributeValueMapper
    LUT = f,false,t,true
    SRC = skilting
    VAL_ATTR = skilting
    DEFAULT_VALUE = NEI
    DIRECTION = Forward (Source To Destination)
    -> Skoytetrase_AttributeValueMapper
Skoytetrase_AttributeValueMapper: AttributeValueMapper
    LUT = f,false,t,true
    SRC = skoytetrase
    VAL_ATTR = skoytetrase
    DEFAULT_VALUE = NEI
    DIRECTION = Forward (Source To Destination)
    -> gmlfile_AttributeCreator
Note: Legger til en del attributter: / - gmlFile: settes til verdien av parameter GML_FILE og brukes til 'fanout' på datafil / for å kunne klare å henvise til $[FME_SERVER_OUTPUT_DIR] / - dataeier: settes til "Statens kartverk - Miljødirektoratet" og kan benyttes videre. / - fylkesnr: inneholder fylkesnummeret for objektet / - komm: tilsvarer fylkesnr, men denne inneholder kommunenummer
gmlfile_AttributeCreator: AttributeCreator
    ATTR_LIST = gmlfile,"FME_CONDITIONAL:DEFAULT_VALUE'Friluftsliv_$(OUTPUT_EPSG_CODE)_$(GML_FILE)_GML'BOOL_OP;OR;COMPOSITE_TEST;<Unused>;TEST $(FANOUT) LIKE Kommuner'Friluftsliv_@PadLeft(@Value(kommuneid),4,0)_@Value(knavn)_$(OUTPUT_EPSG_CODE)_$(GML_FILE)_GML'BOOL_OP;OR;COMPOSITE_TEST;<Unused>;TEST $(FANOUT) LIKE Fylker'Friluftsliv_@PadLeft(@Value(fylkeid),2,0)_@Value(fnavn)_$(OUTPUT_EPSG_CODE)_$(GML_FILE)_GML'BOOL_OP;OR;COMPOSITE_TEST;<Unused>;TEST $(FANOUT) LIKE Norge'Friluftsliv_0000_Norge_$(OUTPUT_EPSG_CODE)_$(GML_FILE)_GML'FME_NUM_CONDITIONS4___",dataeier,Statens kartverk - Miljødirektoratet,fylkesnr,@Value(fylkeid),komm,"FME_CONDITIONAL:DEFAULT_VALUE'@PadLeft(@Value(kommuneid),4,0)'BOOL_OP;OR;COMPOSITE_TEST;<Unused>;TEST kommuneid ATTRIBUTE_IS_MISSING _FME_BLANK_STRING_'FME_NULL_VALUE'FME_NUM_CONDITIONS2___"
    -> FeatureTypeFilter
FeatureTypeFilter
    ATTRIBUTES = turogfriluftsruter.annenrute,turogfriluftsruter.fotrute,turogfriluftsruter.friluftslivtilrettelegging,turogfriluftsruter.skiloype,turogfriluftsruter.sykkelrute,<BLANK>,<UNFILTERED>
    turogfriluftsruter.annenrute -> Annenrute_tilgjengelighetsgruppe_FeatureMerger [input 1]
    turogfriluftsruter.fotrute -> Fotrute_tilgjengelighetsgruppe_FeatureMerger [input 1]
    turogfriluftsruter.skiloype -> Skiloype_opparbeiding_FeatureMerger [input 1]
    turogfriluftsruter.sykkelrute -> Sykkelrute_opparbeiding_FeatureMerger [input 1]
    turogfriluftsruter.friluftslivtilrettelegging -> DateFormatter_3

Bookmark: Fylke og/eller kommune clippers
admingrense.fylkeflate (reader POSTGIS_1)
    attributes: fylkeid int4, navn varchar(80)
    -> FylkesnavnRenamer
FylkesnavnRenamer: AttributeRenamer
    ATTR_LIST = navn,fnavn,
    -> Fylkeid_Tester
    -> HeleNorge_AttributeCreator
HeleNorge_AttributeCreator: AttributeCreator
    ATTR_LIST = _clippercoords,$(CLIPPERCOORDS),_clipper_file,$(CLIPPER_FILE),_fnr,$(FNR),_knr,$(KNR)
    -> HeleNorge_Tester
HeleNorge_Tester: Tester
    TEST_CLAUSE:
      TEST _clipper_file ATTRIBUTE_IS_EMPTY ""
      TEST _clippercoords ATTRIBUTE_IS_EMPTY ""
      TEST _fnr ATTRIBUTE_IS_EMPTY ""
      TEST _knr ATTRIBUTE_IS_EMPTY ""
    TEST_DESCRIPTION = ""
    TEST_MODE = Automatic
    BOOL_OP = AND
    PASSED -> Dissolver
Dissolver
    NO_OVRLP = No
    ACCUM_INPUT_ATTRS = Yes
    AREA -> AdminFlateReprojector
Fylkeid_Tester: Tester
    TEST_CLAUSE = TEST @Value(fylkeid) IN $(FNR)
    TEST_DESCRIPTION = ""
    TEST_MODE = Automatic
    BOOL_OP = OR
    PASSED -> AdminFlateReprojector
admingrense.kommuneflate (reader POSTGIS_1)
    attributes: kommuneid int4, navn varchar(80)
    -> KommuneNavnRenamer
KommuneNavnRenamer: AttributeRenamer
    ATTR_LIST = navn,knavn,
    -> kommuneid_Tester
kommuneid_Tester: Tester
    TEST_CLAUSE = TEST @Value(kommuneid) IN $(KNR)
    TEST_DESCRIPTION = ""
    TEST_MODE = Automatic
    BOOL_OP = OR
    PASSED -> AdminFlateReprojector
AdminFlateReprojector: Reprojector
    INTERPOLATION_TYPE_NAME = Nearest Neighbor
    RASTER_CELL_SIZE = Preserve Cells
    SOURCE = Read from feature
    DEST = EPSG:4258
    REPROJECTED -> FeatureReader

Bookmark: Clipper file (any format)
Creator
    GEOMTYPE = Geometry Object
    NUM = 1
    CREATED -> ClipperFile_FeatureReader
ClipperFile_FeatureReader: FeatureReader
    DATASET = $(CLIPPER_FILE)
    FEATURETYPES_RADIO = FEATURETYPES
    ATTRIBUTES = NewFeatureType,
    INTERACT = $(SPATIAL_FILTER)
    ATTR_ACCUM_MODE = Only Use Result
    FORMAT = GENERIC
    GENERIC_REAL_FORMAT = GUESS_FROM_EXTENSION
    OUTPUT_FEATURES_DISPLAY = Based on Connections
    COMBINE_GEOM = Use Result
    <OTHER> -> ClipperFileReprojector
ClipperFileReprojector: Reprojector
    INTERPOLATION_TYPE_NAME = Nearest Neighbor
    RASTER_CELL_SIZE = Preserve Cells
    SOURCE = Read from feature
    DEST = EPSG:4258
    REPROJECTED -> Clipper [input 1]
    REPROJECTED -> FeatureReader

Bookmark: Formatering og mapping GML
DateFormatter_3
    SRCFMT = Unknown - Automatic Detection
    INVALID_DATE_VALUE = _FME_NO_OP_
    FMT = ISO DateTime (%Y-%m-%dT%H:%M:%S)
    DATE_ATTR = datafangstdato,oppdateringsdato
    -> GeometryPropertySetter_3
GeometryPropertySetter_3
    SETTYPE_PARAM = Geometry Name
    OVERWRITE_CHOICE = Yes
    GEOM_NAME_FIELD = posisjon
    SET -> AttributeRenamer_3
AttributeRenamer_3
    ATTR_LIST = lokalid,identifikasjon.Identifikasjon.lokalId,,malemetode,kvalitet.Posisjonskvalitet.målemetode,,malemetodehoyde,kvalitet.Posisjonskvalitet.målemetodeHøyde,,noyaktighet,kvalitet.Posisjonskvalitet.nøyaktighet,,noyaktighet,kvalitet.Posisjonskvalitet.nøyaktighetHøyde,,synbarhet,kvalitet.Posisjonskvalitet.synbarhet,,fritilrettelegging,tilrettelegging,,vedlikeh,vedlikeholdsansvarlig,
    -> NullAttributeMapper_3
NullAttributeMapper_3
    SOURCE_ATTR_VAL = Empty Null
    NULL_TREATMENT = Missing
    ATTRLIST = belysning kommune kvalitet.Posisjonskvalitet.målemetodeHøyde kvalitet.Posisjonskvalitet.synbarhet lengde rutebetydning rutebredde rutetype ryddebredde stigning trafikkbelastning underlagstype
    ATTRCHOICE = Selected Attributes
    -> FriluftslivTilrettelegging (writer GML_1)
DateFormatter
    SRCFMT = Unknown - Automatic Detection
    INVALID_DATE_VALUE = _FME_NO_OP_
    FMT = ISO DateTime (%Y-%m-%dT%H:%M:%S)
    DATE_ATTR = datafangstdato,oppdateringsdato
    -> ListRenamer_8
ListRenamer_8
    LIST_NAME = _ar_list_opparbeiding{}.opparbeiding
    LEAVE_ORIG = No
    LIST_COMPONENT_NAMES = _ar_list_opparbeiding{},_ar_list_opparbeiding{},opparbeiding{},opparbeiding{}
    LIST_ACTION = Promote
    -> ListRenamer_9
ListRenamer_9
    LIST_NAME = _ar_list_tilgjengelighetsgruppe{}.tilgjengelighetsgruppe
    LEAVE_ORIG = No
    LIST_COMPONENT_NAMES = _ar_list_tilgjengelighetsgruppe{},_ar_list_tilgjengelighetsgruppe{},tilgjengelighetsgruppe{},tilgjengelighetsGruppe{}
    LIST_ACTION = Promote
    -> GeometryPropertySetter_5
GeometryPropertySetter_5
    SETTYPE_PARAM = Geometry Name
    OVERWRITE_CHOICE = Yes
    GEOM_NAME_FIELD = senterlinje
    SET -> AttributeRenamer_5
AttributeRenamer_5
    ATTR_LIST = lokalid,identifikasjon.Identifikasjon.lokalId,,malemetode,kvalitet.Posisjonskvalitet.målemetode,,malemetodehoyde,kvalitet.Posisjonskvalitet.målemetodeHøyde,,noyaktighet,kvalitet.Posisjonskvalitet.nøyaktighet,,noyaktighet,kvalitet.Posisjonskvalitet.nøyaktighetHøyde,,synbarhet,kvalitet.Posisjonskvalitet.synbarhet,,rutenr,rutenummer,,vedlikeh,vedlikeholdsansvarlig,,frilufteierforhold,friluftEierforhold,,rutemerking,merking,,rutefolger,ruteFølger,,spesialsykkelrutetype,spesialSykkelrutetype,,rutevanskelighetsgrad,ruteVanskelighetsgrad,,arutetype,annenRutetype,
    -> NullAttributeMapper_5
NullAttributeMapper_5
    SOURCE_ATTR_VAL = Null Empty
    NULL_TREATMENT = Missing
    ATTRLIST = annenRutetype belysning friluftEierforhold kommune kvalitet.Posisjonskvalitet.målemetode kvalitet.Posisjonskvalitet.målemetodeHøyde kvalitet.Posisjonskvalitet.nøyaktighet kvalitet.Posisjonskvalitet.nøyaktighetHøyde kvalitet.Posisjonskvalitet.synbarhet lengde rutebetydning rutebredde ruteFølger rutetype ruteVanskelighetsgrad stigning underlagstype
    ATTRCHOICE = Selected Attributes
    -> AnnenRute (writer GML_1)
DateFormatter_2
    SRCFMT = Unknown - Automatic Detection
    INVALID_DATE_VALUE = _FME_NO_OP_
    FMT = ISO DateTime (%Y-%m-%dT%H:%M:%S)
    DATE_ATTR = datafangstdato,oppdateringsdato
    -> ListRenamer_5
ListRenamer_5
    LIST_NAME = _fr_list_opparbeiding{}.opparbeiding
    LEAVE_ORIG = No
    LIST_COMPONENT_NAMES = _fr_list_opparbeiding{},_fr_list_opparbeiding{},opparbeiding{},opparbeiding{}
    LIST_ACTION = Promote
    -> ListRenamer_6
ListRenamer_6
    LIST_NAME = _fr_list_sfotrutetype{}.sfotrutetype
    LEAVE_ORIG = No
    LIST_COMPONENT_NAMES = _fr_list_sfotrutetype{},_fr_list_sfotrutetype{},sfotrutetype{},spesialFotrutetype{}
    LIST_ACTION = Promote
    -> ListRenamer_7
ListRenamer_7
    LIST_NAME = _fr_list_tilgjengelighetsgruppe{}.tilgjengelighetsgruppe
    LEAVE_ORIG = No
    LIST_COMPONENT_NAMES = _fr_list_tilgjengelighetsgruppe{},_fr_list_tilgjengelighetsgruppe{},tilgjengelighetsgruppe{},tilgjengelighetsgruppe{}
    LIST_ACTION = Promote
    -> GeometryPropertySetter_4
GeometryPropertySetter_4
    SETTYPE_PARAM = Geometry Name
    OVERWRITE_CHOICE = Yes
    GEOM_NAME_FIELD = senterlinje
    SET -> AttributeRenamer_4
AttributeRenamer_4
    ATTR_LIST = lokalid,identifikasjon.Identifikasjon.lokalId,,malemetode,kvalitet.Posisjonskvalitet.målemetode,,malemetodehoyde,kvalitet.Posisjonskvalitet.målemetodeHøyde,,noyaktighet,kvalitet.Posisjonskvalitet.nøyaktighet,,noyaktighet,kvalitet.Posisjonskvalitet.nøyaktighetHøyde,,synbarhet,kvalitet.Posisjonskvalitet.synbarhet,,rutenr,rutenummer,,vedlikeh,vedlikeholdsansvarlig,,frilufteierforhold,friluftEierforhold,,rutemerking,merking,,rutefolger,ruteFølger,,spesialsykkelrutetype,spesialSykkelrutetype,,rutevanskelighetsgrad,ruteVanskelighetsgrad,
    -> NullAttributeMapper_4
NullAttributeMapper_4
    SOURCE_ATTR_VAL = Null Empty
    NULL_TREATMENT = Missing
    ATTRLIST = belysning friluftEierforhold kommune kvalitet.Posisjonskvalitet.målemetodeHøyde kvalitet.Posisjonskvalitet.synbarhet lengde rutebetydning rutebredde rutetype ruteVanskelighetsgrad sesong stigning underlagstype
    ATTRCHOICE = Selected Attributes
    -> Fotrute (writer GML_1)
DateFormatter_4
    SRCFMT = Unknown - Automatic Detection
    INVALID_DATE_VALUE = _FME_NO_OP_
    FMT = ISO DateTime (%Y-%m-%dT%H:%M:%S)
    DATE_ATTR = datafangstdato,oppdateringsdato
    -> ListRenamer_3
ListRenamer_3
    LIST_NAME = _sl_list_opparbeiding{}.opparbeiding
    LEAVE_ORIG = No
    LIST_COMPONENT_NAMES = _sl_list_opparbeiding{},_sl_list_opparbeiding{},opparbeiding{},opparbeiding{}
    LIST_ACTION = Promote
    -> ListRenamer_4
ListRenamer_4
    LIST_NAME = _sl_list_tilgjengelighetsgruppe{}.tilgjengelighetsgruppe
    LEAVE_ORIG = No
    LIST_COMPONENT_NAMES = _sl_list_tilgjengelighetsgruppe{},_sl_list_tilgjengelighetsgruppe{},tilgjengelighetsgruppe{},tilgjengelighetsGruppe{}
    LIST_ACTION = Promote
    -> GeometryPropertySetter_2
GeometryPropertySetter_2
    SETTYPE_PARAM = Geometry Name
    OVERWRITE_CHOICE = Yes
    GEOM_NAME_FIELD = senterlinje
    SET -> AttributeRenamer_2
AttributeRenamer_2
    ATTR_LIST = lokalid,identifikasjon.Identifikasjon.lokalId,,malemetode,kvalitet.Posisjonskvalitet.målemetode,,malemetodehoyde,kvalitet.Posisjonskvalitet.målemetodeHøyde,,noyaktighet,kvalitet.Posisjonskvalitet.nøyaktighet,,noyaktighet,kvalitet.Posisjonskvalitet.nøyaktighetHøyde,,synbarhet,kvalitet.Posisjonskvalitet.synbarhet,,rutenr,rutenummer,,vedlikeh,vedlikeholdsansvarlig,,frilufteierforhold,friluftEierforhold,,rutemerking,merking,,rutefolger,ruteFølger,,rutevanskelighetsgrad,ruteVanskelighetsgrad,,spes_skiloypetype,spesialSkiløypetype,,antallskispor,antallSkispor,,skoytetrase,skøytetrase,
    -> NullAttributeMapper_2
NullAttributeMapper_2
    SOURCE_ATTR_VAL = Empty Null
    NULL_TREATMENT = Missing
    ATTRLIST = antallSkispor belysning friluftEierforhold kommune kvalitet.Posisjonskvalitet.målemetodeHøyde kvalitet.Posisjonskvalitet.synbarhet lengde rutebetydning rutebredde ruteFølger rutetype ruteVanskelighetsgrad ryddebredde spesialSkiløypetype stigning trafikkbelastning underlagstype
    ATTRCHOICE = Selected Attributes
    -> Skiløype (writer GML_1)
DateFormatter_5
    SRCFMT = Unknown - Automatic Detection
    INVALID_DATE_VALUE = _FME_NO_OP_
    FMT = ISO DateTime (%Y-%m-%dT%H:%M:%S)
    DATE_ATTR = datafangstdato,oppdateringsdato
    -> ListRenamer
ListRenamer
    LIST_NAME = _sr_list_opparbeiding{}.opparbeiding
    LEAVE_ORIG = No
    LIST_COMPONENT_NAMES = _sr_list_opparbeiding{},_sr_list_opparbeiding{},opparbeiding{},opparbeiding{}
    LIST_ACTION = Promote
    -> ListRenamer_2
ListRenamer_2
    LIST_NAME = _sr_list_tilgjengelighetsgruppe{}.tilgjengelighetsgruppe
    LEAVE_ORIG = No
    LIST_COMPONENT_NAMES = _sr_list_tilgjengelighetsgruppe{},_sr_list_tilgjengelighetsgruppe{},tilgjengelighetsgruppe{},tilgjengelighetsGruppe{}
    LIST_ACTION = Promote
    -> GeometryPropertySetter
GeometryPropertySetter
    SETTYPE_PARAM = Geometry Name
    OVERWRITE_CHOICE = Yes
    GEOM_NAME_FIELD = senterlinje
    SET -> AttributeRenamer
AttributeRenamer
    ATTR_LIST = lokalid,identifikasjon.Identifikasjon.lokalId,,malemetode,kvalitet.Posisjonskvalitet.målemetode,,malemetodehoyde,kvalitet.Posisjonskvalitet.målemetodeHøyde,,noyaktighet,kvalitet.Posisjonskvalitet.nøyaktighet,,noyaktighet,kvalitet.Posisjonskvalitet.nøyaktighetHøyde,,synbarhet,kvalitet.Posisjonskvalitet.synbarhet,,rutenr,rutenummer,,vedlikeh,vedlikeholdsansvarlig,,frilufteierforhold,friluftEierforhold,,rutemerking,merking,,rutefolger,ruteFølger,,spesialsykkelrutetype,spesialSykkelrutetype,,rutevanskelighetsgrad,ruteVanskelighetsgrad,
    -> NullAttributeMapper
NullAttributeMapper
    SOURCE_ATTR_VAL = Empty Null
    NULL_TREATMENT = Missing
    ATTRLIST = belysning friluftEierforhold kvalitet.Posisjonskvalitet.målemetodeHøyde kvalitet.Posisjonskvalitet.synbarhet lengde rutebetydning rutebredde ruteFølger rutetype ruteVanskelighetsgrad spesialSykkelrutetype stigning trafikkbelastning underlagstype kommune
    ATTRCHOICE = Selected Attributes
    -> Sykkelrute (writer GML_1)

Bookmark: Måldata gml
FriluftslivTilrettelegging (writer GML_1)
    attributes: identifikasjon.Identifikasjon.lokalId xml_buffer, datafangstdato xml_datetime, oppdateringsdato xml_datetime, kvalitet.Posisjonskvalitet.målemetode xml_buffer, kvalitet.Posisjonskvalitet.nøyaktighet xml_int64, kvalitet.Posisjonskvalitet.synbarhet xml_buffer, kvalitet.Posisjonskvalitet.målemetodeHøyde xml_buffer, kvalitet.Posisjonskvalitet.nøyaktighetHøyde xml_int64, opphav xml_buffer, kommune xml_buffer, informasjon xml_buffer, link xml_buffer, posisjon xml_geometry, vedlikeholdsansvarlig xml_buffer, tilrettelegging xml_buffer
AnnenRute (writer GML_1)
    attributes: identifikasjon.Identifikasjon.lokalId xml_buffer, datafangstdato xml_datetime, oppdateringsdato xml_datetime, kvalitet.Posisjonskvalitet.målemetode xml_buffer, kvalitet.Posisjonskvalitet.nøyaktighet xml_int64, kvalitet.Posisjonskvalitet.synbarhet xml_buffer, kvalitet.Posisjonskvalitet.målemetodeHøyde xml_buffer, kvalitet.Posisjonskvalitet.nøyaktighetHøyde xml_int64, opphav xml_buffer, kommune xml_buffer, informasjon xml_buffer, link xml_buffer, senterlinje xml_geometry, navn xml_buffer, rutenummer xml_int64, vedlikeholdsansvarlig xml_buffer, friluftEierforhold xml_buffer, belysning xml_buffer, merking xml_buffer, skilting xml_boolean, ruteFølger xml_buffer, rutebredde xml_buffer, opparbeiding{} xml_buffer, rutebetydning xml_buffer, ruteVanskelighetsgrad xml_buffer, underlagstype xml_buffer, lengde xml_int64, stigning xml_int64, tilgjengelighetsGruppe{} xml_buffer, rutetype xml_buffer,
      annenRutetype xml_buffer
Fotrute (writer GML_1)
    attributes: identifikasjon.Identifikasjon.lokalId xml_buffer, datafangstdato xml_datetime, oppdateringsdato xml_datetime, kvalitet.Posisjonskvalitet.målemetode xml_buffer, kvalitet.Posisjonskvalitet.nøyaktighet xml_int64, kvalitet.Posisjonskvalitet.synbarhet xml_buffer, kvalitet.Posisjonskvalitet.målemetodeHøyde xml_buffer, kvalitet.Posisjonskvalitet.nøyaktighetHøyde xml_int64, opphav xml_buffer, kommune xml_buffer, informasjon xml_buffer, link xml_buffer, senterlinje xml_geometry, navn xml_buffer, rutenummer xml_int64, vedlikeholdsansvarlig xml_buffer, friluftEierforhold xml_buffer, belysning xml_buffer, merking xml_buffer, skilting xml_boolean, ruteFølger xml_buffer, rutebredde xml_buffer, opparbeiding{} xml_buffer, rutebetydning xml_buffer, ruteVanskelighetsgrad xml_buffer, underlagstype xml_buffer, lengde xml_int64, stigning xml_int64, tilgjengelighetsGruppe{} xml_buffer, rutetype xml_buffer,
      spesialFotrutetype{} xml_buffer, sesong xml_buffer
Skiløype (writer GML_1)
    attributes: identifikasjon.Identifikasjon.lokalId xml_buffer, datafangstdato xml_datetime, oppdateringsdato xml_datetime, kvalitet.Posisjonskvalitet.målemetode xml_buffer, kvalitet.Posisjonskvalitet.nøyaktighet xml_int64, kvalitet.Posisjonskvalitet.synbarhet xml_buffer, kvalitet.Posisjonskvalitet.målemetodeHøyde xml_buffer, kvalitet.Posisjonskvalitet.nøyaktighetHøyde xml_int64, opphav xml_buffer, kommune xml_buffer, informasjon xml_buffer, link xml_buffer, senterlinje xml_geometry, navn xml_buffer, rutenummer xml_int64, vedlikeholdsansvarlig xml_buffer, friluftEierforhold xml_buffer, belysning xml_buffer, merking xml_buffer, skilting xml_boolean, ruteFølger xml_buffer, rutebredde xml_buffer, opparbeiding{} xml_buffer, rutebetydning xml_buffer, ruteVanskelighetsgrad xml_buffer, underlagstype xml_buffer, lengde xml_int64, stigning xml_int64, tilgjengelighetsGruppe{} xml_buffer, rutetype xml_buffer,
      spesialSkiløypetype xml_buffer, preparering xml_buffer, ryddebredde xml_buffer, antallSkispor xml_int64, skøytetrase xml_boolean
Sykkelrute (writer GML_1)
    attributes: identifikasjon.Identifikasjon.lokalId xml_buffer, datafangstdato xml_datetime, oppdateringsdato xml_datetime, kvalitet.Posisjonskvalitet.målemetode xml_buffer, kvalitet.Posisjonskvalitet.nøyaktighet xml_int64, kvalitet.Posisjonskvalitet.synbarhet xml_buffer, kvalitet.Posisjonskvalitet.målemetodeHøyde xml_buffer, kvalitet.Posisjonskvalitet.nøyaktighetHøyde xml_int64, opphav xml_buffer, kommune xml_buffer, informasjon xml_buffer, link xml_buffer, senterlinje xml_geometry, navn xml_buffer, rutenummer xml_int64, vedlikeholdsansvarlig xml_buffer, friluftEierforhold xml_buffer, belysning xml_buffer, merking xml_buffer, skilting xml_boolean, ruteFølger xml_buffer, rutebredde xml_buffer, opparbeiding{} xml_buffer, rutebetydning xml_buffer, ruteVanskelighetsgrad xml_buffer, underlagstype xml_buffer, lengde xml_int64, stigning xml_int64, tilgjengelighetsGruppe{} xml_buffer, rutetype xml_buffer,
      spesialSykkelrutetype xml_buffer, trafikkbelastning xml_buffer

Bookmark: Annenrute koblingstabeller
turogfriluftsruter.annenrute_opparbeiding (reader POSTGRES_1)
    attributes: objid int4,PRIKEY, opparbeiding int4
    -> Annenrute_opparbeiding_FeatureMerger [input 2]
turogfriluftsruter.annenrute_tilgjengelighetsgruppe (reader POSTGRES_1)
    attributes: objid int4,PRIKEY, tilgjengelighetsgruppe int4
    -> Annenrute_tilgjengelighetsgruppe_FeatureMerger [input 2]

Bookmark: Joiner inn felter med [0..*] multiplisitet for Annenrute
Annenrute_tilgjengelighetsgruppe_FeatureMerger: FeatureMerger
    JOIN_KEYS = @Value(objid) @Value(objid) NUM
    ATTR_CONFLICT_RES = Use Requestor
    ATTR_ACCUM_MODE = Merge Supplier
    MERGE_TYPE = Attributes Only
    PROCESS_DUPS = No
    LIST_NAME = _ar_list_tilgjengelighetsgruppe
    SUPPLIERS_FIRST = No
    IGNORE_NULLS = No
    MERGED -> Annenrute_opparbeiding_FeatureMerger [input 1]
    NOT_MERGED -> Annenrute_opparbeiding_FeatureMerger [input 1]
Annenrute_opparbeiding_FeatureMerger: FeatureMerger
    JOIN_KEYS = @Value(objid) @Value(objid) NUM
    ATTR_CONFLICT_RES = Use Requestor
    ATTR_ACCUM_MODE = Merge Supplier
    MERGE_TYPE = Attributes Only
    PROCESS_DUPS = No
    LIST_NAME = _ar_list_opparbeiding
    SUPPLIERS_FIRST = No
    IGNORE_NULLS = No
    NOT_MERGED -> DateFormatter
    MERGED -> DateFormatter

Bookmark: Fotrute koblingstabeller
turogfriluftsruter.fotrute_opparbeiding (reader POSTGRES_1)
    attributes: objid int4,PRIKEY, opparbeiding int4
    -> _fr_opparbeiding_FeatureMerger [input 2]
turogfriluftsruter.fotrute_sfotrutetype (reader POSTGRES_1)
    attributes: objid int4,PRIKEY, sfotrutetype varchar(80)
    -> _fr_sfotrutetype_FeatureMerger [input 2]
turogfriluftsruter.fotrute_tilgjengelighetsgruppe (reader POSTGRES_1)
    attributes: objid int4,PRIKEY, tilgjengelighetsgruppe int4
    -> Fotrute_tilgjengelighetsgruppe_FeatureMerger [input 2]

Bookmark: Joiner inn felter med [0..*] multiplisitet for Fotruter
Fotrute_tilgjengelighetsgruppe_FeatureMerger: FeatureMerger
    JOIN_KEYS = @Value(objid) @Value(objid) NUM
    ATTR_CONFLICT_RES = Use Requestor
    ATTR_ACCUM_MODE = Merge Supplier
    MERGE_TYPE = Attributes Only
    PROCESS_DUPS = No
    LIST_NAME = _fr_list_tilgjengelighetsgruppe
    SUPPLIERS_FIRST = No
    IGNORE_NULLS = No
    MERGED -> _fr_sfotrutetype_FeatureMerger [input 1]
    NOT_MERGED -> _fr_sfotrutetype_FeatureMerger [input 1]
_fr_sfotrutetype_FeatureMerger: FeatureMerger
    JOIN_KEYS = @Value(objid) @Value(objid) NUM
    ATTR_CONFLICT_RES = Use Requestor
    ATTR_ACCUM_MODE = Merge Supplier
    MERGE_TYPE = Attributes Only
    PROCESS_DUPS = No
    LIST_NAME = _fr_list_sfotrutetype
    SUPPLIERS_FIRST = No
    IGNORE_NULLS = No
    MERGED -> _fr_opparbeiding_FeatureMerger [input 1]
    NOT_MERGED -> _fr_opparbeiding_FeatureMerger [input 1]
_fr_opparbeiding_FeatureMerger: FeatureMerger
    JOIN_KEYS = @Value(objid) @Value(objid) NUM
    ATTR_CONFLICT_RES = Use Requestor
    ATTR_ACCUM_MODE = Merge Supplier
    MERGE_TYPE = Attributes Only
    PROCESS_DUPS = No
    LIST_NAME = _fr_list_opparbeiding
    SUPPLIERS_FIRST = No
    IGNORE_NULLS = No
    MERGED -> DateFormatter_2
    NOT_MERGED -> DateFormatter_2

Bookmark: Skiloype koblingstabeller
turogfriluftsruter.skiloype_opparbeiding (reader POSTGRES_1)
    attributes: objid int4,PRIKEY, opparbeiding int4
    -> Skiloype_opparbeiding_FeatureMerger [input 2]
turogfriluftsruter.skiloype_tilgjengelighetsgruppe (reader POSTGRES_1)
    attributes: objid int4,PRIKEY, tilgjengelighetsgruppe int4
    -> Skiloype_tilghengelighetsgruppe_FeatureMerger [input 2]

Bookmark: Joiner inn felter med [0..*] multiplisitet for Skiløype
Skiloype_opparbeiding_FeatureMerger: FeatureMerger
    JOIN_KEYS = @Value(objid) @Value(objid) NUM
    ATTR_CONFLICT_RES = Use Requestor
    ATTR_ACCUM_MODE = Merge Supplier
    MERGE_TYPE = Attributes Only
    PROCESS_DUPS = No
    LIST_NAME = _sl_list_opparbeiding
    SUPPLIERS_FIRST = No
    IGNORE_NULLS = No
    MERGED -> Skiloype_tilghengelighetsgruppe_FeatureMerger [input 1]
    NOT_MERGED -> Skiloype_tilghengelighetsgruppe_FeatureMerger [input 1]
Skiloype_tilghengelighetsgruppe_FeatureMerger: FeatureMerger
    JOIN_KEYS = @Value(objid) @Value(objid) STRING
    ATTR_CONFLICT_RES = Use Requestor
    ATTR_ACCUM_MODE = Merge Supplier
    MERGE_TYPE = Attributes Only
    PROCESS_DUPS = No
    LIST_NAME = _sl_list_tilgjengelighetsgruppe
    SUPPLIERS_FIRST = No
    IGNORE_NULLS = No
    NOT_MERGED -> DateFormatter_4
    MERGED -> DateFormatter_4

Bookmark: Sykkelrute koblingstabeller
turogfriluftsruter.sykkelrute_opparbeiding (reader POSTGRES_1)
    attributes: objid int4,PRIKEY, opparbeiding int4
    -> Sykkelrute_opparbeiding_FeatureMerger [input 2]
turogfriluftsruter.sykkelrute_tilgjengelighetsgruppe (reader POSTGRES_1)
    attributes: objid int4,PRIKEY, tilgjengelighetsgruppe int4
    -> Sykkelrute_tilgjengelighetsgruppe_FeatureMerger [input 2]

Bookmark: Joiner inn felter med [0..*] multiplisitet for Sykkelrute
Sykkelrute_opparbeiding_FeatureMerger: FeatureMerger
    JOIN_KEYS = @Value(objid) @Value(objid) NUM
    ATTR_CONFLICT_RES = Use Requestor
    ATTR_ACCUM_MODE = Merge Supplier
    MERGE_TYPE = Attributes Only
    PROCESS_DUPS = No
    LIST_NAME = _sr_list_opparbeiding
    SUPPLIERS_FIRST = No
    IGNORE_NULLS = No
    MERGED -> Sykkelrute_tilgjengelighetsgruppe_FeatureMerger [input 1]
    NOT_MERGED -> Sykkelrute_tilgjengelighetsgruppe_FeatureMerger [input 1]
Sykkelrute_tilgjengelighetsgruppe_FeatureMerger: FeatureMerger
    JOIN_KEYS = @Value(objid) @Value(objid) NUM
    ATTR_CONFLICT_RES = Use Requestor
    ATTR_ACCUM_MODE = Merge Supplier
    MERGE_TYPE = Attributes Only
    PROCESS_DUPS = No
    LIST_NAME = _sr_list_tilgjengelighetsgruppe
    SUPPLIERS_FIRST = No
    IGNORE_NULLS = No
    MERGED -> DateFormatter_5
    NOT_MERGED -> DateFormatter_5

FME custom transformer CreateClipper

Parameters:
- CLIPPERCOORDS = 253577 6650999 253577 6651246 253763 6651246 253763 6650999 253577 6650999   # Clipper Coordinate List
- CLIPPERCOORDSYS = EPSG:25833   # Clipper Coordinate System
- DESTCOORDSYS = "ESRIWKT|ETRS_1989_UTM_Zone_35N|PROJCS["ETRS_1989_UTM_Zone_35N",GEOGCS["GCS_ETRS_1989",DATUM["D_ETRS_1989",SPHEROID["GRS_1980",6378137.0,298.257222101]],PRIMEM["Greenwich",0.0],UNIT["Degree",0.0174532925199433]],PROJECTION["Transverse_Mercator"],PARAMETER["False_Easting",500000.0],PARAMETER["False_Northing",0.0],PARAMETER["Central_Meridian",27.0],PARAMETER["Scale_Factor",0.9996],PARAMETER["Latitude_Of_Origin",0.0],UNIT["Meter",1.0]]"   # Destination Coordinate System

Note: Creating geometry from / the Clipper coords
Creator
    GEOMTYPE = 2D Coordinate List
    COORDSYS = $(CLIPPERCOORDSYS)
    COORDS = $(CLIPPERCOORDS)
    NUM = 1
    CREATED -> BoundingBoxAccumulator
Note: Calculating the bounding / box (envelope) from the geometry
BoundingBoxAccumulator
    TOPFER_INDEX = No
    BOUNDING_BOX -> SpatialFilter [input 1]
    ORIGINAL -> SpatialFilter [input 2]
Note: If the geometry is equal to its / own bounding box - it is a rectangle!
SpatialFilter
    PREDICATES = EQUALS
    PASS_CRITERIA = Pass Against One Base
    USE_BOUNDING_BOX = No
    BASE_TYPE = Single Base
    MERGE_ATTRS = No
    CURVE_BOUNDARY_RULE_PARAM = Default Rule
    PREDATTR = _predicate
    PASSED -> Reprojector
    FAILED -> Reprojector_2
Note: If rectangle, reproject the / geometry to the destination / coordinate system
Reprojector
    INTERPOLATION_TYPE_NAME = Nearest Neighbor
    STROKE_ARCS = Yes
    RASTER_CELL_SIZE = Preserve Cells
    SOURCE = Read from feature
    DEST = $(DESTCOORDSYS)
    REPROJECTED -> BoundingBoxAccumulator_2
Note: Then calculate the bounding / box from the projected geoemtry
BoundingBoxAccumulator_2
    TOPFER_INDEX = No
    BOUNDING_BOX -> Reprojector_3
Note: Reproject the geometry back to / the DB coordsys (LL/EUREF89)
Reprojector_3
    INTERPOLATION_TYPE_NAME = Nearest Neighbor
    STROKE_ARCS = Yes
    RASTER_CELL_SIZE = Preserve Cells
    SOURCE = Read from feature
    DEST = EPSG:4258
    REPROJECTED -> GeometryFilter
Note: Reproject clipper to / the DB coordsys (LL/EUREF89)
Reprojector_2
    INTERPOLATION_TYPE_NAME = Nearest Neighbor
    STROKE_ARCS = Yes
    RASTER_CELL_SIZE = Preserve Cells
    SOURCE = Read from feature
    DEST = EPSG:4258
    REPROJECTED -> GeometryFilter
Note: Getting rid of dummies
GeometryFilter
    GEOM_PORT_NAMES = Area
    BREAK_AGG = No
    AREA -> reprojectBboxESRI_REPROJECTED_2 (output)
reprojectBboxESRI_REPROJECTED_2 (output)
