FME workspace nvdbtrafikkulykker_postgis2gml.fmw
# Copyright: (c) xgrimor 2015
# Licence: <your licence>
Shutdown Python:
      # -*- coding: utf-8 -*-
      #-------------------------------------------------------------------------------
      # Name:        zipfiles.py
      # Purpose:     Pakker filer i output folderen
      #
      # Author:      xsunknu
      #
      # Created:     18.09.2015
      # Copyright:   (c) xsunknu 2015
      # Licence:     <your licence>
      #-------------------------------------------------------------------------------

      import sys, os, zipfile, fme

      def zip(gmlfile, zfile):
          from os.path import basename

          # Lager korresponderende zip-fil av gml-fil
          if os.path.isfile(zfile):
              os.remove(zfile)

          zf = zipfile.ZipFile(zfile, "w", zipfile.ZIP_DEFLATED)

          # Ønsker ikke full sti inn i ZIP-filen
          arcname = basename(gmlfile)

          # ZIP-formatet støtter ikke non-ascii tegn
          # Erstatter AØÅæøå med ascii-tegn
          arcname = arcname.replace('\xc6', 'E')
          arcname = arcname.replace('\xd8', 'O')
          arcname = arcname.replace('\xc5', 'A')
          arcname = arcname.replace('\xe6', 'e')
          arcname = arcname.replace('\xf8', 'o')
          arcname = arcname.replace('\xe5', 'a')

          zf.write(gmlfile, arcname)
          zf.close()
          os.remove(gmlfile)

          return

      def main():

          # Kjøres ikke på FME Server, da FME Server selv sørger for pakkingen
          if not 'FME_SERVER_DEST_DIR' in fme.macroValues:
              if 'FANOUT_FOLDER' in fme.macroValues:
                  path = fme.macroValues['FANOUT_FOLDER']
                  for dirpath, dnames, fnames in os.walk(path):
                      for f in fnames:
                          if f.endswith(".gml"):
                              # Scanner gjennom alle gml-filer
                              gmlfile = os.path.join(path, f)
                              zfile = os.path.splitext(gmlfile)[0] + '.zip'
                              if os.path.isfile(zfile):

                                  # Korresponderende ZIP-fil finnes, sjekker timestamps
                                  gmltstamp = os.stat(gmlfile).st_mtime
                                  ziptstamp = os.stat(zfile).st_mtime

                                  if gmltstamp > ziptstamp:
                                      # gml-fil er nyere enn ZIP-fila, ZIP-fila oppdateres
                                      # gml-fila slettes
                                      try:
                                          zip(gmlfile, zfile)
                                      except:
                                          print 'Kunne ikke pakke: ' + gmlfile
                                  else:
                                      # gml-fila er eldre enn ZIP-fila
                                      # gml-fila slettes
                                      try:
                                          os.remove(gmlfile)
                                      except:
                                          print 'Kunne ikke slette: ' + gmlfile
                              else:
                                  # ZIP-fila eksisterer ikke og lages
                                  # gml-fila slettes
                                  try:
                                      zip(gmlfile, zfile)
                                  except:
                                      print 'Kunne ikke pakke: ' + gmlfile


      if __name__ == '__main__':
          main()

Parameters:
- KNR =   # Kommune(r)
- FNR =   # Fylke(r)
- CLIPPERCOORDS =   # Clipper coordinates
- CLIPPER_EPSG_CODE =   # Clipper coordinate system
- CLIPPER_FILE =   # "" Clipper file (any format)
- OUTPUT_EPSG_CODE = 25833   # Destination coordinate system
- FANOUT =   # Fanout områder
- DestDataset_GML = $(FME_MF_DIR)Trafikkulykker.gml   # Destination Geography Markup Language (GML) File
- CONFIG_FILE:   # Python Script
      #-------------------------------------------------------------------------------
      # Name:        GetConfigFile
      # Purpose:
      #
      # Author:      xsunknu
      #
      # Created:     21.08.2015
      # Copyright:   (c) xsunknu 2015
      # Licence:     <your licence>
      #-------------------------------------------------------------------------------
      
      import os, fme
      
      fmwdir = fme.macroValues['FME_MF_DIR']
      fmwfile = fme.macroValues['FME_MF_NAME']
      
      fmwfile = os.path.join(fmwdir, fmwfile)
      configfile = os.path.splitext(fmwfile)[0] + '_config.xml'
      
      return configfile
- PG_DB:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgdb').text
      
      return value
- PG_HOST:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pghost').text
      
      return value
- PG_PORT:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgport').text
      
      return value
- PG_USER:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pguser').text
      
      return value
- PG_PWD:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgpwd').text
      
      return value
- SPATIAL_FILTER:   # Python Script
      #-------------------------------------------------------------------------------
      # Name:        SetSpatialFilter
      # Purpose:
      #
      # Author:      xsunknu
      #
      # Created:     21.08.2015
      # Copyright:   (c) xsunknu 2015
      # Licence:     <your licence>
      #-------------------------------------------------------------------------------
      
      import fme
      
      spatialfilter = 'Intersects'
      
      knr = fme.macroValues['KNR']
      fnr = fme.macroValues['FNR']
      coords = fme.macroValues['CLIPPERCOORDS']
      file = fme.macroValues['CLIPPER_FILE']
      
      if knr == '' and fnr == '' and coords == '' and file == '':
          spatialfilter = '<No Spatial Filter>'
      
      return spatialfilter
- CLIPPERCOORDSYS:   # Python Script
      #-------------------------------------------------------------------------------
      # Name:        SetCoordinateSystem
      # Purpose:
      #
      # Author:      xsunknu
      #
      # Created:     21.08.2015
      # Copyright:   (c) xsunknu 2015
      # Licence:     <your licence>
      #-------------------------------------------------------------------------------
      
      import os, fme
      
      EPSGvalue = fme.macroValues['CLIPPER_EPSG_CODE']
      EPSGcode  = 'EPSG:' + EPSGvalue
      
      return EPSGcode
- FIXEDCLIPPERCOORDS:   # Python Script
      #-------------------------------------------------------------------------------
      # Name:        FixClipperCoords
      # Purpose:
      #
      # Author:      xsunknu
      #
      # Created:     21.08.2015
      # Copyright:   (c) xsunknu 2015
      # Licence:     <your licence>
      #-------------------------------------------------------------------------------
      
      import fme
      clippercoords = fme.macroValues['CLIPPERCOORDS']
      
      if clippercoords == '':
          clippercoords = '1 1'
      
      return clippercoords
- UNDERTEMA = Trafikkulykker   # Undertema
- HOVEDTEMA = Samferdsel   # Hovedtema
- DESTCOORDSYS:   # Python Script
      #-------------------------------------------------------------------------------
      # Name:        SetCoordinateSystem
      # Purpose:
      #
      # Author:      xsunknu
      #
      # Created:     21.08.2015
      # Copyright:   (c) xsunknu 2015
      # Licence:     <your licence>
      #-------------------------------------------------------------------------------
      
      import os, fme
      
      EPSGvalue = fme.macroValues['OUTPUT_EPSG_CODE']
      EPSGcode  = 'EPSG:' + EPSGvalue
      
      return EPSGcode
- FANOUT_FOLDER:   # Python Script
      #-------------------------------------------------------------------------------
      # Name:        GetConfigFile
      # Purpose:
      #
      # Author:      xsunknu
      #
      # Created:     21.08.2015
      # Copyright:   (c) xsunknu 2015
      # Licence:     <your licence>
      #-------------------------------------------------------------------------------
      
      import os, fme
      from xml.etree import ElementTree as ET
      
      if 'FME_SERVER_DEST_DIR' in fme.macroValues:
          value = fme.macroValues['FME_SERVER_DEST_DIR']
      else:
          #Read XML config file
          configtree = ET.parse(fme.macroValues['CONFIG_FILE'])
          configdoc = configtree.getroot()
          value = configdoc.find('destdir').text
      
      return value
- LOG_FILE:   # Python Script
      #-------------------------------------------------------------------------------
      # Name:        GetConfigFile
      # Purpose:
      #
      # Author:      xsunknu
      #
      # Created:     21.08.2015
      # Copyright:   (c) xsunknu 2015
      # Licence:     <your licence>
      #-------------------------------------------------------------------------------
      
      import os, uuid, fme
      
      fmwdir = fme.macroValues['FME_MF_DIR']
      fmwfile = fme.macroValues['FME_MF_NAME']
      
      logdir = os.path.join(fmwdir, 'log')
      if not os.path.isdir(logdir):
          os.mkdir(logdir)
      
      logfile = os.path.splitext(fmwfile)[0] + '_' + str(uuid.uuid1()).replace('-','') + '.log'
      logfile = os.path.join(logdir, logfile)
      
      return logfile

Readers:
- POSTGIS_1: POSTGIS from $(PG_DB)

Writers:
- GML_1: GML to $(DestDataset_GML)

CreateClipper
    CLIPPERCOORDSYS = $(CLIPPERCOORDSYS)
    CLIPPERCOORDS = $(FIXEDCLIPPERCOORDS)
    DESTCOORDSYS = $(DESTCOORDSYS)
    -> Clipper [input 1]
    -> FeatureReader_3
DateFormatter
    FMT = ISO Date (%Y-%m-%d)
    DATE_ATTR = nvdb_registreringsdatofagdata,nvdb_ulykkesdato
    SRCFMT = Unknown - Automatic Detection
    INVALID_DATE_VALUE = _FME_NO_OP_
    -> DateFormatter_2
DateFormatter_2
    FMT = ISO DateTime (%Y-%m-%dT%H:%M:%S)
    DATE_ATTR = datauttaksdato
    SRCFMT = Unknown - Automatic Detection
    INVALID_DATE_VALUE = _FME_NO_OP_
    -> AttributeRenamer
AttributeRenamer
    ATTR_LIST = nvdb_alvorligsteskadegrad,alvorligsteSkadegrad,,nvdb_antallalvorligskadet,antallAlvorligSkadet,,nvdb_antalldrepteiulykken,antallDrepteIUlykken,,nvdb_antallenheter,antallEnheter,,nvdb_antallkjoerefelt,antallKjørefelt,,nvdb_antalllettereskadet,antallLettereSkadet,,nvdb_antallmegetalvorligskadet,antallMegetAlvorligSkadet,,nvdb_bebyggelse,bebyggelse,,nvdb_dekketype,dekketype,,nvdb_fartsgrense,fartsgrense,,nvdb_felttype,felttype,,nvdb_foereforhold,føreforhold,,nvdb_historiskhp,historiskHp,,nvdb_historiskkilometerverdi,historiskKilometerverdi,,nvdb_historiskvegkategori,historiskVegkategori,,nvdb_historiskvegnummer,historiskVegnummer,,nvdb_historiskvegstatus,historiskVegstatus,,nvdb_kommunenr,kommunenr,,nvdb_lysforhold,lysforhold,,nvdb_midtdeler,midtdeler,,nvdb_registreringsdatofagdata,registreringsdatoFagdata,,nvdb_stedfestingensnoeyaktighet,stedfestingensNøyaktighet,,nvdb_stedsforhold,stedsforhold,,nvdb_temperatur,temperatur,,nvdb_uhellkategori,uhellKategori,,nvdb_uhellskode,uhellskode,,nvdb_ukedag,ukedag,,nvdb_ulykkesdato,ulykkesdato,,nvdb_ulykkestidspunkt,ulykkestidspunkt,,nvdb_vaerforhold,værforhold,,nvdb_vegbredde,vegbredde,,nvdb_vegnavn,vegnavn,,nvdb_vegtype,vegtype,
    -> GeometryPropertySetter
GeometryPropertySetter
    OVERWRITE_CHOICE = Yes
    SETTYPE_PARAM = Geometry Name
    GEOM_NAME_FIELD = posisjon
    SET -> NullAttributeMapper
NullAttributeMapper
    ATTRLIST = antallKjørefelt kommunenr temperatur vegbredde historiskHp historiskKilometerverdi historiskVegkategori historiskVegnummer historiskVegstatus
    SOURCE_ATTR_VAL = Empty Null
    NULL_TREATMENT = Missing
    ATTRCHOICE = Selected Attributes
    -> NullAttributeMapper_2
NullAttributeMapper_2
    NEW_VALUE = 0
    ATTRLIST = antallDrepteIUlykken
    SOURCE_ATTR_VAL = Empty Null
    NULL_TREATMENT = New Value
    ATTRCHOICE = Selected Attributes
    -> Trafikkulykke (writer GML_1)
Trafikkulykke (writer GML_1)
    attributes: datauttaksdato xml_datetime, alvorligsteSkadegrad xml_buffer, alvorligsteSkadegrad.codeSpace xml_buffer, ulykkesdato xml_date, ulykkestidspunkt xml_buffer, ukedag xml_buffer, ukedag.codeSpace xml_buffer, registreringsdatoFagdata xml_date, uhellKategori xml_buffer, uhellKategori.codeSpace xml_buffer, uhellskode xml_buffer, uhellskode.codeSpace xml_buffer, antallEnheter xml_int64, antallDrepteIUlykken xml_int64, antallMegetAlvorligSkadet xml_int64, antallAlvorligSkadet xml_int64, antallLettereSkadet xml_int64, vegtype xml_buffer, vegtype.codeSpace xml_buffer, stedsforhold xml_buffer, stedsforhold.codeSpace xml_buffer, midtdeler xml_buffer, midtdeler.codeSpace xml_buffer, dekketype xml_buffer, dekketype.codeSpace xml_buffer, føreforhold xml_buffer, føreforhold.codeSpace xml_buffer, værforhold xml_buffer, værforhold.codeSpace xml_buffer, lysforhold xml_buffer,
      lysforhold.codeSpace xml_buffer, felttype xml_buffer, felttype.codeSpace xml_buffer, antallKjørefelt xml_int64, bebyggelse xml_buffer, bebyggelse.codeSpace xml_buffer, vegbredde xml_real64, fartsgrense xml_buffer, fartsgrense.codeSpace xml_buffer, temperatur xml_int64, kommunenr xml_int64, historiskVegstatus xml_buffer, historiskVegstatus.codeSpace xml_buffer, historiskVegkategori xml_buffer, historiskVegkategori.codeSpace xml_buffer, historiskVegnummer xml_int64, historiskHp xml_int64, historiskKilometerverdi xml_int64, vegnavn xml_buffer, stedfestingensNøyaktighet xml_buffer, stedfestingensNøyaktighet.codeSpace xml_buffer, posisjon xml_geometry

Bookmark: Fylke and/or kommune clippers
Creator_2
    GEOMTYPE = Geometry Object
    NUM = 1
    CREATED -> AttributeCreator_8
AttributeCreator_8
    ATTR_LIST = _clippercoords,$(CLIPPERCOORDS),_clipper_file,$(CLIPPER_FILE),_fnr,$(FNR),_knr,$(KNR)
    -> Tester_4
Note: Sender inn en dummy initiator / dersom alle klippeparametrene er / blanke siden Luftfartshindere / strekker seg utover fastlands- / Norge
Tester_4
    BOOL_OP = AND
    TEST_DESCRIPTION = ""
    TEST_MODE = Automatic
    TEST_CLAUSE:
      TEST _clipper_file ATTRIBUTE_IS_EMPTY ""
      TEST _clippercoords ATTRIBUTE_IS_EMPTY ""
      TEST _fnr ATTRIBUTE_IS_EMPTY ""
      TEST _knr ATTRIBUTE_IS_EMPTY ""
    PASSED -> Reprojector_2
admingrense.fylkeflate (reader POSTGIS_1)
    attributes: fylkeid int4, navn varchar(80)
    -> Tester
Tester
    BOOL_OP = OR
    TEST_DESCRIPTION = ""
    TEST_MODE = Automatic
    TEST_CLAUSE = TEST @Value(fylkeid) IN $(FNR)
    PASSED -> Reprojector_2
admingrense.kommuneflate (reader POSTGIS_1)
    attributes: kommuneid int4, navn varchar(80)
    -> Tester_2
Tester_2
    BOOL_OP = OR
    TEST_DESCRIPTION = ""
    TEST_MODE = Automatic
    TEST_CLAUSE = TEST @Value(kommuneid) IN $(KNR)
    PASSED -> Reprojector_2
Reprojector_2
    SOURCE = Read from feature
    DEST = EPSG:4258
    INTERPOLATION_TYPE_NAME = Nearest Neighbor
    RASTER_CELL_SIZE = Preserve Cells
    REPROJECTED -> Clipper [input 1]
    REPROJECTED -> FeatureReader_3

Bookmark: Clipper file (any format)
Creator
    GEOMTYPE = Geometry Object
    NUM = 1
    CREATED -> FeatureReader
FeatureReader
    ATTR_ACCUM_MODE = Only Use Result
    INTERACT = $(SPATIAL_FILTER)
    COMBINE_GEOM = Use Result
    DATASET = $(CLIPPER_FILE)
    GENERIC_REAL_FORMAT = GUESS_FROM_EXTENSION
    ATTRIBUTES = NewFeatureType,
    OUTPUT_FEATURES_DISPLAY = Based on Connections
    FORMAT = GENERIC
    FEATURETYPES_RADIO = FEATURETYPES
    <OTHER> -> Reprojector_3
Reprojector_3
    SOURCE = Read from feature
    DEST = EPSG:4258
    INTERPOLATION_TYPE_NAME = Nearest Neighbor
    RASTER_CELL_SIZE = Preserve Cells
    REPROJECTED -> Clipper [input 1]
    REPROJECTED -> FeatureReader_3

Bookmark: Leser features og relaterte data
FeatureReader_3
    POSTGIS_PORT = $(PG_PORT)
    COMBINE_GEOM = Use Result
    POSTGIS_HOST = $(PG_HOST)
    ATTR_ACCUM_MODE = Only Use Result
    FEATURETYPES_RADIO = FEATURETYPES
    POSTGIS_SCHEMALIST = nvdb_trafikkulykker
    INTERACT = $(SPATIAL_FILTER)
    ATTRIBUTES = nvdb_trafikkulykker.trafikkulykke,"objid,objtype,nvdb_alvorligsteskadegrad,nvdb_ulykkesdato,nvdb_ukedag,nvdb_registreringsdatofagdata,nvdb_uhellkategori,nvdb_uhellskode,nvdb_antallenheter,nvdb_antalldrepteiulykken,nvdb_antallmegetalvorligskadet,nvdb_antallalvorligskadet,nvdb_antalllettereskadet,nvdb_vegtype,nvdb_stedsforhold,nvdb_midtdeler,nvdb_dekketype,nvdb_foereforhold,nvdb_vaerforhold,nvdb_lysforhold,nvdb_felttype,nvdb_antallkjoerefelt,nvdb_bebyggelse,nvdb_vegbredde,nvdb_fartsgrense,nvdb_temperatur,nvdb_kommunenr,nvdb_historiskvegstatus,nvdb_historiskvegkategori,nvdb_historiskvegnummer,nvdb_historiskhp,nvdb_historiskkilometerverdi,nvdb_vegnavn,nvdb_stedfestingensnoeyaktighet,datauttaksdato,nvdb_ulykkestidspunkt"
    OUTPUT_FEATURES_DISPLAY = Based on Connections
    POSTGIS_CLIP_TO_ENVELOPE = NO
    POSTGIS_USE_TRUE_POSTGIS_TYPES = yes
    FORMAT = POSTGIS
    POSTGIS_PASSWORD = $(PG_PWD)
    FEATURETYPES = nvdb_trafikkulykker.trafikkulykke
    POSTGIS_USER_NAME = $(PG_USER)
    POSTGIS_USE_SEARCH_ENVELOPE = NO
    DATASET = $(PG_DB)
    POSTGIS_DISABLE_COLLECTION_SPLITTING = yes
    POSTGIS_QUERY_FEATURE_TYPES_FOR_MERGE_FILTERS = Yes
    nvdb_trafikkulykker.trafikkulykke -> AttributeCreator_12
AttributeCreator_12
    ATTR_LIST = _clippercoords,$(CLIPPERCOORDS),_clipper_file,$(CLIPPER_FILE),_fnr,$(FNR),_knr,$(KNR)
    -> TestFilter
TestFilter
    DEFAULT_VALUE = <UNFILTERED>
    TEST_LIST:
      BOOL_OP,AND,COMPOSITE_TEST,<Unused>,TEST_CLAUSE,"TEST _clipper_file ATTRIBUTE_IS_EMPTY """"
      TEST _clippercoords ATTRIBUTE_IS_EMPTY """"
      TEST _fnr ATTRIBUTE_IS_EMPTY """"
      TEST _knr ATTRIBUTE_IS_EMPTY """"",Landsdekkende,BOOL_OP,AND,COMPOSITE_TEST,<Unused>,TEST_CLAUSE,"TEST _clipper_file ATTRIBUTE_IS_EMPTY """"
      TEST _clippercoords ATTRIBUTE_IS_EMPTY """"
      TEST _fnr NOT_ATTRIBUTE_IS_EMPTY """"
      TEST _knr ATTRIBUTE_IS_EMPTY """"",Fylkesvis,BOOL_OP,AND,COMPOSITE_TEST,<Unused>,TEST_CLAUSE,"TEST _clipper_file ATTRIBUTE_IS_EMPTY """"
      TEST _clippercoords ATTRIBUTE_IS_EMPTY """"
      TEST _fnr ATTRIBUTE_IS_EMPTY """"
      TEST _knr NOT_ATTRIBUTE_IS_EMPTY """"",Kommunevis
    Landsdekkende -> SosiFilenameSetter
    Fylkesvis -> Clipper [input 2]
    Kommunevis -> Clipper [input 2]
    <UNFILTERED> -> Clipper [input 2]

Bookmark: Klipper
Clipper
    BOUNDARY_CASES = Treat as Inside
    ATTR_ACCUM_MODE = Merge Clipper
    ATTR_CONFLICT_RES = Use Clippee
    CLIP_TYPE = Multiple Clippers
    CLIPPED_ATTR = _clipped
    CREATE_AGGREGATES = No
    PRESERVE_CLIPPEE_EXTENTS = No
    INSIDE -> SosiFilenameSetter

Bookmark: Tagger og reprojiserer
SosiFilenameSetter
    KOMMUNEID = @Value(kommuneid)
    Hovedtema = $(HOVEDTEMA)
    _KNR = @Value(_knr)
    FYLKEID = @Value(fylkeid)
    OUTPUT_EPSG_CODE = $(OUTPUT_EPSG_CODE)
    PG_PWD:
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------

      import fme
      from xml.etree import ElementTree as ET

      #Read XML config file
      configtree = ET.parse(fme.macroValues['CONFIG_FILE'])
      configdoc = configtree.getroot()
      value = configdoc.find('pgpwd').text

      return value
    _CREATION_INSTANCE = @Value(_creation_instance)
    PG_USER:
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------

      import fme
      from xml.etree import ElementTree as ET

      #Read XML config file
      configtree = ET.parse(fme.macroValues['CONFIG_FILE'])
      configdoc = configtree.getroot()
      value = configdoc.find('pguser').text

      return value
    _FNR = @Value(_fnr)
    _CLIPPERCOORDS = @Value(_clippercoords)
    PG_PORT:
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------

      import fme
      from xml.etree import ElementTree as ET

      #Read XML config file
      configtree = ET.parse(fme.macroValues['CONFIG_FILE'])
      configdoc = configtree.getroot()
      value = configdoc.find('pgport').text

      return value
    Undertema = $(UNDERTEMA)
    PG_DB:
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------

      import fme
      from xml.etree import ElementTree as ET

      #Read XML config file
      configtree = ET.parse(fme.macroValues['CONFIG_FILE'])
      configdoc = configtree.getroot()
      value = configdoc.find('pgdb').text

      return value
    FANOUT = $(FANOUT)
    _CLIPPED = @Value(_clipped)
    _CLIPPER_FILE = @Value(_clipper_file)
    PG_HOST:
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------

      import fme
      from xml.etree import ElementTree as ET

      #Read XML config file
      configtree = ET.parse(fme.macroValues['CONFIG_FILE'])
      configdoc = configtree.getroot()
      value = configdoc.find('pghost').text

      return value
    -> Reprojector
Reprojector
    SOURCE = Read from feature
    DEST = $(DESTCOORDSYS)
    INTERPOLATION_TYPE_NAME = Nearest Neighbor
    RASTER_CELL_SIZE = Preserve Cells
    REPROJECTED -> FeatureTypeFilter
FeatureTypeFilter
    ATTRIBUTES = nvdb_trafikkulykker.trafikkulykke,<BLANK>,<UNFILTERED>
    nvdb_trafikkulykker.trafikkulykke -> DateFormatter

FME custom transformer SosiFilenameSetter

Parameters:
- OUTPUT_EPSG_CODE = 25832   # Destination coordinate system
- FANOUT = Kommuner   # Fanout områder
- _CLIPPED = @Value(_clipped)   # Clipped
- _CLIPPER_FILE = @Value(_clipper_file)   # Clipper File
- _CLIPPERCOORDS = @Value(_clippercoords)   # Clippercoords
- _CREATION_INSTANCE = @Value(_creation_instance)   # Creation Instance
- _FNR = @Value(_fnr)   # Fnr
- _KNR = @Value(_knr)   # Knr
- FYLKEID = @Value(fylkeid)   # fylkeid
- KOMMUNEID = @Value(kommuneid)   # kommuneid
- Hovedtema =
- Undertema =
- PG_DB:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgdb').text
      
      return value
- PG_HOST:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pghost').text
      
      return value
- PG_PORT:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgport').text
      
      return value
- PG_PWD:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgpwd').text
      
      return value
- PG_USER:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pguser').text
      
      return value

Input (input)
    -> ParameterFetcher
ParameterFetcher
    ATTR_LIST = _output_epsg_code {$(OUTPUT_EPSG_CODE)} _fanout {$(FANOUT)}
    -> AttributeValueMapper
Note: Fikser kjente feil i kommunenummer
AttributeValueMapper
    DEFAULT_VALUE = @Value(kommuneid)
    LUT = 1901,1903
    SRC = kommuneid
    VAL_ATTR = kommuneid
    DIRECTION = Forward (Source To Destination)
    -> TestFilter_2
TestFilter_2
    DEFAULT_VALUE = Ufiltrert
    TEST_LIST = BOOL_OP,OR,COMPOSITE_TEST,<Unused>,TEST_CLAUSE,"TEST $(FANOUT) = Kommuner",Kommuner,BOOL_OP,OR,COMPOSITE_TEST,<Unused>,TEST_CLAUSE,"TEST $(FANOUT) = Fylker",Fylker
    Kommuner -> Joiner
    Ufiltrert -> AttributeCreator_13
    Fylker -> Joiner_2
Joiner
    MATCH_RULE_DISPLAY = Must Match Exactly One (1:1)
    POSTGIS_HOST = $(PG_HOST)
    POSTGIS_QUERY_FEATURE_TYPES_FOR_MERGE_FILTERS = Yes
    JOIN_KEYS = kommuneid kommuneid
    TABLE = admingrense.kommuner
    POSTGIS_USER_NAME = $(PG_USER)
    POSTGIS_PASSWORD = $(PG_PWD)
    DATASET = $(PG_DB)
    POSTGIS_DISABLE_COLLECTION_SPLITTING = yes
    POSTGIS_PORT = $(PG_PORT)
    CACHE_SIZE = 5000
    PREFETCH_EXHAUSTIVE = Yes
    POSTGIS_USE_TRUE_POSTGIS_TYPES = yes
    FORMAT = POSTGIS
    ADDED_FIELDS = navn
    JOINED -> StringReplacer
Joiner_2
    MATCH_RULE_DISPLAY = Must Match Exactly One (1:1)
    POSTGIS_HOST = $(PG_HOST)
    POSTGIS_QUERY_FEATURE_TYPES_FOR_MERGE_FILTERS = Yes
    JOIN_KEYS = fylkeid fylkeid
    TABLE = admingrense.fylkeflate
    POSTGIS_USER_NAME = $(PG_USER)
    POSTGIS_PASSWORD = $(PG_PWD)
    DATASET = $(PG_DB)
    POSTGIS_DISABLE_COLLECTION_SPLITTING = yes
    POSTGIS_PORT = $(PG_PORT)
    CACHE_SIZE = 5000
    PREFETCH_EXHAUSTIVE = Yes
    POSTGIS_USE_TRUE_POSTGIS_TYPES = yes
    FORMAT = POSTGIS
    ADDED_FIELDS = navn
    JOINED -> StringReplacer
StringReplacer
    SRC_ATTRS = navn
    REPLACE_TEXT = _
    REGEXP = no
    FIND_TEXT = " "
    CASE = no
    NO_MATCH = _FME_NO_OP_
    -> AttributeCreator_13
AttributeCreator_13
    ATTR_LIST = sosifile,"FME_CONDITIONAL:DEFAULT_VALUE'$(Hovedtema)_$(OUTPUT_EPSG_CODE)_$(Undertema)_GML'BOOL_OP;OR;COMPOSITE_TEST;<Unused>;TEST $(FANOUT) LIKE Kommuner'$(Hovedtema)_@PadLeft(@Value(kommuneid),4,0)_@Value(navn)_$(OUTPUT_EPSG_CODE)_$(Undertema)_GML'BOOL_OP;OR;COMPOSITE_TEST;<Unused>;TEST $(FANOUT) LIKE Fylker'$(Hovedtema)_@PadLeft(@Value(fylkeid),2,0)_@Value(navn)_$(OUTPUT_EPSG_CODE)_$(Undertema)_GML'BOOL_OP;OR;COMPOSITE_TEST;<Unused>;TEST $(FANOUT) LIKE Norge'$(Hovedtema)_0000_Norge_$(OUTPUT_EPSG_CODE)_$(Undertema)_GML'FME_NUM_CONDITIONS4___"
    -> Output (output)
Output (output)

FME custom transformer CreateClipper

Parameters:
- CLIPPERCOORDS = 253577 6650999 253577 6651246 253763 6651246 253763 6650999 253577 6650999   # Clipper Coordinate List
- CLIPPERCOORDSYS = EPSG:25833   # Clipper Coordinate System
- DESTCOORDSYS = "ESRIWKT|ETRS_1989_UTM_Zone_35N|PROJCS["ETRS_1989_UTM_Zone_35N",GEOGCS["GCS_ETRS_1989",DATUM["D_ETRS_1989",SPHEROID["GRS_1980",6378137.0,298.257222101]],PRIMEM["Greenwich",0.0],UNIT["Degree",0.0174532925199433]],PROJECTION["Transverse_Mercator"],PARAMETER["False_Easting",500000.0],PARAMETER["False_Northing",0.0],PARAMETER["Central_Meridian",27.0],PARAMETER["Scale_Factor",0.9996],PARAMETER["Latitude_Of_Origin",0.0],UNIT["Meter",1.0]]"   # Destination Coordinate System

Note: Creating geometry from / the Clipper coords
Creator
    GEOMTYPE = 2D Coordinate List
    COORDS = $(CLIPPERCOORDS)
    COORDSYS = $(CLIPPERCOORDSYS)
    NUM = 1
    CREATED -> BoundingBoxAccumulator
Note: Calculating the bounding / box (envelope) from the geometry
BoundingBoxAccumulator
    TOPFER_INDEX = No
    BOUNDING_BOX -> SpatialFilter [input 1]
    ORIGINAL -> SpatialFilter [input 2]
Note: If the geometry is equal to its / own bounding box - it is a rectangle!
SpatialFilter
    USE_BOUNDING_BOX = No
    PREDICATES = EQUALS
    PASS_CRITERIA = Pass Against One Base
    CURVE_BOUNDARY_RULE_PARAM = Default Rule
    MERGE_ATTRS = No
    BASE_TYPE = Single Base
    PREDATTR = _predicate
    PASSED -> Reprojector
    FAILED -> Reprojector_2
Note: If rectangle, reproject the / geometry to the destination / coordinate system
Reprojector
    SOURCE = Read from feature
    DEST = $(DESTCOORDSYS)
    INTERPOLATION_TYPE_NAME = Nearest Neighbor
    STROKE_ARCS = Yes
    RASTER_CELL_SIZE = Preserve Cells
    REPROJECTED -> BoundingBoxAccumulator_2
Note: Then calculate the bounding / box from the projected geoemtry
BoundingBoxAccumulator_2
    TOPFER_INDEX = No
    BOUNDING_BOX -> Reprojector_3
Note: Reproject the geometry back to / the DB coordsys (LL/EUREF89)
Reprojector_3
    SOURCE = Read from feature
    DEST = EPSG:4258
    INTERPOLATION_TYPE_NAME = Nearest Neighbor
    STROKE_ARCS = Yes
    RASTER_CELL_SIZE = Preserve Cells
    REPROJECTED -> GeometryFilter
Note: Reproject clipper to / the DB coordsys (LL/EUREF89)
Reprojector_2
    SOURCE = Read from feature
    DEST = EPSG:4258
    INTERPOLATION_TYPE_NAME = Nearest Neighbor
    STROKE_ARCS = Yes
    RASTER_CELL_SIZE = Preserve Cells
    REPROJECTED -> GeometryFilter
Note: Getting rid of dummies
GeometryFilter
    BREAK_AGG = No
    GEOM_PORT_NAMES = Area
    AREA -> Output (output)
Output (output)
