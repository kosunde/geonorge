FME workspace nvdbtrafikkulykker_postgis2sosi.fmw
# Copyright: (c) xgrimor 2015
# Licence: <your licence>
Shutdown Python:
      # -*- coding: utf-8 -*-
      #-------------------------------------------------------------------------------
      # Name:        zipfiles.py
      # Purpose:     Pakker filer i output folderen
      #
      # Author:      xsunknu
      #
      # Created:     18.09.2015
      # Copyright:   (c) xsunknu 2015
      # Licence:     <your licence>
      #-------------------------------------------------------------------------------

      import sys, os, zipfile, fme

      def zip(sosifile, zfile):
          from os.path import basename

          # Lager korresponderende zip-fil av SOSI-fil
          if os.path.isfile(zfile):
              os.remove(zfile)

          zf = zipfile.ZipFile(zfile, "w", zipfile.ZIP_DEFLATED)

          # Ønsker ikke full sti inn i ZIP-filen
          arcname = basename(sosifile)

          # ZIP-formatet støtter ikke non-ascii tegn
          # Erstatter AØÅæøå med ascii-tegn
          arcname = arcname.replace('\xc6', 'E')
          arcname = arcname.replace('\xd8', 'O')
          arcname = arcname.replace('\xc5', 'A')
          arcname = arcname.replace('\xe6', 'e')
          arcname = arcname.replace('\xf8', 'o')
          arcname = arcname.replace('\xe5', 'a')

          zf.write(sosifile, arcname)
          zf.close()
          os.remove(sosifile)

          return

      def main():

          # Kjøres ikke på FME Server, da FME Server selv sørger for pakkingen
          if not 'FME_SERVER_DEST_DIR' in fme.macroValues:
              if 'FANOUT_FOLDER' in fme.macroValues:
                  path = fme.macroValues['FANOUT_FOLDER']
                  for dirpath, dnames, fnames in os.walk(path):
                      for f in fnames:
                          if f.endswith(".sos"):
                              # Scanner gjennom alle SOSI-filer
                              sosifile = os.path.join(path, f)
                              zfile = os.path.splitext(sosifile)[0] + '.zip'
                              if os.path.isfile(zfile):

                                  # Korresponderende ZIP-fil finnes, sjekker timestamps
                                  sositstamp = os.stat(sosifile).st_mtime
                                  ziptstamp = os.stat(zfile).st_mtime

                                  if sositstamp > ziptstamp:
                                      # SOSI-fil er nyere enn ZIP-fila, ZIP-fila oppdateres
                                      # SOSI-fila slettes
                                      try:
                                          zip(sosifile, zfile)
                                      except:
                                          print 'Kunne ikke pakke: ' + sosifile
                                  else:
                                      # SOSI-fila er eldre enn ZIP-fila
                                      # SOSI-fila slettes
                                      try:
                                          os.remove(sosifile)
                                      except:
                                          print 'Kunne ikke slette: ' + sosifile
                              else:
                                  # ZIP-fila eksisterer ikke og lages
                                  # SOSI-fila slettes
                                  try:
                                      zip(sosifile, zfile)
                                  except:
                                      print 'Kunne ikke pakke: ' + sosifile


      if __name__ == '__main__':
          main()

Parameters:
- KNR =   # Kommune(r)
- FNR =   # Fylke(r)
- CLIPPERCOORDS =   # Clipper coordinates
- CLIPPER_EPSG_CODE =   # Clipper coordinate system
- CLIPPER_FILE =   # "" Clipper file (any format)
- OUTPUT_EPSG_CODE =   # Destination coordinate system
- FANOUT =   # Fanout områder
- DestDataset_SOSI = $(FME_MF_DIR)out.sosi.sos   # Destination SOSI File
- CONFIG_FILE:   # Python Script
      #-------------------------------------------------------------------------------
      # Name:        GetConfigFile
      # Purpose:
      #
      # Author:      xsunknu
      #
      # Created:     21.08.2015
      # Copyright:   (c) xsunknu 2015
      # Licence:     <your licence>
      #-------------------------------------------------------------------------------
      
      import os, fme
      
      fmwdir = fme.macroValues['FME_MF_DIR']
      fmwfile = fme.macroValues['FME_MF_NAME']
      
      fmwfile = os.path.join(fmwdir, fmwfile)
      configfile = os.path.splitext(fmwfile)[0] + '_config.xml'
      
      return configfile
- PG_DB:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgdb').text
      
      return value
- PG_HOST:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pghost').text
      
      return value
- PG_PORT:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgport').text
      
      return value
- PG_USER:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pguser').text
      
      return value
- PG_PWD:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgpwd').text
      
      return value
- SPATIAL_FILTER:   # Python Script
      #-------------------------------------------------------------------------------
      # Name:        SetSpatialFilter
      # Purpose:
      #
      # Author:      xsunknu
      #
      # Created:     21.08.2015
      # Copyright:   (c) xsunknu 2015
      # Licence:     <your licence>
      #-------------------------------------------------------------------------------
      
      import fme
      
      spatialfilter = 'Intersects'
      
      knr = fme.macroValues['KNR']
      fnr = fme.macroValues['FNR']
      coords = fme.macroValues['CLIPPERCOORDS']
      file = fme.macroValues['CLIPPER_FILE']
      
      if knr == '' and fnr == '' and coords == '' and file == '':
          spatialfilter = '<No Spatial Filter>'
      
      return spatialfilter
- CLIPPERCOORDSYS:   # Python Script
      #-------------------------------------------------------------------------------
      # Name:        SetCoordinateSystem
      # Purpose:
      #
      # Author:      xsunknu
      #
      # Created:     21.08.2015
      # Copyright:   (c) xsunknu 2015
      # Licence:     <your licence>
      #-------------------------------------------------------------------------------
      
      import os, fme
      
      EPSGvalue = fme.macroValues['CLIPPER_EPSG_CODE']
      EPSGcode  = 'EPSG:' + EPSGvalue
      
      return EPSGcode
- FIXEDCLIPPERCOORDS:   # Python Script
      #-------------------------------------------------------------------------------
      # Name:        FixClipperCoords
      # Purpose:
      #
      # Author:      xsunknu
      #
      # Created:     21.08.2015
      # Copyright:   (c) xsunknu 2015
      # Licence:     <your licence>
      #-------------------------------------------------------------------------------
      
      import fme
      clippercoords = fme.macroValues['CLIPPERCOORDS']
      
      if clippercoords == '':
          clippercoords = '1 1'
      
      return clippercoords
- UNDERTEMA = Trafikkulykker   # Undertema
- HOVEDTEMA = Samferdsel   # Hovedtema
- DESTCOORDSYS:   # Python Script
      #-------------------------------------------------------------------------------
      # Name:        SetCoordinateSystem
      # Purpose:
      #
      # Author:      xsunknu
      #
      # Created:     21.08.2015
      # Copyright:   (c) xsunknu 2015
      # Licence:     <your licence>
      #-------------------------------------------------------------------------------
      
      import os, fme
      
      EPSGvalue = fme.macroValues['OUTPUT_EPSG_CODE']
      EPSGcode  = 'EPSG:' + EPSGvalue
      
      return EPSGcode
- FANOUT_FOLDER:   # Python Script
      #-------------------------------------------------------------------------------
      # Name:        GetConfigFile
      # Purpose:
      #
      # Author:      xsunknu
      #
      # Created:     21.08.2015
      # Copyright:   (c) xsunknu 2015
      # Licence:     <your licence>
      #-------------------------------------------------------------------------------
      
      import os, fme
      from xml.etree import ElementTree as ET
      
      if 'FME_SERVER_DEST_DIR' in fme.macroValues:
          value = fme.macroValues['FME_SERVER_DEST_DIR']
      else:
          #Read XML config file
          configtree = ET.parse(fme.macroValues['CONFIG_FILE'])
          configdoc = configtree.getroot()
          value = configdoc.find('destdir').text
      
      return value
- LOG_FILE:   # Python Script
      #-------------------------------------------------------------------------------
      # Name:        GetConfigFile
      # Purpose:
      #
      # Author:      xsunknu
      #
      # Created:     21.08.2015
      # Copyright:   (c) xsunknu 2015
      # Licence:     <your licence>
      #-------------------------------------------------------------------------------
      
      import os, uuid, fme
      
      fmwdir = fme.macroValues['FME_MF_DIR']
      fmwfile = fme.macroValues['FME_MF_NAME']
      
      logdir = os.path.join(fmwdir, 'log')
      if not os.path.isdir(logdir):
          os.mkdir(logdir)
      
      logfile = os.path.splitext(fmwfile)[0] + '_' + str(uuid.uuid1()).replace('-','') + '.log'
      logfile = os.path.join(logdir, logfile)
      
      return logfile
- MAPPINGFILE:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme, os
      from xml.etree import ElementTree as ET
      
      #Read XML config file
      configtree = ET.parse(fme.macroValues['CONFIG_FILE'])
      configdoc = configtree.getroot()
      
      value = os.path.join(fme.macroValues['FME_MF_DIR'], configdoc.find('mappingfile').text)
      
      return value
- SOSIDEF_FILE:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme, os
      from xml.etree import ElementTree as ET
      
      #Read XML config file
      configtree = ET.parse(fme.macroValues['CONFIG_FILE'])
      configdoc = configtree.getroot()
      
      value = os.path.join(fme.macroValues['FME_MF_DIR'], configdoc.find('sosideffile').text)
      
      return value

Readers:
- POSTGIS_1: POSTGIS from $(PG_DB)

Writers:
- SOSI_1: SOSI to $(DestDataset_SOSI)

CreateClipper
    CLIPPERCOORDSYS = $(CLIPPERCOORDSYS)
    DESTCOORDSYS = $(DESTCOORDSYS)
    CLIPPERCOORDS = $(FIXEDCLIPPERCOORDS)
    -> Clipper [input 1]
    -> FeatureReader_3
BulkAttributeRenamer
    ATTRLIST = datauttaksdato nvdb_alvorligsteskadegrad nvdb_antallalvorligskadet nvdb_antalldrepteiulykken nvdb_antallenheter nvdb_antallkjoerefelt nvdb_antalllettereskadet nvdb_antallmegetalvorligskadet nvdb_bebyggelse nvdb_dekketype nvdb_fartsgrense nvdb_felttype nvdb_foereforhold nvdb_historiskhp nvdb_historiskkilometerverdi nvdb_historiskvegkategori nvdb_historiskvegnummer nvdb_historiskvegstatus nvdb_kommunenr nvdb_lysforhold nvdb_midtdeler nvdb_registreringsdatofagdata nvdb_stedfestingensnoeyaktighet nvdb_stedsforhold nvdb_temperatur nvdb_uhellkategori nvdb_uhellskode nvdb_ukedag nvdb_ulykkesdato nvdb_ulykkestidspunkt nvdb_vaerforhold nvdb_vegbredde nvdb_vegnavn nvdb_vegtype objtype
    PATTERN_ACTION_DISP = Change Case
    CASE_CHANGE_TYPE = UPPERCASE
    ATTRCHOICE = Selected Attributes
    -> AttributeRenamer
AttributeRenamer
    ATTR_LIST = NVDB_FOEREFORHOLD,NVDB_FØREFORHOLD,,NVDB_VAERFORHOLD,NVDB_VÆRFORHOLD,,NVDB_ANTALLKJOEREFELT,NVDB_ANTALLKJØREFELT,,NVDB_STEDFESTINGENSNOEYAKTIGHET,NVDB_STEDFESTINGENSNØYAKTIGHET,
    -> nvdb_trafikkulykker.trafikkulykke (writer SOSI_1)
nvdb_trafikkulykker.trafikkulykke (writer SOSI_1)
    attributes: OBJTYPE SOSI_varchar(32), NVDB_ALVORLIGSTESKADEGRAD SOSI_varchar(80), NVDB_ULYKKESDATO SOSI_date, NVDB_ULYKKESTIDSPUNKT SOSI_int16, NVDB_UKEDAG SOSI_varchar(80), NVDB_REGISTRERINGSDATOFAGDATA SOSI_date, NVDB_UHELLKATEGORI SOSI_varchar(80), NVDB_UHELLSKODE SOSI_varchar(80), NVDB_ANTALLENHETER SOSI_int32, NVDB_ANTALLDREPTEIULYKKEN SOSI_int32, NVDB_ANTALLMEGETALVORLIGSKADET SOSI_int32, NVDB_ANTALLALVORLIGSKADET SOSI_int32, NVDB_ANTALLLETTERESKADET SOSI_int32, NVDB_VEGTYPE SOSI_varchar(80), NVDB_STEDSFORHOLD SOSI_varchar(80), NVDB_MIDTDELER SOSI_varchar(80), NVDB_DEKKETYPE SOSI_varchar(80), NVDB_FØREFORHOLD SOSI_varchar(80), NVDB_VÆRFORHOLD SOSI_varchar(80), NVDB_LYSFORHOLD SOSI_varchar(80), NVDB_FELTTYPE SOSI_varchar(80), NVDB_ANTALLKJØREFELT SOSI_int32, NVDB_BEBYGGELSE SOSI_varchar(80), NVDB_VEGBREDDE SOSI_real64, NVDB_FARTSGRENSE SOSI_varchar(80), NVDB_TEMPERATUR SOSI_int32, NVDB_KOMMUNENR SOSI_int32, NVDB_HISTORISKVEGSTATUS SOSI_varchar(80), NVDB_HISTORISKVEGKATEGORI SOSI_varchar(80), NVDB_HISTORISKVEGNUMMER SOSI_int32,
      NVDB_HISTORISKHP SOSI_int32, NVDB_HISTORISKKILOMETERVERDI SOSI_int32, NVDB_VEGNAVN SOSI_varchar(80), NVDB_STEDFESTINGENSNØYAKTIGHET SOSI_varchar(80), DATAUTTAKSDATO SOSI_datetime

Bookmark: Fylke and/or kommune clippers
Creator_2
    NUM = 1
    GEOMTYPE = Geometry Object
    CREATED -> AttributeCreator_8
AttributeCreator_8
    ATTR_LIST = _clippercoords,$(CLIPPERCOORDS),_clipper_file,$(CLIPPER_FILE),_fnr,$(FNR),_knr,$(KNR)
    -> Tester_4
Note: Sender inn en dummy initiator / dersom alle klippeparametrene er / blanke siden Luftfartshindere / strekker seg utover fastlands- / Norge
Tester_4
    TEST_MODE = Automatic
    TEST_DESCRIPTION = ""
    TEST_CLAUSE:
      TEST _clipper_file ATTRIBUTE_IS_EMPTY ""
      TEST _clippercoords ATTRIBUTE_IS_EMPTY ""
      TEST _fnr ATTRIBUTE_IS_EMPTY ""
      TEST _knr ATTRIBUTE_IS_EMPTY ""
    BOOL_OP = AND
    PASSED -> Reprojector_2
admingrense.fylkeflate (reader POSTGIS_1)
    attributes: fylkeid int4, navn varchar(80)
    -> Tester
Tester
    TEST_MODE = Automatic
    TEST_DESCRIPTION = ""
    TEST_CLAUSE = TEST @Value(fylkeid) IN $(FNR)
    BOOL_OP = OR
    PASSED -> Reprojector_2
admingrense.kommuneflate (reader POSTGIS_1)
    attributes: kommuneid int4, navn varchar(80)
    -> Tester_2
Tester_2
    TEST_MODE = Automatic
    TEST_DESCRIPTION = ""
    TEST_CLAUSE = TEST @Value(kommuneid) IN $(KNR)
    BOOL_OP = OR
    PASSED -> Reprojector_2
Reprojector_2
    DEST = EPSG:4258
    RASTER_CELL_SIZE = Preserve Cells
    SOURCE = Read from feature
    INTERPOLATION_TYPE_NAME = Nearest Neighbor
    REPROJECTED -> Clipper [input 1]
    REPROJECTED -> FeatureReader_3

Bookmark: Clipper file (any format)
Creator
    NUM = 1
    GEOMTYPE = Geometry Object
    CREATED -> FeatureReader
FeatureReader
    ATTRIBUTES = NewFeatureType,
    FEATURETYPES_RADIO = FEATURETYPES
    OUTPUT_FEATURES_DISPLAY = Based on Connections
    GENERIC_REAL_FORMAT = GUESS_FROM_EXTENSION
    INTERACT = $(SPATIAL_FILTER)
    FORMAT = GENERIC
    DATASET = $(CLIPPER_FILE)
    COMBINE_GEOM = Use Result
    ATTR_ACCUM_MODE = Only Use Result
    <OTHER> -> Reprojector_3
Reprojector_3
    DEST = EPSG:4258
    RASTER_CELL_SIZE = Preserve Cells
    SOURCE = Read from feature
    INTERPOLATION_TYPE_NAME = Nearest Neighbor
    REPROJECTED -> Clipper [input 1]
    REPROJECTED -> FeatureReader_3

Bookmark: Leser features og relaterte data
FeatureReader_3
    FORMAT = POSTGIS
    POSTGIS_PASSWORD = $(PG_PWD)
    POSTGIS_CLIP_TO_ENVELOPE = NO
    POSTGIS_QUERY_FEATURE_TYPES_FOR_MERGE_FILTERS = Yes
    POSTGIS_PORT = $(PG_PORT)
    FEATURETYPES_RADIO = FEATURETYPES
    POSTGIS_USE_TRUE_POSTGIS_TYPES = yes
    ATTR_ACCUM_MODE = Only Use Result
    FEATURETYPES = nvdb_trafikkulykker.trafikkulykke
    DATASET = $(PG_DB)
    POSTGIS_HOST = $(PG_HOST)
    INTERACT = $(SPATIAL_FILTER)
    COMBINE_GEOM = Use Result
    POSTGIS_SCHEMALIST = nvdb_trafikkulykker
    POSTGIS_USER_NAME = $(PG_USER)
    POSTGIS_DISABLE_COLLECTION_SPLITTING = yes
    OUTPUT_FEATURES_DISPLAY = Based on Connections
    ATTRIBUTES = nvdb_trafikkulykker.trafikkulykke,"objid,objtype,nvdb_alvorligsteskadegrad,nvdb_ulykkesdato,nvdb_ukedag,nvdb_registreringsdatofagdata,nvdb_uhellkategori,nvdb_uhellskode,nvdb_antallenheter,nvdb_antalldrepteiulykken,nvdb_antallmegetalvorligskadet,nvdb_antallalvorligskadet,nvdb_antalllettereskadet,nvdb_vegtype,nvdb_stedsforhold,nvdb_midtdeler,nvdb_dekketype,nvdb_foereforhold,nvdb_vaerforhold,nvdb_lysforhold,nvdb_felttype,nvdb_antallkjoerefelt,nvdb_bebyggelse,nvdb_vegbredde,nvdb_fartsgrense,nvdb_temperatur,nvdb_kommunenr,nvdb_historiskvegstatus,nvdb_historiskvegkategori,nvdb_historiskvegnummer,nvdb_historiskhp,nvdb_historiskkilometerverdi,nvdb_vegnavn,nvdb_stedfestingensnoeyaktighet,datauttaksdato,nvdb_ulykkestidspunkt"
    POSTGIS_USE_SEARCH_ENVELOPE = NO
    nvdb_trafikkulykker.trafikkulykke -> Clipper [input 2]

Bookmark: Klipper
Clipper
    ATTR_ACCUM_MODE = Merge Clipper
    PRESERVE_CLIPPEE_EXTENTS = No
    CLIPPED_ATTR = _clipped
    BOUNDARY_CASES = Treat as Inside
    ATTR_CONFLICT_RES = Use Clippee
    CLIP_TYPE = Multiple Clippers
    CREATE_AGGREGATES = No
    INSIDE -> SosiFilenameSetter

Bookmark: Tagger og reprojiserer
SosiFilenameSetter
    PG_HOST:
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------

      import fme
      from xml.etree import ElementTree as ET

      #Read XML config file
      configtree = ET.parse(fme.macroValues['CONFIG_FILE'])
      configdoc = configtree.getroot()
      value = configdoc.find('pghost').text

      return value
    FANOUT = $(FANOUT)
    FYLKEID = @Value(fylkeid)
    PG_USER:
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------

      import fme
      from xml.etree import ElementTree as ET

      #Read XML config file
      configtree = ET.parse(fme.macroValues['CONFIG_FILE'])
      configdoc = configtree.getroot()
      value = configdoc.find('pguser').text

      return value
    _KNR = @Value(_knr)
    Undertema = $(UNDERTEMA)
    PG_DB:
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------

      import fme
      from xml.etree import ElementTree as ET

      #Read XML config file
      configtree = ET.parse(fme.macroValues['CONFIG_FILE'])
      configdoc = configtree.getroot()
      value = configdoc.find('pgdb').text

      return value
    _FNR = @Value(_fnr)
    _CREATION_INSTANCE = @Value(_creation_instance)
    OUTPUT_EPSG_CODE = $(OUTPUT_EPSG_CODE)
    PG_PORT:
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------

      import fme
      from xml.etree import ElementTree as ET

      #Read XML config file
      configtree = ET.parse(fme.macroValues['CONFIG_FILE'])
      configdoc = configtree.getroot()
      value = configdoc.find('pgport').text

      return value
    PG_PWD:
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------

      import fme
      from xml.etree import ElementTree as ET

      #Read XML config file
      configtree = ET.parse(fme.macroValues['CONFIG_FILE'])
      configdoc = configtree.getroot()
      value = configdoc.find('pgpwd').text

      return value
    _CLIPPER_FILE = @Value(_clipper_file)
    KOMMUNEID = @Value(kommuneid)
    Hovedtema = $(HOVEDTEMA)
    _CLIPPERCOORDS = @Value(_clippercoords)
    _CLIPPED = @Value(_clipped)
    -> Reprojector
Reprojector
    DEST = $(DESTCOORDSYS)
    RASTER_CELL_SIZE = Preserve Cells
    SOURCE = Read from feature
    INTERPOLATION_TYPE_NAME = Nearest Neighbor
    REPROJECTED -> FeatureTypeFilter
FeatureTypeFilter
    ATTRIBUTES = nvdb_trafikkulykker.trafikkulykke,<BLANK>,<UNFILTERED>
    nvdb_trafikkulykker.trafikkulykke -> BulkAttributeRenamer

FME custom transformer CreateClipper

Parameters:
- CLIPPERCOORDS = 253577 6650999 253577 6651246 253763 6651246 253763 6650999 253577 6650999   # Clipper Coordinate List
- CLIPPERCOORDSYS = EPSG:25833   # Clipper Coordinate System
- DESTCOORDSYS = "ESRIWKT|ETRS_1989_UTM_Zone_35N|PROJCS["ETRS_1989_UTM_Zone_35N",GEOGCS["GCS_ETRS_1989",DATUM["D_ETRS_1989",SPHEROID["GRS_1980",6378137.0,298.257222101]],PRIMEM["Greenwich",0.0],UNIT["Degree",0.0174532925199433]],PROJECTION["Transverse_Mercator"],PARAMETER["False_Easting",500000.0],PARAMETER["False_Northing",0.0],PARAMETER["Central_Meridian",27.0],PARAMETER["Scale_Factor",0.9996],PARAMETER["Latitude_Of_Origin",0.0],UNIT["Meter",1.0]]"   # Destination Coordinate System

Note: Creating geometry from / the Clipper coords
Creator
    COORDSYS = $(CLIPPERCOORDSYS)
    NUM = 1
    COORDS = $(CLIPPERCOORDS)
    GEOMTYPE = 2D Coordinate List
    CREATED -> BoundingBoxAccumulator
Note: Calculating the bounding / box (envelope) from the geometry
BoundingBoxAccumulator
    TOPFER_INDEX = No
    BOUNDING_BOX -> SpatialFilter [input 1]
    ORIGINAL -> SpatialFilter [input 2]
Note: If the geometry is equal to its / own bounding box - it is a rectangle!
SpatialFilter
    USE_BOUNDING_BOX = No
    MERGE_ATTRS = No
    PREDICATES = EQUALS
    PASS_CRITERIA = Pass Against One Base
    PREDATTR = _predicate
    BASE_TYPE = Single Base
    CURVE_BOUNDARY_RULE_PARAM = Default Rule
    PASSED -> Reprojector
    FAILED -> Reprojector_2
Note: If rectangle, reproject the / geometry to the destination / coordinate system
Reprojector
    DEST = $(DESTCOORDSYS)
    RASTER_CELL_SIZE = Preserve Cells
    SOURCE = Read from feature
    INTERPOLATION_TYPE_NAME = Nearest Neighbor
    STROKE_ARCS = Yes
    REPROJECTED -> BoundingBoxAccumulator_2
Note: Then calculate the bounding / box from the projected geoemtry
BoundingBoxAccumulator_2
    TOPFER_INDEX = No
    BOUNDING_BOX -> Reprojector_3
Note: Reproject the geometry back to / the DB coordsys (LL/EUREF89)
Reprojector_3
    DEST = EPSG:4258
    RASTER_CELL_SIZE = Preserve Cells
    SOURCE = Read from feature
    INTERPOLATION_TYPE_NAME = Nearest Neighbor
    STROKE_ARCS = Yes
    REPROJECTED -> GeometryFilter
Note: Reproject clipper to / the DB coordsys (LL/EUREF89)
Reprojector_2
    DEST = EPSG:4258
    RASTER_CELL_SIZE = Preserve Cells
    SOURCE = Read from feature
    INTERPOLATION_TYPE_NAME = Nearest Neighbor
    STROKE_ARCS = Yes
    REPROJECTED -> GeometryFilter
Note: Getting rid of dummies
GeometryFilter
    GEOM_PORT_NAMES = Area
    BREAK_AGG = No
    AREA -> Output (output)
Output (output)

FME custom transformer SosiFilenameSetter

Parameters:
- OUTPUT_EPSG_CODE = 25832   # Destination coordinate system
- FANOUT = Kommuner   # Fanout områder
- _CLIPPED = @Value(_clipped)   # Clipped
- _CLIPPER_FILE = @Value(_clipper_file)   # Clipper File
- _CLIPPERCOORDS = @Value(_clippercoords)   # Clippercoords
- _CREATION_INSTANCE = @Value(_creation_instance)   # Creation Instance
- _FNR = @Value(_fnr)   # Fnr
- _KNR = @Value(_knr)   # Knr
- FYLKEID = @Value(fylkeid)   # fylkeid
- KOMMUNEID = @Value(kommuneid)   # kommuneid
- Hovedtema =
- Undertema =
- PG_DB:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgdb').text
      
      return value
- PG_HOST:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pghost').text
      
      return value
- PG_PORT:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgport').text
      
      return value
- PG_PWD:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgpwd').text
      
      return value
- PG_USER:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pguser').text
      
      return value

Input (input)
    -> ParameterFetcher
ParameterFetcher
    ATTR_LIST = _output_epsg_code {$(OUTPUT_EPSG_CODE)} _fanout {$(FANOUT)}
    -> AttributeValueMapper
Note: Fikser kjente feil i kommunenummer
AttributeValueMapper
    DIRECTION = Forward (Source To Destination)
    VAL_ATTR = kommuneid
    DEFAULT_VALUE = @Value(kommuneid)
    LUT = 1901,1903
    SRC = kommuneid
    -> TestFilter_2
TestFilter_2
    DEFAULT_VALUE = Ufiltrert
    TEST_LIST = BOOL_OP,OR,COMPOSITE_TEST,<Unused>,TEST_CLAUSE,"TEST $(FANOUT) = Kommuner",Kommuner,BOOL_OP,OR,COMPOSITE_TEST,<Unused>,TEST_CLAUSE,"TEST $(FANOUT) = Fylker",Fylker
    Kommuner -> Joiner
    Ufiltrert -> AttributeCreator_13
    Fylker -> Joiner_2
Joiner
    TABLE = admingrense.kommuner
    POSTGIS_USER_NAME = $(PG_USER)
    MATCH_RULE_DISPLAY = Must Match Exactly One (1:1)
    POSTGIS_DISABLE_COLLECTION_SPLITTING = yes
    ADDED_FIELDS = navn
    PREFETCH_EXHAUSTIVE = Yes
    FORMAT = POSTGIS
    POSTGIS_HOST = $(PG_HOST)
    DATASET = $(PG_DB)
    POSTGIS_PASSWORD = $(PG_PWD)
    POSTGIS_QUERY_FEATURE_TYPES_FOR_MERGE_FILTERS = Yes
    JOIN_KEYS = kommuneid kommuneid
    CACHE_SIZE = 5000
    POSTGIS_PORT = $(PG_PORT)
    POSTGIS_USE_TRUE_POSTGIS_TYPES = yes
    JOINED -> StringReplacer
Joiner_2
    TABLE = admingrense.fylkeflate
    POSTGIS_USER_NAME = $(PG_USER)
    MATCH_RULE_DISPLAY = Must Match Exactly One (1:1)
    POSTGIS_DISABLE_COLLECTION_SPLITTING = yes
    ADDED_FIELDS = navn
    PREFETCH_EXHAUSTIVE = Yes
    FORMAT = POSTGIS
    POSTGIS_HOST = $(PG_HOST)
    DATASET = $(PG_DB)
    POSTGIS_PASSWORD = $(PG_PWD)
    POSTGIS_QUERY_FEATURE_TYPES_FOR_MERGE_FILTERS = Yes
    JOIN_KEYS = fylkeid fylkeid
    CACHE_SIZE = 5000
    POSTGIS_PORT = $(PG_PORT)
    POSTGIS_USE_TRUE_POSTGIS_TYPES = yes
    JOINED -> StringReplacer
StringReplacer
    REPLACE_TEXT = _
    SRC_ATTRS = navn
    REGEXP = no
    FIND_TEXT = " "
    NO_MATCH = _FME_NO_OP_
    CASE = no
    -> AttributeCreator_13
AttributeCreator_13
    ATTR_LIST = sosifile,"FME_CONDITIONAL:DEFAULT_VALUE'$(Hovedtema)_$(OUTPUT_EPSG_CODE)_$(Undertema)_GML'BOOL_OP;OR;COMPOSITE_TEST;<Unused>;TEST $(FANOUT) LIKE Kommuner'$(Hovedtema)_@PadLeft(@Value(kommuneid),4,0)_@Value(navn)_$(OUTPUT_EPSG_CODE)_$(Undertema)_GML'BOOL_OP;OR;COMPOSITE_TEST;<Unused>;TEST $(FANOUT) LIKE Fylker'$(Hovedtema)_@PadLeft(@Value(fylkeid),2,0)_@Value(navn)_$(OUTPUT_EPSG_CODE)_$(Undertema)_GML'BOOL_OP;OR;COMPOSITE_TEST;<Unused>;TEST $(FANOUT) LIKE Norge'$(Hovedtema)_0000_Norge_$(OUTPUT_EPSG_CODE)_$(Undertema)_GML'FME_NUM_CONDITIONS4___"
    -> Output (output)
Output (output)
