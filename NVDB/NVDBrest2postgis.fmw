FME workspace NVDBrest2postgis.fmw

Parameters:
- DestDataset_POSTGIS = geonortst@nnridb504:5432/geonor01tst   # Connection
- DestDataset_POSTGIS_2 = geonortst@nnridb504:5432/geonor01tst   # Connection
- SourceDataset_POSTGRES = geonortst@nnridb504:5432/geonor01tst   # Connection

Readers:
- POSTGRES_1: POSTGRES from $(SourceDataset_POSTGRES)

Writers:
- POSTGIS_1: POSTGIS to $(DestDataset_POSTGIS)
- POSTGIS_3: POSTGIS to $(DestDataset_POSTGIS_2)

admingrense.kommuner (reader POSTGRES_1)
    attributes: kommuneid int2,PRIKEY, navn varchar(80)
    -> HTTPCaller
HTTPCaller
    TARGET_URL = https://www.vegvesen.no/nvdb/api/sok?kriterie={%20lokasjon:%20{kommune:%20[@Value(kommuneid)]%20},%20objektTyper:%20[%20{%20id:%20570,%20antall:100000}]%20}
    VERIFY_SSL_CERTIFICATES = Yes
    CUSTOM_HEADERS = Accept;application/vnd.vegvesen.nvdb-v1+xml
    FOLLOW_REDIRECTS = Yes
    RESPONSE_HEADER_LIST_ATTR = _headers
    SAVE_FILE = Attribute
    TRANSFER_TIMEOUT_LENGTH = 90
    USE_COOKIES = No
    TARGET_ATTR = _response_body
    TARGET_ATTR_ENCODING = utf-8
    HTTP_METHOD = GET
    STATUS_CODE_ATTR = _http_status_code
    CONNECTION_TIMEOUT_LENGTH = 60
    ERROR_ATTR = _error
    -> XMLFeatureMapper
XMLFeatureMapper
    FEATURE_COUNT_PER_XML = _xml_feature_count_
    XML_SOURCE_NAME = _xml_source_
    ATTRIBUTE_XML = _response_body
    FEATURE_TYPE_ATTR = fme_feature_type
    MERGE_ATTRS = No
    SCRIPT_XFMAP:
      <?xml version="1.0"?>
      <xfMap>
        <feature-map multi-feature-construction="true">
           <mapping match="vegObjekt">
              <feature-type><literal expr="vegObjekt"/> </feature-type>
           </mapping>
        </feature-map>
        <feature-content-map>
          <mapping match="egenskap">
             <attributes>
                <attribute type="sequenced">
                   <name><extract expr="./navn"/></name>
                   <value><extract expr="./verdi"/></value>
                </attribute>
             </attributes>
           </mapping>
          <mapping match="objektTypeNavn">
             <attributes>
                <attribute>
                   <name><literal expr="objtype"/></name>
                   <value><extract expr="."/></value>
                </attribute>
             </attributes>
           </mapping>
          <mapping match="geometriWgs84">
             <attributes>
                <attribute>
                   <name><literal expr="koordinater"/></name>
                   <value><extract expr="."/></value>
                </attribute>
             </attributes>
           </mapping>
       </feature-content-map>
      </xfMap>
    NEW_ATTRIBUTES = Alvorligste skadegrad Antall alvorlig skadet Antall drepte i ulykken Antall enheter Antall kjørefelt Antall lettere skadet Antall meget alvorlig skadet Bebyggelse Dekketype Fartsgrense Felttype Føreforhold Geometri, punkt Historisk hp Historisk kilometerverdi Historisk vegkategori Historisk vegnummer Historisk vegstatus Lysforhold Midtdeler Registreringsdato for fagdata Stedfestingens nøyaktighet Stedsforhold Temperatur Uhell kategori Uhellskode Ukedag Ulykkesdato Ulykkestidspunkt Vegbredde Vegnavn Vegtype Værforhold objtype Kommunenr koordinater
    XML_INPUT_TYPE = Attribute with XML document
    CONFIGURATION_TYPE = Embedded xfMap script
    MAPPED -> AttributeRenamer
AttributeRenamer
    ATTR_LIST = Alvorligste skadegrad,nvdb_alvorligsteskadegrad,,Antall alvorlig skadet,nvdb_antallalvorligskadet,,Antall drepte i ulykken,nvdb_antalldrepteiulykken,,Antall enheter,nvdb_antallenheter,,Antall kjørefelt,nvdb_antallkjoerefelt,,Antall lettere skadet,nvdb_antalllettereskadet,,Antall meget alvorlig skadet,nvdb_antallmegetalvorligskadet,,Bebyggelse,nvdb_bebyggelse,,Dekketype,nvdb_dekketype,,Fartsgrense,nvdb_fartsgrense,,Felttype,nvdb_felttype,,Føreforhold,nvdb_foereforhold,,Historisk hp,nvdb_historiskhp,,Historisk kilometerverdi,nvdb_historiskkilometerverdi,,Historisk vegkategori,nvdb_historiskvegkategori,,Historisk vegnummer,nvdb_historiskvegnummer,,Historisk vegstatus,nvdb_historiskvegstatus,,Lysforhold,nvdb_lysforhold,,Midtdeler,nvdb_midtdeler,,Registreringsdato for fagdata,nvdb_registreringsdatofagdata,,Stedfestingens nøyaktighet,nvdb_stedfestingensnoeyaktighet,,Stedsforhold,nvdb_stedsforhold,,Temperatur,nvdb_temperatur,,Uhell kategori,nvdb_uhellkategori,,Uhellskode,nvdb_uhellskode,,Ukedag,nvdb_ukedag,,Ulykkesdato,nvdb_ulykkesdato,,Vegbredde,nvdb_vegbredde,,Vegnavn,nvdb_vegnavn,,Vegtype,nvdb_vegtype,,Værforhold,nvdb_vaerforhold,,Kommunenr,nvdb_kommunenr,,Ulykkestidspunkt,nvdb_ulykkestidspunkt,
    -> SubstringExtractor
SubstringExtractor
    START = 7
    RESULT_ATTR = koordinater
    SRC_STRING = @Value(koordinater)
    END = -2
    -> AttributeValueMapper
AttributeValueMapper
    DIRECTION = Forward (Source To Destination)
    VAL_ATTR = nvdb_uhellskode
    LUT = Avsvinging i hver sin retning,42,Avsvinging i samme retning,41,Avsvingning til høyre foran kjørende i motsatt retning fra fortau eller G/S-veg,44,Avsvingning til venstre foran kjørende i motsatt retning fra fortau eller G/S-veg,45,Avsvingning til venstre foran kjørende i motsatt retning,40,Barn lekte i kjørebanen,86,Enslig kjøretøy kjørte på trafikkøy eller ende av midtdeler,97,Enslig kjøretøy kjørte utfor på høyre side i høyrekurve,93,Enslig kjøretøy kjørte utfor på høyre side i venstrekurve,94,Enslig kjøretøy kjørte utfor på høyre side på rett vegstrekning,90,Enslig kjøretøy kjørte utfor på venstre side i høyrekurve,92,Enslig kjøretøy kjørte utfor på venstre side i venstrekurve,95,Enslig kjøretøy kjørte utfor på venstre side på rett vegstrekning,91,Enslig kjøretøy kjørte utfor ved avsvinging i kryss o.l.,96,Enslig kjøretøy veltet i kjørebanen,3,Forbikjøring på høyre side i kryss eller avkjørsel,52,Forbikjøring på venstre side i kryss eller avkjørsel,51,Fotgjenger gikk langs vegen og ble påkjørt av ryggende kjøretøy,85,Fotgjenger gikk på vegens høyre side,80,Fotgjenger gikk på vegens venstre side,81,Fotgjenger krysset kjørebanen foran høyresvingende kjøretøy i kryss,72,Fotgjenger krysset kjørebanen foran venstresvingende kjøretøy i kryss,73,Fotgjenger krysset kjørebanen forøvrig,75,Fotgjenger krysset kjørebanen i gangfelt utenfor kryss,74,Fotgjenger krysset kjørebanen i kryss bak parkert eller stanset kjøretøy,76,Fotgjenger krysset kjørebanen og ble påkjørt av ryggende kjøretøy,78,Fotgjenger krysset kjørebanen på bortsiden av krysset,70,Fotgjenger krysset kjørebanen på hitsiden av krysset,71,Fotgjenger krysset kjørebanen utenfor kryss bak parkert eller stanset kjøretøy,77,Fotgjenger påkjørt på fortau,82,Fotgjenger påkjørt ved forbikjøring,83,Fotgjenger stod stille eller oppholdt seg forøvrig i kjørebanen,84,Hull i vegen o.l.,2,Høyresving foran kjørende i motsatt retning,61,Høyresving foran kjørende i samme retning,60,Høyresving foran venstresvingende kjøretøy,62,Kjørende fra G/S-veg krysset kjørebanen utenfor kryss,55,Kjørende fra fortau eller G/S-veg krysset kjørebanen på bortsiden av krysset,54,Kjørende fra fortau eller G/S-veg krysset kjørebanen på hitsiden av krysset,53,Kjøring i parallelle kjørefelter forøvrig,13,Kryssende kjøreretninger,50,Møting etter oppstart fra stanset eller parkert stilling,26,Møting i kurve,21,Møting på rett vegstrekning,20,Møting under forbikjøring av stanset eller parkert kjøretøy,25,Møting under forbikjøring i høyrekurve,23,Møting under forbikjøring i venstrekurve,24,Møting under forbikjøring på rett vegstrekning,22,Påkjøring av fast gjenstand på kjørebanen,1,Påkjøring av forankjørende ved skifte av felt til høyre,17,Påkjøring av forankjørende ved skifte av felt til venstre,16,Påkjøring av kjørende fra fortau eller G/S-veg, ved høyresving,35,Påkjøring av kjørende fra fortau eller G/S-veg, ved venstresving,36,Påkjøring av parkert kjøretøy på høyre side,4,Påkjøring av parkert kjøretøy på venstre side,5,Påkjøring av parkert kjøretøy ved forbikjøring,6,Påkjøring bakfra etter oppstart fra stanset eller parkert stilling,15,Påkjøring bakfra ved høyresving,30,Påkjøring bakfra ved venstresving,32,Påkjøring bakfra,14,Påkjøring forøvrig ved høyresving,31,Påkjøring forøvrig ved venstresving,33,Påkjøring ved vending foran kjørende i samme retning,34,Samtidig høyresving,66,Samtidig venstresving,65,Skifte av felt til høyre,12,Skifte av felt til venstre,11,Uhell med dyr innblandet,0,Uhell med uklart forløp / uhell som ikke faller inn under noen bestemt uh.kode,9,Uhell med uklart forløp hvor enslig kjøretøy kjørte utfor vegen,99,Uhell med uklart forløp hvor fotgjenger gikk langs eller oppholdt seg i kj.banen,89,Uhell med uklart forløp hvor fotgjenger krysset kjørebanen,79,Uhell med uklart forløp mellom kjøretøy med samme kjøreretning,19,Uhell med uklart forløp ved avsvinging fra motsatte kjøreretninger,49,Uhell med uklart forløp ved avsvinging fra samme kjøreretning,39,Uhell med uklart forløp ved kryssende kj.retn hvor ett el. begge kj.tøy svinger av,69,Uhell med uklart forløp ved kryssende kj.retn uten at noen kj.tøy svinger av,59,Uhell med uklart forløp ved møting,29,Uhell ved av- eller påstigning av kjøretøy,8,Vending foran kjørende i motsatt retning,43,Venstresving foran kjørende i motsatt retning,64,Venstresving foran kjørende i samme retning,63,Øvrige parkeringsuhell,7,Forbikjøring,10
    SRC = nvdb_uhellskode
    -> AttributeSplitter
AttributeSplitter
    LIST_NAME = _list
    DROP_EMPTY_PARTS = No
    ATTR_NAME = koordinater
    TRIM_OPTION = Both
    DELIMITER = " "
    -> VertexCreator
VertexCreator
    XVAL = @Value(_list{0})
    MODE_NAME = Add Point
    YVAL = @Value(_list{1})
    -> CoordinateSystemSetter
CoordinateSystemSetter
    COORDSYS = EPSG:4326
    -> TimeStamper
TimeStamper
    FMT = FME Date/Time (^Y^m^d^H^M^S)
    TIME_ATTR = datauttaksdato
    -> AttributeCreator
AttributeCreator
    ATTR_LIST = fme_feature_type,trafikkulykke
    -> Counter
Counter
    SCOPE = Global
    START = 0
    CNT_ATTR = objid
    DOMAIN = counter
    -> nvdb_trafikkulykker.trafikkulykke (writer POSTGIS_3)
nvdb_trafikkulykker.trafikkulykke (writer POSTGIS_3)
    attributes: objid serial,PRIKEY, objtype varchar(32), nvdb_alvorligsteskadegrad varchar(80), nvdb_ulykkesdato date, nvdb_ukedag varchar(80), nvdb_registreringsdatofagdata date, nvdb_uhellkategori varchar(80), nvdb_uhellskode varchar(80), nvdb_antallenheter int4, nvdb_antalldrepteiulykken int4, nvdb_antallmegetalvorligskadet int4, nvdb_antallalvorligskadet int4, nvdb_antalllettereskadet int4, nvdb_vegtype varchar(80), nvdb_stedsforhold varchar(80), nvdb_midtdeler varchar(80), nvdb_dekketype varchar(80), nvdb_foereforhold varchar(80), nvdb_vaerforhold varchar(80), nvdb_lysforhold varchar(80), nvdb_felttype varchar(80), nvdb_antallkjoerefelt int4, nvdb_bebyggelse varchar(80), nvdb_vegbredde float8, nvdb_fartsgrense varchar(80), nvdb_temperatur int4, nvdb_kommunenr int4, nvdb_historiskvegstatus varchar(80), nvdb_historiskvegkategori varchar(80), nvdb_historiskvegnummer int4,
      nvdb_historiskhp int4, nvdb_historiskkilometerverdi int4, nvdb_vegnavn varchar(80), nvdb_stedfestingensnoeyaktighet varchar(80), datauttaksdato timestamp, nvdb_ulykkestidspunkt varchar(20)
nvdb_trafikkmengde.trafikkmengde (writer POSTGIS_1)
    attributes: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
