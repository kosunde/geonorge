FME workspace NVDBrest2postgis.fmw

Parameters:
- SourceDataset_POSTGRES = geonortst@nnridb504:5432/geonor01tst   # Connection
- SourceDataset_POSTGIS = geonortst@nnridb504:5432/geonor01tst   # Connection
- CONFIG_FILE:   # Python Script
      #-------------------------------------------------------------------------------
      # Name:        GetConfigFile
      # Purpose:
      #
      # Author:      xsunknu
      #
      # Created:     21.08.2015
      # Copyright:   (c) xsunknu 2015
      # Licence:     <your licence>
      #-------------------------------------------------------------------------------
      
      import os, fme
      
      fmwdir = fme.macroValues['FME_MF_DIR']
      fmwfile = fme.macroValues['FME_MF_NAME']
      
      fmwfile = os.path.join(fmwdir, fmwfile)
      configfile = os.path.splitext(fmwfile)[0] + '_config.xml'
      
      return configfile
- PG_DB:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgdb').text
      
      return value

Readers:
- POSTGRES_1: POSTGRES from $(SourceDataset_POSTGRES)
- POSTGIS_1: POSTGIS from $(SourceDataset_POSTGIS)

Writers:
- POSTGIS_2: POSTGIS to $(PG_DB)

admingrense.kommuneflate (reader POSTGIS_1)
    attributes: kommuneid int4, navn varchar(80)
    -> Sorter

Bookmark: Oslo, Bergen og Trondheim må deles opp.
Sorter
    SORT_PARM = kommuneid NUMERIC ASCENDING
    SORTED -> Tester
Tester
    TEST_DESCRIPTION = ""
    BOOL_OP = OR
    TEST_CLAUSE = TEST @Value(kommuneid) IN 301,1201,1601
    TEST_MODE = Automatic
    PASSED -> Reprojector_3
    FAILED -> HTTPCaller_3
Reprojector_3
    DEST = EPSG:32633
    RASTER_CELL_SIZE = Preserve Cells
    SOURCE = EPSG:4258
    INTERPOLATION_TYPE_NAME = Nearest Neighbor
    REPROJECTED -> Tiler

Bookmark: Trafikkulykker
Tiler
    COL_ATTR = _column
    XINC = 2500
    TILING_TYPE = Tile Size
    ROW_ATTR = _row
    YINC = 2500
    TILED -> BoundsExtractor
BoundsExtractor
    YMIN = _ymin
    YMAX = _ymax
    ZMIN = _zmin
    ZMAX = _zmax
    XMIN = _xmin
    XMAX = _xmax
    -> HTTPCaller
Note: Henter data fra NVDB tile for tile
HTTPCaller
    SAVE_FILE = Attribute
    TARGET_ATTR = _response_body
    HTTP_METHOD = GET
    RESPONSE_HEADER_LIST_ATTR = _headers
    TARGET_ATTR_ENCODING = utf-8
    CUSTOM_HEADERS = Accept;application/vnd.vegvesen.nvdb-v1+xml
    TRANSFER_TIMEOUT_LENGTH = 0
    CONNECTION_TIMEOUT_LENGTH = 0
    USE_COOKIES = Yes
    ERROR_ATTR = _error
    STATUS_CODE_ATTR = _http_status_code
    FOLLOW_REDIRECTS = Yes
    TARGET_URL = https://www.vegvesen.no/nvdb/api/sok?kriterie={%20lokasjon:%20{bbox:%20"@Value(_xmin),@Value(_ymin),@Value(_xmax),@Value(_ymax)"%20},%20kommune:%20[@Value(kommuneid)],%20objektTyper:%20[%20{%20id:%20570,%20antall:100000}]%20}
    VERIFY_SSL_CERTIFICATES = No
    -> XMLFeatureMapper
Note: Henter data fra NVDB kommune for kommune
HTTPCaller_3
    SAVE_FILE = Attribute
    TARGET_ATTR = _response_body
    HTTP_METHOD = GET
    RESPONSE_HEADER_LIST_ATTR = _headers
    TARGET_ATTR_ENCODING = utf-8
    CUSTOM_HEADERS = Accept;application/vnd.vegvesen.nvdb-v1+xml
    TRANSFER_TIMEOUT_LENGTH = 0
    CONNECTION_TIMEOUT_LENGTH = 0
    USE_COOKIES = Yes
    ERROR_ATTR = _error
    STATUS_CODE_ATTR = _http_status_code
    FOLLOW_REDIRECTS = Yes
    TARGET_URL = https://www.vegvesen.no/nvdb/api/sok?kriterie={%20lokasjon:%20{kommune:%20[@Value(kommuneid)]%20},%20objektTyper:%20[%20{%20id:%20570,%20antall:100000}]%20}
    VERIFY_SSL_CERTIFICATES = No
    -> XMLFeatureMapper
nvdb_trafikkulykker.trafikkulykke (writer POSTGIS_2)
    attributes: objid serial,PRIKEY, objtype varchar(32), nvdb_alvorligsteskadegrad varchar(80), nvdb_ulykkesdato date, nvdb_ukedag varchar(80), nvdb_registreringsdatofagdata date, nvdb_uhellkategori varchar(80), nvdb_uhellskode varchar(80), nvdb_antallenheter int4, nvdb_antalldrepteiulykken int4, nvdb_antallmegetalvorligskadet int4, nvdb_antallalvorligskadet int4, nvdb_antalllettereskadet int4, nvdb_vegtype varchar(80), nvdb_stedsforhold varchar(80), nvdb_midtdeler varchar(80), nvdb_dekketype varchar(80), nvdb_foereforhold varchar(80), nvdb_vaerforhold varchar(80), nvdb_lysforhold varchar(80), nvdb_felttype varchar(80), nvdb_antallkjoerefelt int4, nvdb_bebyggelse varchar(80), nvdb_vegbredde float8, nvdb_fartsgrense varchar(80), nvdb_temperatur int4, nvdb_kommunenr int4, nvdb_historiskvegstatus varchar(80), nvdb_historiskvegkategori varchar(80), nvdb_historiskvegnummer int4,
      nvdb_historiskhp int4, nvdb_historiskkilometerverdi int4, nvdb_vegnavn varchar(80), nvdb_stedfestingensnoeyaktighet varchar(80), datauttaksdato timestamp, nvdb_ulykkestidspunkt varchar(20)

Bookmark: XML-parsing og attributtmapping
Note: Mapper og eksponerer attributter fra / rå XML.
XMLFeatureMapper
    SCRIPT_XFMAP:
      <?xml version="1.0"?>
      <xfMap>
        <feature-map multi-feature-construction="true">
           <mapping match="vegObjekt">
              <feature-type><literal expr="vegObjekt"/> </feature-type>
           </mapping>
        </feature-map>
        <feature-content-map>
          <mapping match="egenskap">
             <attributes>
                <attribute type="sequenced">
                   <name><extract expr="./navn"/></name>
                   <value><extract expr="./verdi"/></value>
                </attribute>
             </attributes>
           </mapping>
          <mapping match="objektTypeNavn">
             <attributes>
                <attribute>
                   <name><literal expr="objtype"/></name>
                   <value><extract expr="."/></value>
                </attribute>
             </attributes>
           </mapping>
          <mapping match="geometriWgs84">
             <attributes>
                <attribute>
                   <name><literal expr="koordinater"/></name>
                   <value><extract expr="."/></value>
                </attribute>
             </attributes>
           </mapping>
       </feature-content-map>
      </xfMap>
    MERGE_ATTRS = No
    NEW_ATTRIBUTES = Alvorligste skadegrad Antall alvorlig skadet Antall drepte i ulykken Antall enheter Antall kjørefelt Antall lettere skadet Antall meget alvorlig skadet Bebyggelse Dekketype Fartsgrense Felttype Føreforhold Geometri, punkt Historisk hp Historisk kilometerverdi Historisk vegkategori Historisk vegnummer Historisk vegstatus Lysforhold Midtdeler Registreringsdato for fagdata Stedfestingens nøyaktighet Stedsforhold Temperatur Uhell kategori Uhellskode Ukedag Ulykkesdato Ulykkestidspunkt Vegbredde Vegnavn Vegtype Værforhold objtype Kommunenr koordinater
    XML_INPUT_TYPE = Attribute with XML document
    ATTRIBUTE_XML = _response_body
    CONFIGURATION_TYPE = Embedded xfMap script
    XML_SOURCE_NAME = _xml_source_
    FEATURE_TYPE_ATTR = fme_feature_type
    FEATURE_COUNT_PER_XML = _xml_feature_count_
    MAPPED -> AttributeRenamer
Note: Renamer til databaseskjema fra UML
AttributeRenamer
    ATTR_LIST = Alvorligste skadegrad,nvdb_alvorligsteskadegrad,,Antall alvorlig skadet,nvdb_antallalvorligskadet,,Antall drepte i ulykken,nvdb_antalldrepteiulykken,,Antall enheter,nvdb_antallenheter,,Antall kjørefelt,nvdb_antallkjoerefelt,,Antall lettere skadet,nvdb_antalllettereskadet,,Antall meget alvorlig skadet,nvdb_antallmegetalvorligskadet,,Bebyggelse,nvdb_bebyggelse,,Dekketype,nvdb_dekketype,,Fartsgrense,nvdb_fartsgrense,,Felttype,nvdb_felttype,,Føreforhold,nvdb_foereforhold,,Historisk hp,nvdb_historiskhp,,Historisk kilometerverdi,nvdb_historiskkilometerverdi,,Historisk vegkategori,nvdb_historiskvegkategori,,Historisk vegnummer,nvdb_historiskvegnummer,,Historisk vegstatus,nvdb_historiskvegstatus,,Lysforhold,nvdb_lysforhold,,Midtdeler,nvdb_midtdeler,,Registreringsdato for fagdata,nvdb_registreringsdatofagdata,,Stedfestingens nøyaktighet,nvdb_stedfestingensnoeyaktighet,,Stedsforhold,nvdb_stedsforhold,,Temperatur,nvdb_temperatur,,Uhell kategori,nvdb_uhellkategori,,Uhellskode,nvdb_uhellskode,,Ukedag,nvdb_ukedag,,Ulykkesdato,nvdb_ulykkesdato,,Vegbredde,nvdb_vegbredde,,Vegnavn,nvdb_vegnavn,,Vegtype,nvdb_vegtype,,Værforhold,nvdb_vaerforhold,,Kommunenr,nvdb_kommunenr,,Ulykkestidspunkt,nvdb_ulykkestidspunkt,
    -> AttributeValueMapper
Note: Mapper tekst til kode
AttributeValueMapper
    DIRECTION = Forward (Source To Destination)
    VAL_ATTR = nvdb_uhellskode
    LUT = Avsvinging i hver sin retning,42,Avsvinging i samme retning,41,Avsvingning til høyre foran kjørende i motsatt retning fra fortau eller G/S-veg,44,Avsvingning til venstre foran kjørende i motsatt retning fra fortau eller G/S-veg,45,Avsvingning til venstre foran kjørende i motsatt retning,40,Barn lekte i kjørebanen,86,Enslig kjøretøy kjørte på trafikkøy eller ende av midtdeler,97,Enslig kjøretøy kjørte utfor på høyre side i høyrekurve,93,Enslig kjøretøy kjørte utfor på høyre side i venstrekurve,94,Enslig kjøretøy kjørte utfor på høyre side på rett vegstrekning,90,Enslig kjøretøy kjørte utfor på venstre side i høyrekurve,92,Enslig kjøretøy kjørte utfor på venstre side i venstrekurve,95,Enslig kjøretøy kjørte utfor på venstre side på rett vegstrekning,91,Enslig kjøretøy kjørte utfor ved avsvinging i kryss o.l.,96,Enslig kjøretøy veltet i kjørebanen,3,Forbikjøring på høyre side i kryss eller avkjørsel,52,Forbikjøring på venstre side i kryss eller avkjørsel,51,Fotgjenger gikk langs vegen og ble påkjørt av ryggende kjøretøy,85,Fotgjenger gikk på vegens høyre side,80,Fotgjenger gikk på vegens venstre side,81,Fotgjenger krysset kjørebanen foran høyresvingende kjøretøy i kryss,72,Fotgjenger krysset kjørebanen foran venstresvingende kjøretøy i kryss,73,Fotgjenger krysset kjørebanen forøvrig,75,Fotgjenger krysset kjørebanen i gangfelt utenfor kryss,74,Fotgjenger krysset kjørebanen i kryss bak parkert eller stanset kjøretøy,76,Fotgjenger krysset kjørebanen og ble påkjørt av ryggende kjøretøy,78,Fotgjenger krysset kjørebanen på bortsiden av krysset,70,Fotgjenger krysset kjørebanen på hitsiden av krysset,71,Fotgjenger krysset kjørebanen utenfor kryss bak parkert eller stanset kjøretøy,77,Fotgjenger påkjørt på fortau,82,Fotgjenger påkjørt ved forbikjøring,83,Fotgjenger stod stille eller oppholdt seg forøvrig i kjørebanen,84,Hull i vegen o.l.,2,Høyresving foran kjørende i motsatt retning,61,Høyresving foran kjørende i samme retning,60,Høyresving foran venstresvingende kjøretøy,62,Kjørende fra G/S-veg krysset kjørebanen utenfor kryss,55,Kjørende fra fortau eller G/S-veg krysset kjørebanen på bortsiden av krysset,54,Kjørende fra fortau eller G/S-veg krysset kjørebanen på hitsiden av krysset,53,Kjøring i parallelle kjørefelter forøvrig,13,Kryssende kjøreretninger,50,Møting etter oppstart fra stanset eller parkert stilling,26,Møting i kurve,21,Møting på rett vegstrekning,20,Møting under forbikjøring av stanset eller parkert kjøretøy,25,Møting under forbikjøring i høyrekurve,23,Møting under forbikjøring i venstrekurve,24,Møting under forbikjøring på rett vegstrekning,22,Påkjøring av fast gjenstand på kjørebanen,1,Påkjøring av forankjørende ved skifte av felt til høyre,17,Påkjøring av forankjørende ved skifte av felt til venstre,16,Påkjøring av kjørende fra fortau eller G/S-veg, ved høyresving,35,Påkjøring av kjørende fra fortau eller G/S-veg, ved venstresving,36,Påkjøring av parkert kjøretøy på høyre side,4,Påkjøring av parkert kjøretøy på venstre side,5,Påkjøring av parkert kjøretøy ved forbikjøring,6,Påkjøring bakfra etter oppstart fra stanset eller parkert stilling,15,Påkjøring bakfra ved høyresving,30,Påkjøring bakfra ved venstresving,32,Påkjøring bakfra,14,Påkjøring forøvrig ved høyresving,31,Påkjøring forøvrig ved venstresving,33,Påkjøring ved vending foran kjørende i samme retning,34,Samtidig høyresving,66,Samtidig venstresving,65,Skifte av felt til høyre,12,Skifte av felt til venstre,11,Uhell med dyr innblandet,0,Uhell med uklart forløp / uhell som ikke faller inn under noen bestemt uh.kode,9,Uhell med uklart forløp hvor enslig kjøretøy kjørte utfor vegen,99,Uhell med uklart forløp hvor fotgjenger gikk langs eller oppholdt seg i kj.banen,89,Uhell med uklart forløp hvor fotgjenger krysset kjørebanen,79,Uhell med uklart forløp mellom kjøretøy med samme kjøreretning,19,Uhell med uklart forløp ved avsvinging fra motsatte kjøreretninger,49,Uhell med uklart forløp ved avsvinging fra samme kjøreretning,39,Uhell med uklart forløp ved kryssende kj.retn hvor ett el. begge kj.tøy svinger av,69,Uhell med uklart forløp ved kryssende kj.retn uten at noen kj.tøy svinger av,59,Uhell med uklart forløp ved møting,29,Uhell ved av- eller påstigning av kjøretøy,8,Vending foran kjørende i motsatt retning,43,Venstresving foran kjørende i motsatt retning,64,Venstresving foran kjørende i samme retning,63,Øvrige parkeringsuhell,7,Forbikjøring,10
    SRC = nvdb_uhellskode
    -> TimeStamper
Note: Setter datauttaksdato
TimeStamper
    TIME_ATTR = datauttaksdato
    FMT = FME Date/Time (^Y^m^d^H^M^S)
    -> AttributeCreator
Note: Setter feature type
AttributeCreator
    ATTR_LIST = fme_feature_type,trafikkulykke
    -> Counter
Note: Lager objektID
Counter
    DOMAIN = counter
    SCOPE = Global
    START = 0
    CNT_ATTR = objid
    -> GeometryReplacer

Bookmark: Lager geometri
GeometryReplacer
    SOURCE = @Value(koordinater)
    KIND_LONG = OGC Well Known Text
    REMOVE_ATTRIBUTE = Yes
    -> Reprojector
Note: Til EPSG:4258
Reprojector
    DEST = EPSG:4258
    RASTER_CELL_SIZE = Preserve Cells
    SOURCE = EPSG:4326
    INTERPOLATION_TYPE_NAME = Nearest Neighbor
    REPROJECTED -> CoordinateSystemSetter
Note: Setter koordsys i objektenes metadata
CoordinateSystemSetter
    COORDSYS = EPSG:4258
    -> nvdb_trafikkulykker.trafikkulykke (writer POSTGIS_2)

Bookmark: Trafikkmengde
admingrense.kommuner (reader POSTGRES_1)
    attributes: kommuneid int2,PRIKEY, navn varchar(80)
    -> HTTPCaller_2
Note: Henter data fra NVDB kommune for kommune
HTTPCaller_2
    SAVE_FILE = Attribute
    TARGET_ATTR = _response_body
    HTTP_METHOD = GET
    RESPONSE_HEADER_LIST_ATTR = _headers
    TARGET_ATTR_ENCODING = utf-8
    CUSTOM_HEADERS = Accept;application/vnd.vegvesen.nvdb-v1+xml
    TRANSFER_TIMEOUT_LENGTH = 360
    CONNECTION_TIMEOUT_LENGTH = 360
    USE_COOKIES = No
    ERROR_ATTR = _error
    STATUS_CODE_ATTR = _http_status_code
    FOLLOW_REDIRECTS = Yes
    TARGET_URL = https://www.vegvesen.no/nvdb/api/sok?kriterie={%20lokasjon:%20{kommune:%20[@Value(kommuneid)]%20},%20objektTyper:%20[%20{%20id:%20540,%20antall:100000}]%20}
    VERIFY_SSL_CERTIFICATES = Yes
    -> XMLFeatureMapper_2
nvdb_trafikkmengde.trafikkmengde (writer POSTGIS_2)
    attributes: objid serial,PRIKEY, objtype varchar(32), nvdb_aadttotal int4, nvdb_aadtandellangekjoeretoey int4, nvdb_aargjelderfor int4, nvdb_grunnlagforaadt varchar(80), nvdb_ansvarligid varchar(80), nvdb_aadtstart int4, nvdb_aadtslutt int4, nvdb_oppdatertfra varchar(80), nvdb_tellepunktprimaert int4, nvdb_tellepunktsekundaert int4, nvdb_forholdaadt float8, nvdb_forholdlange float8, nvdb_koplingsaar int4, nvdb_mfaktor float8, datauttaksdato timestamp, nvdb_trafikkarbeidstall int4

Bookmark: Mapper attributter
Note: Mapper og eksponerer attributter fra / rå XML.
XMLFeatureMapper_2
    SCRIPT_XFMAP:
      <?xml version="1.0"?>
      <xfMap>
        <feature-map multi-feature-construction="true">
           <mapping match="vegObjekt">
              <feature-type><literal expr="vegObjekt"/> </feature-type>
           </mapping>
        </feature-map>
        <feature-content-map>
          <mapping match="egenskap">
             <attributes>
                <attribute type="sequenced">
                   <name><extract expr="./navn"/></name>
                   <value><extract expr="./verdi"/></value>
                </attribute>
             </attributes>
           </mapping>
          <mapping match="objektTypeNavn">
             <attributes>
                <attribute>
                   <name><literal expr="objtype"/></name>
                   <value><extract expr="."/></value>
                </attribute>
             </attributes>
           </mapping>
          <mapping match="sluttDato">
             <attributes>
                <attribute>
                   <name><literal expr="sluttDato"/></name>
                   <value><extract expr="."/></value>
                </attribute>
             </attributes>
           </mapping>
          <mapping match="startDato">
             <attributes>
                <attribute>
                   <name><literal expr="startDato"/></name>
                   <value><extract expr="."/></value>
                </attribute>
             </attributes>
           </mapping>
          <mapping match="strekningslengde">
             <attributes>
                <attribute>
                   <name><literal expr="strekningslengde"/></name>
                   <value><extract expr="."/></value>
                </attribute>
             </attributes>
           </mapping>
          <mapping match="geometriWgs84">
             <attributes>
                <attribute>
                   <name><literal expr="koordinater"/></name>
                   <value><extract expr="."/></value>
                </attribute>
             </attributes>
           </mapping>
       </feature-content-map>
      </xfMap>
    MERGE_ATTRS = No
    NEW_ATTRIBUTES = koordinater objtype Ansvarlig - id ForholdLange ForholdÅDT Grunnlag for ÅDT Koplingsår Mfaktor sluttDato startDato strekningslengde Tellepunkt, primært ÅDT, andel lange kjøretøy ÅDT, slutt ÅDT, start ÅDT, total År, gjelder for Oppdatert fra ForholdLange Tellepunkt, sekundært Trafikkarbeidstall
    XML_INPUT_TYPE = Attribute with XML document
    ATTRIBUTE_XML = _response_body
    CONFIGURATION_TYPE = Embedded xfMap script
    XML_SOURCE_NAME = _xml_source_
    FEATURE_TYPE_ATTR = fme_feature_type
    FEATURE_COUNT_PER_XML = _xml_feature_count_
    MAPPED -> AttributeRenamer_2
AttributeRenamer_2
    ATTR_LIST = Ansvarlig - id,nvdb_ansvarligid,,ForholdLange,nvdb_foereforhold,,ForholdÅDT,nvdb_forholdaadt,,Grunnlag for ÅDT,nvdb_grunnlagforaadt,,Koplingsår,nvdb_koplingsaar,,Mfaktor,nvdb_mfaktor,,Tellepunkt, primært,nvdb_tellepunktprimaert,,ÅDT, slutt,nvdb_aadtslutt,,ÅDT, start,nvdb_aadtstart,,ÅDT, total,nvdb_aadttotal,,ÅDT, andel lange kjøretøy,nvdb_aadtandellangekjoeretoey,,År, gjelder for,nvdb_aargjelderfor,,Oppdatert fra,nvdb_oppdatertfra,,ForholdLange,nvdb_forholdlange,,Tellepunkt, sekundært,nvdb_tellepunktsekundaert,,Trafikkarbeidstall,nvdb_trafikkarbeidstall,
    -> TimeStamper_2
TimeStamper_2
    TIME_ATTR = datauttaksdato
    FMT = FME Date/Time (^Y^m^d^H^M^S)
    -> Counter_2

Bookmark: Bygger geometri
Note: ObjektID
Counter_2
    DOMAIN = counter
    SCOPE = Global
    START = 0
    CNT_ATTR = objid
    -> GeometryReplacer_2
GeometryReplacer_2
    SOURCE = @Value(koordinater)
    KIND_LONG = OGC Well Known Text
    REMOVE_ATTRIBUTE = Yes
    -> Reprojector_2
Reprojector_2
    DEST = EPSG:4258
    RASTER_CELL_SIZE = Preserve Cells
    SOURCE = EPSG:4326
    INTERPOLATION_TYPE_NAME = Nearest Neighbor
    REPROJECTED -> CoordinateSystemSetter_2
CoordinateSystemSetter_2
    COORDSYS = EPSG:4258
    -> AttributeRounder
AttributeRounder
    SRC_ATTRS = nvdb_aadtandellangekjoeretoey,nvdb_aadtslutt,nvdb_aadtstart,nvdb_aadttotal
    PLACES = 0
    ROUND_TYPE = nearest
    -> nvdb_trafikkmengde.trafikkmengde (writer POSTGIS_2)
