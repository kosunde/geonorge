FME workspace korallrev_postgis2none.fmw

Parameters:
- SourceDataset_POSTGIS = geonor01tst   # Database

Readers:
- POSTGIS_1: POSTGIS from $(SourceDataset_POSTGIS)

Bookmark: Metode for joining av kommune- og fylkesopplysninger i FME
Note: Objektklasse: KORALLREV
korallrev.korallrev (reader POSTGIS_1)
    attributes: objid serial,PRIKEY, objtype varchar(32), obs_metode varchar(80), obs_start timestamp, obs_slutt timestamp, bmnatyp varchar(80), bm_kildenavn varchar(80), bm_kildetittel varchar(80), bmkildtyp varchar(80), bm_kildeaar int4, dybde_min int4, dybde_max int4, lokalid uuid,PRIKEY, navnerom varchar(80), versjonid varchar(80), verifiseringsdato timestamp, maalemetode varchar(80), noeyaktighet int4, synbarhet varchar(80), maalemetodehoeyde varchar(80), h_noeyaktighet int4, max_avvik int4, medium varchar(80), opphav varchar(80), noeyaktighetsklasse varchar(80), produkt varchar(80), versjon varchar(80)
    -> PointOnAreaOverlayer [input 1]
Note: Objektklasse: Kommuneflate
admingrense.kommuneflate (reader POSTGIS_1)
    attributes: kommuneid int4, navn varchar(80)
    -> PointOnAreaOverlayer [input 2]
PointOnAreaOverlayer
    OV_ATTR = _overlaps
    INCOMING_PREFIX = k_
    POLYS_FIRST = NO
    ATTR_ACCUM_MODE = Prefix Incoming
    POINT -> PointOnAreaOverlayer_2 [input 1]
Note: Objektklasse: Fylkeflate
admingrense.fylkeflate (reader POSTGIS_1)
    attributes: fylkeid int4, navn varchar(80)
    -> PointOnAreaOverlayer_2 [input 2]
PointOnAreaOverlayer_2
    OV_ATTR = _overlaps
    INCOMING_PREFIX = f_
    POLYS_FIRST = NO
    ATTR_ACCUM_MODE = Prefix Incoming
    POINT -> NullAttributeMapper
NullAttributeMapper
    NEW_VALUE = 99
    NULL_TREATMENT = New Value
    SOURCE_ATTR_VAL = Null Empty "Missing (Selected Attributes Only)"
    ATTRCHOICE = Selected Attributes
    ATTRLIST = f_fylkeid
    -> NullAttributeMapper_2
NullAttributeMapper_2
    NEW_VALUE = Uplassert-i-fylke
    NULL_TREATMENT = New Value
    SOURCE_ATTR_VAL = Null Empty "Missing (Selected Attributes Only)"
    ATTRCHOICE = Selected Attributes
    ATTRLIST = f_navn
    -> NullAttributeMapper_3
NullAttributeMapper_3
    NEW_VALUE = 9999
    NULL_TREATMENT = New Value
    SOURCE_ATTR_VAL = Null Empty "Missing (Selected Attributes Only)"
    ATTRCHOICE = Selected Attributes
    ATTRLIST = k_kommuneid
    -> NullAttributeMapper_4
NullAttributeMapper_4
    NEW_VALUE = Uplassert-i-kommune
    NULL_TREATMENT = New Value
    SOURCE_ATTR_VAL = Null Empty "Missing (Selected Attributes Only)"
    ATTRCHOICE = Selected Attributes
    ATTRLIST = k_navn
    -> AttributeRemover
AttributeRemover
    REMOVE_ATTRS = _overlaps
    -> FME_modell_med_kommune
FME_modell_med_kommune: Inspector

Bookmark: Metode for joining av kommune- og fylkesopplysninger i PostGIS
Note: View: V_KORALLREV
korallrev.v_korallrev (reader POSTGIS_1)
    attributes: objid int4, objtype varchar(32), obs_metode varchar(80), obs_start timestamp, obs_slutt timestamp, bmnatyp varchar(80), bm_kildenavn varchar(80), bm_kildetittel varchar(80), bmkildtyp varchar(80), bm_kildeaar int4, dybde_min int4, dybde_max int4, lokalid uuid, navnerom varchar(80), versjonid varchar(80), verifiseringsdato timestamp, maalemetode varchar(80), noeyaktighet int4, synbarhet varchar(80), maalemetodehoeyde varchar(80), h_noeyaktighet int4, max_avvik int4, medium varchar(80), opphav varchar(80), noeyaktighetsklasse varchar(80), produkt varchar(80), versjon varchar(80), k_kommuneid int4, k_navn varchar(80), f_fylkeid int4,
      f_navn varchar(80)
    -> View_med_kommune
View_med_kommune: Inspector
