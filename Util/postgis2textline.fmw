FME workspace postgis2textline.fmw

Parameters:
- SourceDataset_POSTGIS = geonortst@nnridb504:5432/geonor01tst   # Connection
- DestDataset_TEXTLINE = C:\Users\xsunknu\Desktop\Planomriss_postgis2sosi.bat   # Destination Text File

Readers:
- POSTGIS_1: POSTGIS from $(SourceDataset_POSTGIS)

Writers:
- TEXTLINE_1: TEXTLINE to $(DestDataset_TEXTLINE)

Creator_2
    GEOMTYPE = Geometry Object
    NUM = 1
    CREATED -> AttributeCreator_4
AttributeCreator_4
    ATTR_LIST = text_line_data,REM Hakker opp planomriss i landsdekkende, kommunevise og fylkesvise SOSI-filer i lokal UTM-sone  ,nr,0
    -> Sorter
Creator
    GEOMTYPE = Geometry Object
    NUM = 1
    CREATED -> AttributeCreator_3
AttributeCreator_3
    ATTR_LIST = text_line_data,"$(FME_HOME_ENCODED)fme.exe" \\nnrite507\Geodata\Jobs\Planomriss_postgis2sosi\Planomriss_postgis2sosi.fmw --OUTPUT_EPSG_CODE "25833",nr,5000
    -> Sorter
admingrense.fylkeflate (reader POSTGIS_1)
    attributes: fylkeid int4, navn varchar(80)
    -> AttributeCreator_2
AttributeCreator_2
    ATTR_LIST = text_line_data,"FME_CONDITIONAL:DEFAULT_VALUE'_FME_NO_OP_'BOOL_OP;OR;COMPOSITE_TEST;<Unused>;TEST @Value(fylkeid) < 18'"$(FME_HOME_ENCODED)fme.exe" \\nnrite507\Geodata\Jobs\Planomriss_postgis2sosi\Planomriss_postgis2sosi.fmw --FNR "@Value(fylkeid)" --OUTPUT_EPSG_CODE "25832" --FANOUT "Fylker"'BOOL_OP;AND;COMPOSITE_TEST;<Unused>;TEST @Value(fylkeid) >= 18;TEST @Value(fylkeid) < 20'"$(FME_HOME_ENCODED)fme.exe" \\nnrite507\Geodata\Jobs\Planomriss_postgis2sosi\Planomriss_postgis2sosi.fmw --FNR "@Value(fylkeid)" --OUTPUT_EPSG_CODE "25833" --FANOUT "Fylker"'BOOL_OP;AND;COMPOSITE_TEST;<Unused>;TEST @Value(fylkeid) >= 20'"$(FME_HOME_ENCODED)fme.exe" \\nnrite507\Geodata\Jobs\Planomriss_postgis2sosi\Planomriss_postgis2sosi.fmw --FNR "@Value(fylkeid)" --OUTPUT_EPSG_CODE "25835" --FANOUT "Fylker"'FME_NUM_CONDITIONS4___",nr,@Evaluate(3000 + @Value(fylkeid))
    -> Sorter
admingrense.kommuneflate (reader POSTGIS_1)
    attributes: kommuneid int4, navn varchar(80)
    -> AttributeCreator
AttributeCreator
    ATTR_LIST = text_line_data,"FME_CONDITIONAL:DEFAULT_VALUE'_FME_NO_OP_'BOOL_OP;OR;COMPOSITE_TEST;<Unused>;TEST @Value(kommuneid) < 1800'"$(FME_HOME_ENCODED)fme.exe" \\nnrite507\Geodata\Jobs\Planomriss_postgis2sosi\Planomriss_postgis2sosi.fmw --KNR "@Value(kommuneid)" --OUTPUT_EPSG_CODE "25832" --FANOUT "Kommuner"'BOOL_OP;AND;COMPOSITE_TEST;<Unused>;TEST @Value(kommuneid) >= 1800;TEST @Value(kommuneid) < 2000'"$(FME_HOME_ENCODED)fme.exe" \\nnrite507\Geodata\Jobs\Planomriss_postgis2sosi\Planomriss_postgis2sosi.fmw --KNR "@Value(kommuneid)" --OUTPUT_EPSG_CODE "25833" --FANOUT "Kommuner"'BOOL_OP;AND;COMPOSITE_TEST;<Unused>;TEST @Value(kommuneid) >= 2000'"$(FME_HOME_ENCODED)fme.exe" \\nnrite507\Geodata\Jobs\Planomriss_postgis2sosi\Planomriss_postgis2sosi.fmw --KNR "@Value(kommuneid)" --OUTPUT_EPSG_CODE "25835" --FANOUT "Kommuner"'FME_NUM_CONDITIONS4___",nr,@Value(kommuneid)
    -> Sorter
Sorter
    SORT_PARM = nr NUMERIC ASCENDING
    SORTED -> text_line (writer TEXTLINE_1)
text_line (writer TEXTLINE_1)
    attributes: text_line_data buffer
