FME workspace stoydata2postgis.fmw

Parameters:
- URL_FORSVARETSTOY = ftp://ftp.statkart.no/Forsvaret_Støy/Stoy_skytefelt_og_baner_FB.gdb.zip   # FTP-link til zip-fil med støydata for Forsvaret
- DEST_FORSVARETSTOY = .\Forsvaret_Stoy.zip   # Målfil for støydata fra forsvaret
- URL_AVINORSTOY = ftp://ftp.statkart.no/Avinor/Støy/Stoysoner.gdb/**   # Ftp-link til zip-fil med støydata fra Avinor
- DEST_AVINORSTOY = .\Avinor_stoy.gdb   # Målfil for støydata fra Avinor
- SourceDataset_FILEGDB_6 = D:\Data\Støy\Forsvaret_Støy\Stoy_skytefelt_og_baner_FB.gdb.zip   # Source Geodatabase
- SourceDataset_SHAPE = ""$(FME_MF_DIR)banestoy\Bærum_Lden2015.shp" "$(FME_MF_DIR)banestoy\Bærum_Lekva2015.shp""   # Source Esri Shape File(s)
- DestDataset_POSTGIS = geonortst@nnridb504:5432/geonor01tst   # Connection
- SourceDataset_SOSI = $(FME_MF_DIR)vegstoy\FSV220700\FSV220700.sos   # Source SOSI File
- SourceDataset_SOSI_3 = $(FME_MF_DIR)vegstoy\FSV220800\FSV220800.sos   # Source SOSI File
- SourceDataset_SHAPE_3 = $(FME_MF_DIR)vegstoy\stoy_04_05\stoy_norstoy.shp   # Source Esri Shape File(s)
- CONFIG_FILE:   # Python Script
      #-------------------------------------------------------------------------------
      # Name:        GetConfigFile
      # Purpose:
      #
      # Author:      xsunknu
      #
      # Created:     21.08.2015
      # Copyright:   (c) xsunknu 2015
      # Licence:     <your licence>
      #-------------------------------------------------------------------------------
      
      import os, fme
      
      fmwdir = fme.macroValues['FME_MF_DIR']
      fmwfile = fme.macroValues['FME_MF_NAME']
      
      fmwfile = os.path.join(fmwdir, fmwfile)
      configfile = os.path.splitext(fmwfile)[0] + '_config.xml'
      
      return configfile
- PG_DB:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgdb').text
      
      return value

Readers:
- FILEGDB_1: FILEGDB from $(SourceDataset_FILEGDB_6)
- SHAPE_1: SHAPE from $(SourceDataset_SHAPE)
- SOSI_1: SOSI from $(SourceDataset_SOSI)
- SOSI_2: SOSI from $(SourceDataset_SOSI_3)
- SHAPE_2: SHAPE from $(SourceDataset_SHAPE_3)

Writers:
- POSTGIS_1: POSTGIS to $(PG_DB)
- POSTGIS_2: POSTGIS to $(PG_DB)
- POSTGIS_3: POSTGIS to $(DestDataset_POSTGIS)

Bookmark: Støy Jernbane
Bærum_Lekva2015 (reader SHAPE_1)
    attributes: DB_LO number(7,3), DB_HI number(7,3)
    -> Deaggregator_3
Bærum_Lden2015 (reader SHAPE_1)
    attributes: DB_LO number(7,3), DB_HI number(7,3)
    -> Deaggregator_3
Deaggregator_3
    GEOM_NAME_FIELD = _geometry_name
    CHILD_ID_ATTR = _hierarchy_child_id_list
    LIST_ATTR_MODE_LOOKUP = LEAN
    EXPLODE_INSTANCES = No
    COPY_ATTR = Every Node
    PART_NUMBER_FIELD = _part_number
    ID_SELECTION = ID and Parent ID
    ID_ATTR = _hierarchy_id
    PARENT_ID_ATTR = _hierarchy_parent_id
    MODE = Flatten One Level
    SPLIT_COMPOSITES = No
    DEAGGREGATED -> Reprojector_5
    DEAGGREGATED -> TopologyBuilder_3 [input 3]
Reprojector_5
    DEST = EPSG:4258
    INTERPOLATION_TYPE_NAME = Nearest Neighbor
    RASTER_CELL_SIZE = Preserve Cells
    SOURCE = Read from feature
    REPROJECTED -> BulkAttributeRenamer_3
BulkAttributeRenamer_3
    PATTERN_ACTION_DISP = Change Case
    ATTRCHOICE = All Attributes
    CASE_CHANGE_TYPE = lowercase
    -> AttributeRenamer_3
AttributeRenamer_3
    ATTR_LIST = stoysonekategori,stoeysonekategori,,stoymetode,stoeymetode,,stoykildenavn,stoeykildenavn,,stoykilde,stoeykilde,,stoykildeidentifikasjon,stoeykildeidentifikasjon,,malemetode,maalemetode,
    -> AttributeCreator_6
AttributeCreator_6
    ATTR_LIST = lokalid,uuid_generate_v4(),navnerom,NO_KARTVERKET_STOY,objtype,Støy
    -> NullAttributeMapper_3
NullAttributeMapper_3
    NULL_TREATMENT = New Value
    OTHER_VALUE = 0
    ATTRLIST = maalemetode
    ATTRCHOICE = Selected Attributes
    NEW_VALUE = 99
    -> TimeStamper_3
TimeStamper_3
    TIME_ATTR = versjonid
    FMT = FME Date/Time (^Y^m^d^H^M^S)
    -> stoy_bane.stoy (writer POSTGIS_1)
stoy_bane.stoy (writer POSTGIS_1)
    attributes: objid serial,PRIKEY, objtype varchar(32), stoeysonekategori varchar(80), stoeykilde varchar(80), stoeykildeidentifikasjon varchar(80), stoeykildenavn varchar(80), stoeymetode varchar(80), beregnetaar varchar(80), lokalid uuid,PRIKEY, navnerom varchar(80), versjonid varchar(80), datafangstdato timestamp, oppdateringsdato timestamp, maalemetode varchar(80), noeyaktighet int4, max_avvik int4, opphav varchar(80), kommune varchar(80), informasjon varchar(80)
TopologyBuilder_3
    MAX = 0
    ALL_EDGES = Yes
    ALLOW_CYCLES = No
    OVERLAPPING_MODE = No
    CLEAN_DATA = No
    PROP_ATTRS = No
    LINE -> Reprojector_6
Reprojector_6
    DEST = EPSG:4258
    INTERPOLATION_TYPE_NAME = Nearest Neighbor
    RASTER_CELL_SIZE = Preserve Cells
    SOURCE = Read from feature
    REPROJECTED -> Counter_4
Counter_4
    SCOPE = Global
    DOMAIN = counter
    START = 0
    CNT_ATTR = objid
    -> AttributeCreator_7
AttributeCreator_7
    ATTR_LIST = objtype,Støygrense
    -> stoy_bane.stoygrense (writer POSTGIS_1)
stoy_bane.stoygrense (writer POSTGIS_1)
    attributes: objid serial,PRIKEY, objtype varchar(32)

Bookmark: SOSI
Stoy (reader SOSI_1)
    attributes: SOSI_id SOSI_int32, STOYMETODE SOSI_char(255), STOYSONEKATEGORI SOSI_char(1), DATAFANGSTDATO SOSI_datetime, STOYKILDE SOSI_char(2), STOYKILDENAVN SOSI_char(255), KOMM SOSI_int16, MALEMETODE SOSI_int16, STOYINTERVALL SOSI_int16, OBJTYPE SOSI_char(32), STOYENHET SOSI_char(255), BEREGNETAR SOSI_char(255)
    -> Deaggregator_4
Stoy (reader SOSI_2)
    attributes: SOSI_id SOSI_int32, STOYMETODE SOSI_char(255), STOYSONEKATEGORI SOSI_char(1), DATAFANGSTDATO SOSI_datetime, STOYKILDE SOSI_char(2), STOYKILDENAVN SOSI_char(255), KOMM SOSI_int16, MALEMETODE SOSI_int16, STOYINTERVALL SOSI_int16, OBJTYPE SOSI_char(32), STOYENHET SOSI_char(255), BEREGNETAR SOSI_char(255)
    -> Deaggregator_4
Deaggregator_4
    GEOM_NAME_FIELD = _geometry_name
    CHILD_ID_ATTR = _hierarchy_child_id_list
    LIST_ATTR_MODE_LOOKUP = LEAN
    EXPLODE_INSTANCES = No
    COPY_ATTR = Every Node
    PART_NUMBER_FIELD = _part_number
    ID_SELECTION = ID and Parent ID
    ID_ATTR = _hierarchy_id
    PARENT_ID_ATTR = _hierarchy_parent_id
    MODE = Flatten One Level
    SPLIT_COMPOSITES = No
    DEAGGREGATED -> DonutBridgeBuilder
DonutBridgeBuilder
    -> Reprojector_7
    -> DonutBridgeBuilder_Output
Reprojector_7
    DEST = EPSG:4258
    INTERPOLATION_TYPE_NAME = Nearest Neighbor
    RASTER_CELL_SIZE = Preserve Cells
    SOURCE = Read from feature
    REPROJECTED -> BulkAttributeRenamer_5
BulkAttributeRenamer_5
    PATTERN_ACTION_DISP = Change Case
    ATTRCHOICE = All Attributes
    CASE_CHANGE_TYPE = lowercase
    -> AttributeRenamer_4
AttributeRenamer_4
    ATTR_LIST = stoysonekategori,stoeysonekategori,,stoymetode,stoeymetode,,stoykilde,stoeykilde,,stoykildenavn,stoeykildenavn,,beregnetar,beregnetaar,,komm,kommune,,malemetode,maalemetode,
    -> AttributeCreator_8
DonutBridgeBuilder_Output: Inspector
Stoygrense (reader SOSI_1)
    attributes: SOSI_id SOSI_int32, INFORMASJON SOSI_char(255), OBJTYPE SOSI_char(32), MALEMETODE SOSI_int16
    -> Reprojector_8
Stoygrense (reader SOSI_2)
    attributes: SOSI_id SOSI_int32, INFORMASJON SOSI_char(255), OBJTYPE SOSI_char(32), MALEMETODE SOSI_int16
    -> Reprojector_8
Reprojector_8
    DEST = EPSG:4258
    INTERPOLATION_TYPE_NAME = Nearest Neighbor
    RASTER_CELL_SIZE = Preserve Cells
    SOURCE = Read from feature
    REPROJECTED -> Counter_5
Counter_5
    SCOPE = Global
    DOMAIN = counter
    START = 0
    CNT_ATTR = objid
    -> AttributeCreator_9
AttributeCreator_9
    ATTR_LIST = objtype,Støygrense
    -> stoy_veg.stoygrense (writer POSTGIS_3)
stoy_veg.stoygrense (writer POSTGIS_3)
    attributes: objid int4,PRIKEY, objtype varchar(32)
AttributeCreator_8
    ATTR_LIST = navnerom,NO_KARTVERKET_STOY,objtype,Støy,lokalid,uuid_generate_v4()
    -> NullAttributeMapper_4
NullAttributeMapper_4
    NULL_TREATMENT = New Value
    OTHER_VALUE = 0
    ATTRLIST = maalemetode
    ATTRCHOICE = Selected Attributes
    NEW_VALUE = 99
    -> TimeStamper_4
TimeStamper_4
    TIME_ATTR = versjonid
    FMT = FME Date/Time (^Y^m^d^H^M^S)
    -> Counter_6
Counter_6
    SCOPE = Global
    DOMAIN = counter
    START = 0
    CNT_ATTR = objid
    -> stoy_veg.stoy (writer POSTGIS_3)
stoy_veg.stoy (writer POSTGIS_3)
    attributes: objid int4,PRIKEY, objtype varchar(32), stoeysonekategori varchar(80), stoeykilde varchar(80), stoeykildeidentifikasjon varchar(80), stoeykildenavn varchar(80), stoeymetode varchar(80), beregnetaar varchar(80), lokalid uuid, navnerom varchar(80), versjonid varchar(80), datafangstdato timestamp, oppdateringsdato timestamp, maalemetode varchar(80), noeyaktighet int4, max_avvik int4, opphav varchar(80), kommune varchar(80), informasjon varchar(80)

Bookmark: Støy Veg
stoy_norstoy (reader SHAPE_2)
    attributes: OBJECTID number(9,0), ORIG_FID number(19,11), FTEMA number(19,11), OBJTYPE char(254), STOYKILDE char(254), STOYENHET char(254), STOYMETODE char(254), BEREGNETAR number(19,11), STOYINTER number(19,11), STOYSONEKA char(254), Vertices number(9,0), OBJECTID_1 number(9,0), SHAPE_Leng number(19,11), SHAPE_Area number(19,11)
    -> Deaggregator_5
Deaggregator_5
    GEOM_NAME_FIELD = _geometry_name
    CHILD_ID_ATTR = _hierarchy_child_id_list
    LIST_ATTR_MODE_LOOKUP = LEAN
    EXPLODE_INSTANCES = No
    COPY_ATTR = Every Node
    PART_NUMBER_FIELD = _part_number
    ID_SELECTION = ID and Parent ID
    ID_ATTR = _hierarchy_id
    PARENT_ID_ATTR = _hierarchy_parent_id
    MODE = Flatten One Level
    SPLIT_COMPOSITES = No
    DEAGGREGATED -> Reprojector_9
Reprojector_9
    DEST = EPSG:4258
    INTERPOLATION_TYPE_NAME = Nearest Neighbor
    RASTER_CELL_SIZE = Preserve Cells
    SOURCE = Read from feature
    REPROJECTED -> TopologyBuilder_4 [input 3]
    REPROJECTED -> StringReplacer
TopologyBuilder_4
    MAX = 0
    ALL_EDGES = Yes
    ALLOW_CYCLES = No
    OVERLAPPING_MODE = No
    CLEAN_DATA = No
    PROP_ATTRS = No
    LINE -> Counter_5
StringReplacer
    FIND_TEXT = Ã¸
    REPLACE_TEXT = ø
    REGEXP = no
    CASE = no
    SRC_ATTRS = _geometry_name,_hierarchy_id,_hierarchy_parent_id,_part_number,BEREGNETAR,FTEMA,OBJECTID,OBJECTID_1,OBJTYPE,ORIG_FID,SHAPE_Area,SHAPE_Leng,STOYENHET,STOYINTER,STOYKILDE,STOYMETODE,STOYSONEKA,Vertices
    NO_MATCH = _FME_NO_OP_
    -> AttributeRenamer_5
AttributeRenamer_5
    ATTR_LIST = OBJTYPE,objtype,,STOYKILDE,stoeykilde,,STOYMETODE,stoeymetode,,STOYSONEKA,stoeysonekategori,,BEREGNETAR,beregnetaar,
    -> AttributeCreator_8

Bookmark: Støy flyplasser Forsvaret
STOY_FLYPLASSER_FLATE_FRA_AVINOR_2014 (reader FILEGDB_1)
    attributes: OBJECTID objectid, PERIMETER double, OPPR smallint, X double, Y double, KOORDH double, ICAO text(24), LHSTOY int, ENDRETAV text(24), LUKKET text(100), STOYSONEKATEGORI text(1), FTEMA smallint, MALEMETODE smallint, NOYAKTIGHE int, SYNBARHET smallint, H_MALEMETODE smallint, H_NOYAKTIGHET int, MAX_AVVIK int, OBJTYPE text(32), STOYKILDENAVN text(50), PRODUKT text(15), VERSJON text(20), DATFGSTDATO text(20), STOEYKILDE text(2), DATO date, SHAPE_Length double, SHAPE_Area double
    -> Deaggregator_2
    -> TopologyBuilder [input 3]

Bookmark: Støy flyplass
TopologyBuilder
    MAX = 0
    ALL_EDGES = Yes
    ALLOW_CYCLES = No
    OVERLAPPING_MODE = No
    CLEAN_DATA = No
    PROP_ATTRS = No
    LINE -> AttributeCreator_4
AttributeCreator_4
    ATTR_LIST = objtype,Støygrense
    -> Reprojector
Reprojector
    DEST = EPSG:4258
    INTERPOLATION_TYPE_NAME = Nearest Neighbor
    RASTER_CELL_SIZE = Preserve Cells
    SOURCE = Read from feature
    REPROJECTED -> Counter
Counter
    SCOPE = Global
    DOMAIN = counter
    START = 0
    CNT_ATTR = objid
    -> stoy_flyplass.stoeygrense (writer POSTGIS_2)
stoy_flyplass.stoeygrense (writer POSTGIS_2)
    attributes: objid serial,PRIKEY, objtype varchar(32)
Deaggregator_2
    GEOM_NAME_FIELD = _geometry_name
    CHILD_ID_ATTR = _hierarchy_child_id_list
    LIST_ATTR_MODE_LOOKUP = LEAN
    EXPLODE_INSTANCES = No
    COPY_ATTR = Every Node
    PART_NUMBER_FIELD = _part_number
    ID_SELECTION = ID and Parent ID
    ID_ATTR = _hierarchy_id
    PARENT_ID_ATTR = _hierarchy_parent_id
    MODE = Flatten One Level
    SPLIT_COMPOSITES = No
    DEAGGREGATED -> CoordinateRounder_2
CoordinateRounder_2
    ZPREC = 0
    YPREC = 2
    XPREC = 2
    ROUNDED -> DateFormatter
DateFormatter
    INVALID_DATE_VALUE = _FME_NO_OP_
    SRCFMT = Unknown - Automatic Detection
    DATE_ATTR = DATFGSTDATO
    FMT = FME Date/Time (%Y%m%d%H%M%S)
    -> Reprojector_2
Reprojector_2
    DEST = EPSG:4258
    INTERPOLATION_TYPE_NAME = Nearest Neighbor
    RASTER_CELL_SIZE = Preserve Cells
    SOURCE = Read from feature
    REPROJECTED -> BulkAttributeRenamer_2
BulkAttributeRenamer_2
    PATTERN_ACTION_DISP = Change Case
    ATTRCHOICE = All Attributes
    CASE_CHANGE_TYPE = lowercase
    -> AttributeCreator
AttributeCreator
    ATTR_LIST = objtype,Støy,stoeykilde,F,beregnetaar,@Substring(@Value(datfgstdato),-4,-1),navnerom,NO_KARTVERKET_STOY,lokalid,uuid_generate_v4()
    -> AttributeRenamer
AttributeRenamer
    ATTR_LIST = stoysonekategori,stoeysonekategori,,malemetode,maalemetode,,noyaktighe,noeyaktighet,,oppr,opphav,,stoykildenavn,stoeykildenavn,,datfgstdato,datafangstdato,
    -> Tester
Tester
    TEST_DESCRIPTION = ""
    TEST_CLAUSE = "TEST @Value(stoeykildenavn) =  "
    BOOL_OP = OR
    TEST_MODE = Automatic
    PASSED -> AttributeCreator_2
    FAILED -> Counter_2
AttributeCreator_2
    ATTR_LIST = stoeykildenavn,@Value(icao)
    -> Counter_2
Counter_2
    SCOPE = Global
    DOMAIN = counter
    START = 0
    CNT_ATTR = objid
    -> Tester_4
Tester_4
    TEST_DESCRIPTION = ""
    TEST_CLAUSE = TEST @Value(stoeysonekategori) IN G,R,S,U
    BOOL_OP = OR
    TEST_MODE = Automatic
    PASSED -> NullAttributeMapper
    FAILED -> AttributeRemover_2
AttributeRemover_2
    REMOVE_ATTRS = stoeysonekategori
    -> NullAttributeMapper
NullAttributeMapper
    NULL_TREATMENT = New Value
    OTHER_VALUE = 0
    ATTRLIST = maalemetode
    ATTRCHOICE = Selected Attributes
    NEW_VALUE = 99
    -> TimeStamper
TimeStamper
    TIME_ATTR = versjonid
    FMT = FME Date/Time (^Y^m^d^H^M^S)
    -> stoy_flyplass.stoey (writer POSTGIS_2)
stoy_flyplass.stoey (writer POSTGIS_2)
    attributes: objid serial,PRIKEY, objtype varchar(32), stoeysonekategori varchar(80), stoeykilde varchar(80), stoeykildeidentifikasjon varchar(80), stoeykildenavn varchar(80), stoeymetode varchar(80), beregnetaar varchar(80), lokalid varchar(20), navnerom varchar(80), versjonid varchar(80), datafangstdato timestamp, oppdateringsdato timestamp, maalemetode varchar(80), noeyaktighet int4, max_avvik int4, opphav varchar(80), kommune varchar(80), informasjon varchar(80)

Bookmark: Støy Skytebane
STOY_FELT_BANER_FLATE (reader FILEGDB_1)
    attributes: OBJECTID objectid, MALEMETODE smallint, STOYMETODE text(50), STOYKILDENAVN text(50), OBJTYPE text(32), STOYENHET text(50), STOYKILDE text(2), STOYSONEKATEGORI text(1), INDIKATOR text(50), STOYINTERVALL smallint, BEREGNETAAR text(10), KOMM text(4), OPPHAV text(20), STEDKVAL smallint, REFERANSE text(100), STOYKILDEIDENTIFIKASJON text(50), DATAFANGSTDATO date, SHAPE_Length double, SHAPE_Area double
    -> Deaggregator
Deaggregator
    GEOM_NAME_FIELD = _geometry_name
    CHILD_ID_ATTR = _hierarchy_child_id_list
    LIST_ATTR_MODE_LOOKUP = LEAN
    EXPLODE_INSTANCES = No
    COPY_ATTR = Every Node
    PART_NUMBER_FIELD = _part_number
    ID_SELECTION = ID and Parent ID
    ID_ATTR = _hierarchy_id
    PARENT_ID_ATTR = _hierarchy_parent_id
    MODE = Flatten One Level
    SPLIT_COMPOSITES = No
    DEAGGREGATED -> Reprojector_3
    DEAGGREGATED -> TopologyBuilder_2 [input 3]
Reprojector_3
    DEST = EPSG:4258
    INTERPOLATION_TYPE_NAME = Nearest Neighbor
    RASTER_CELL_SIZE = Preserve Cells
    SOURCE = Read from feature
    REPROJECTED -> BulkAttributeRenamer_4
BulkAttributeRenamer_4
    PATTERN_ACTION_DISP = Change Case
    ATTRCHOICE = All Attributes
    CASE_CHANGE_TYPE = lowercase
    -> AttributeRenamer_2
AttributeRenamer_2
    ATTR_LIST = stoysonekategori,stoeysonekategori,,stoymetode,stoeymetode,,stoykildenavn,stoeykildenavn,,stoykilde,stoeykilde,,stoykildeidentifikasjon,stoeykildeidentifikasjon,,malemetode,maalemetode,
    -> AttributeCreator_3
AttributeCreator_3
    ATTR_LIST = lokalid,uuid_generate_v4(),navnerom,NO_KARTVERKET_STOY,objtype,Støy
    -> NullAttributeMapper_2
NullAttributeMapper_2
    NULL_TREATMENT = New Value
    OTHER_VALUE = 0
    ATTRLIST = maalemetode
    ATTRCHOICE = Selected Attributes
    NEW_VALUE = 99
    -> TimeStamper_2
TimeStamper_2
    TIME_ATTR = versjonid
    FMT = FME Date/Time (^Y^m^d^H^M^S)
    -> stoy_skytebane.stoey (writer POSTGIS_1)
stoy_skytebane.stoey (writer POSTGIS_1)
    attributes: objid serial,PRIKEY, objtype varchar(32), stoeysonekategori varchar(80), stoeykilde varchar(80), stoeykildeidentifikasjon varchar(80), stoeykildenavn varchar(80), stoeymetode varchar(80), beregnetaar varchar(80), lokalid uuid,PRIKEY, navnerom varchar(80), versjonid varchar(80), datafangstdato timestamp, oppdateringsdato timestamp, maalemetode varchar(80), noeyaktighet int4, max_avvik int4, opphav varchar(80), kommune varchar(80), informasjon varchar(80)
TopologyBuilder_2
    MAX = 0
    ALL_EDGES = Yes
    ALLOW_CYCLES = No
    OVERLAPPING_MODE = No
    CLEAN_DATA = No
    PROP_ATTRS = No
    LINE -> Reprojector_4
Reprojector_4
    DEST = EPSG:4258
    INTERPOLATION_TYPE_NAME = Nearest Neighbor
    RASTER_CELL_SIZE = Preserve Cells
    SOURCE = Read from feature
    REPROJECTED -> Counter_3
Counter_3
    SCOPE = Global
    DOMAIN = counter
    START = 0
    CNT_ATTR = objid
    -> AttributeCreator_5
AttributeCreator_5
    ATTR_LIST = objtype,Støygrense
    -> stoy_skytebane.stoeygrense (writer POSTGIS_1)
stoy_skytebane.stoeygrense (writer POSTGIS_1)
    attributes: objid serial,PRIKEY, objtype varchar(32)
