FME workspace Skytebanestoydata_postgis2sosi.fmw
# Copyright: (c) xgrimor 2015
# Licence: <your licence>
Shutdown Python:
      # -*- coding: utf-8 -*-
      #-------------------------------------------------------------------------------
      # Name:        zipfiles.py
      # Purpose:     Pakker filer i output folderen
      #
      # Author:      xsunknu
      #
      # Created:     18.09.2015
      # Copyright:   (c) xsunknu 2015
      # Licence:     <your licence>
      #-------------------------------------------------------------------------------

      import sys, os, zipfile, fme

      def zip(sosifile, zfile):
          from os.path import basename

          # Lager korresponderende zip-fil av SOSI-fil
          if os.path.isfile(zfile):
              os.remove(zfile)

          zf = zipfile.ZipFile(zfile, "w", zipfile.ZIP_DEFLATED)

          # Ønsker ikke full sti inn i ZIP-filen
          arcname = basename(sosifile)

          # ZIP-formatet støtter ikke non-ascii tegn
          # Erstatter AØÅæøå med ascii-tegn
          arcname = arcname.replace('\xc6', 'E')
          arcname = arcname.replace('\xd8', 'O')
          arcname = arcname.replace('\xc5', 'A')
          arcname = arcname.replace('\xe6', 'e')
          arcname = arcname.replace('\xf8', 'o')
          arcname = arcname.replace('\xe5', 'a')

          zf.write(sosifile, arcname)
          zf.close()
          os.remove(sosifile)

          return

      def main():

          # Kjøres ikke på FME Server, da FME Server selv sørger for pakkingen
          if not 'FME_SERVER_DEST_DIR' in fme.macroValues:
              if 'FANOUT_FOLDER' in fme.macroValues:
                  path = fme.macroValues['FANOUT_FOLDER']
                  for dirpath, dnames, fnames in os.walk(path):
                      for f in fnames:
                          if f.endswith(".sos"):
                              # Scanner gjennom alle SOSI-filer
                              sosifile = os.path.join(path, f)
                              zfile = os.path.splitext(sosifile)[0] + '.zip'
                              if os.path.isfile(zfile):

                                  # Korresponderende ZIP-fil finnes, sjekker timestamps
                                  sositstamp = os.stat(sosifile).st_mtime
                                  ziptstamp = os.stat(zfile).st_mtime

                                  if sositstamp > ziptstamp:
                                      # SOSI-fil er nyere enn ZIP-fila, ZIP-fila oppdateres
                                      # SOSI-fila slettes
                                      try:
                                          zip(sosifile, zfile)
                                      except:
                                          print 'Kunne ikke pakke: ' + sosifile
                                  else:
                                      # SOSI-fila er eldre enn ZIP-fila
                                      # SOSI-fila slettes
                                      try:
                                          os.remove(sosifile)
                                      except:
                                          print 'Kunne ikke slette: ' + sosifile
                              else:
                                  # ZIP-fila eksisterer ikke og lages
                                  # SOSI-fila slettes
                                  try:
                                      zip(sosifile, zfile)
                                  except:
                                      print 'Kunne ikke pakke: ' + sosifile


      if __name__ == '__main__':
          main()

Parameters:
- KNR =   # Kommune(r)
- FNR =   # Fylke(r)
- CLIPPERCOORDS =   # Clipper coordinates
- CLIPPER_EPSG_CODE =   # Clipper coordinate system
- CLIPPER_FILE =   # "" Clipper file (any format)
- OUTPUT_EPSG_CODE = 25833   # Destination coordinate system
- FANOUT =   # Fanout områder
- CONFIG_FILE:   # Python Script
      #-------------------------------------------------------------------------------
      # Name:        GetConfigFile
      # Purpose:
      #
      # Author:      xsunknu
      #
      # Created:     21.08.2015
      # Copyright:   (c) xsunknu 2015
      # Licence:     <your licence>
      #-------------------------------------------------------------------------------
      
      import os, fme
      
      fmwdir = fme.macroValues['FME_MF_DIR']
      fmwfile = fme.macroValues['FME_MF_NAME']
      
      fmwfile = os.path.join(fmwdir, fmwfile)
      configfile = os.path.splitext(fmwfile)[0] + '_config.xml'
      
      return configfile
- CLIPPERCOORDSYS:   # Python Script
      #-------------------------------------------------------------------------------
      # Name:        SetCoordinateSystem
      # Purpose:
      #
      # Author:      xsunknu
      #
      # Created:     21.08.2015
      # Copyright:   (c) xsunknu 2015
      # Licence:     <your licence>
      #-------------------------------------------------------------------------------
      
      import os, fme
      
      EPSGvalue = fme.macroValues['CLIPPER_EPSG_CODE']
      EPSGcode  = 'EPSG:' + EPSGvalue
      
      return EPSGcode
- DESTCOORDSYS:   # Python Script
      #-------------------------------------------------------------------------------
      # Name:        SetCoordinateSystem
      # Purpose:
      #
      # Author:      xsunknu
      #
      # Created:     21.08.2015
      # Copyright:   (c) xsunknu 2015
      # Licence:     <your licence>
      #-------------------------------------------------------------------------------
      
      import os, fme
      
      EPSGvalue = fme.macroValues['OUTPUT_EPSG_CODE']
      EPSGcode  = 'EPSG:' + EPSGvalue
      
      return EPSGcode
- SPATIAL_FILTER:   # Python Script
      #-------------------------------------------------------------------------------
      # Name:        SetSpatialFilter
      # Purpose:
      #
      # Author:      xsunknu
      #
      # Created:     21.08.2015
      # Copyright:   (c) xsunknu 2015
      # Licence:     <your licence>
      #-------------------------------------------------------------------------------
      
      import fme
      
      spatialfilter = 'Intersects'
      
      knr = fme.macroValues['KNR']
      fnr = fme.macroValues['FNR']
      coords = fme.macroValues['CLIPPERCOORDS']
      file = fme.macroValues['CLIPPER_FILE']
      
      if knr == '' and fnr == '' and coords == '' and file == '':
          spatialfilter = '<No Spatial Filter>'
      
      return spatialfilter
- FIXEDCLIPPERCOORDS:   # Python Script
      #-------------------------------------------------------------------------------
      # Name:        FixClipperCoords
      # Purpose:
      #
      # Author:      xsunknu
      #
      # Created:     21.08.2015
      # Copyright:   (c) xsunknu 2015
      # Licence:     <your licence>
      #-------------------------------------------------------------------------------
      
      import fme
      clippercoords = fme.macroValues['CLIPPERCOORDS']
      
      if clippercoords == '':
          clippercoords = '1 1'
      
      return clippercoords
- HOVEDTEMA = Forurensning   # Hovedtema
- UNDERTEMA = StoySkytebane   # Undertema
- PG_DB:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgdb').text
      
      return value
- PG_HOST:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pghost').text
      
      return value
- PG_PORT:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgport').text
      
      return value
- PG_USER:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pguser').text
      
      return value
- PG_PWD:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgpwd').text
      
      return value
- MAPPINGFILE:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme, os
      from xml.etree import ElementTree as ET
      
      #Read XML config file
      configtree = ET.parse(fme.macroValues['CONFIG_FILE'])
      configdoc = configtree.getroot()
      
      value = os.path.join(fme.macroValues['FME_MF_DIR'], configdoc.find('mappingfile').text)
      
      return value
- LOG_FILE:   # Python Script
      #-------------------------------------------------------------------------------
      # Name:        GetConfigFile
      # Purpose:
      #
      # Author:      xsunknu
      #
      # Created:     21.08.2015
      # Copyright:   (c) xsunknu 2015
      # Licence:     <your licence>
      #-------------------------------------------------------------------------------
      
      import os, uuid, fme
      
      fmwdir = fme.macroValues['FME_MF_DIR']
      fmwfile = fme.macroValues['FME_MF_NAME']
      
      logdir = os.path.join(fmwdir, 'log')
      if not os.path.isdir(logdir):
          os.mkdir(logdir)
      
      logfile = os.path.splitext(fmwfile)[0] + '_' + str(uuid.uuid1()).replace('-','') + '.log'
      logfile = os.path.join(logdir, logfile)
      
      return logfile
- FANOUT_FOLDER:   # Python Script
      #-------------------------------------------------------------------------------
      # Name:        GetConfigFile
      # Purpose:
      #
      # Author:      xsunknu
      #
      # Created:     21.08.2015
      # Copyright:   (c) xsunknu 2015
      # Licence:     <your licence>
      #-------------------------------------------------------------------------------
      
      import os, fme
      from xml.etree import ElementTree as ET
      
      if 'FME_SERVER_DEST_DIR' in fme.macroValues:
          value = fme.macroValues['FME_SERVER_DEST_DIR']
      else:
          #Read XML config file
          configtree = ET.parse(fme.macroValues['CONFIG_FILE'])
          configdoc = configtree.getroot()
          value = configdoc.find('destdir').text
      
      return value
- DestDataset_SOSI = C:\Users\xmaland\Documents\GitHub\geonorge\Støy\flystoydata_postgis2sosi\skytebanestoy.sos   # Destination SOSI File

Readers:
- POSTGIS_1: POSTGIS from $(PG_DB)

Writers:
- SOSI_1: SOSI to $(DestDataset_SOSI)

CreateClipper
    CLIPPERCOORDSYS = $(CLIPPERCOORDSYS)
    CLIPPERCOORDS = $(FIXEDCLIPPERCOORDS)
    DESTCOORDSYS = $(DESTCOORDSYS)
    -> Clipper [input 1]
    -> FeatureReader_3
stoy_skytebane.stoey (writer SOSI_1)
    attributes: OBJTYPE SOSI_varchar(32), stoeysonekategori SOSI_varchar(80), stoeykilde SOSI_varchar(80), stoeykildeidentifikasjon SOSI_varchar(80), stoeykildenavn SOSI_varchar(80), stoeymetode SOSI_varchar(80), beregnetaar SOSI_varchar(80), lokalid SOSI_buffer, navnerom SOSI_varchar(80), versjonid SOSI_varchar(80), datafangstdato SOSI_datetime, oppdateringsdato SOSI_datetime, maalemetode SOSI_varchar(80), noeyaktighet SOSI_int32, max_avvik SOSI_int32, opphav SOSI_varchar(80), kommune SOSI_varchar(255), informasjon SOSI_varchar(80)
stoy_skytebane.stoeygrense (writer SOSI_1)
    attributes: OBJTYPE SOSI_varchar(32)

Bookmark: Fylke and/or kommune clippers
admingrense.fylkeflate (reader POSTGIS_1)
    attributes: fylkeid int4, navn varchar(80)
    -> Tester
    -> AttributeCreator_8
AttributeCreator_8
    ATTR_LIST = _clippercoords,$(CLIPPERCOORDS),_clipper_file,$(CLIPPER_FILE),_fnr,$(FNR),_knr,$(KNR)
    -> Tester_4
Tester_4
    BOOL_OP = AND
    TEST_MODE = Automatic
    TEST_CLAUSE:
      TEST _clipper_file ATTRIBUTE_IS_EMPTY ""
      TEST _clippercoords ATTRIBUTE_IS_EMPTY ""
      TEST _fnr ATTRIBUTE_IS_EMPTY ""
      TEST _knr ATTRIBUTE_IS_EMPTY ""
    TEST_DESCRIPTION = ""
    PASSED -> Reprojector_2
Tester
    BOOL_OP = OR
    TEST_MODE = Automatic
    TEST_CLAUSE = TEST @Value(fylkeid) IN $(FNR)
    TEST_DESCRIPTION = ""
    PASSED -> Reprojector_2
admingrense.kommuneflate (reader POSTGIS_1)
    attributes: kommuneid int4, navn varchar(80)
    -> Tester_2
Tester_2
    BOOL_OP = OR
    TEST_MODE = Automatic
    TEST_CLAUSE = TEST @Value(kommuneid) IN $(KNR)
    TEST_DESCRIPTION = ""
    PASSED -> Reprojector_2
Note: Sender inn hele landet som initiator / dersom alle klippeparametrene er / blanke
Reprojector_2
    DEST = EPSG:4258
    RASTER_CELL_SIZE = Preserve Cells
    INTERPOLATION_TYPE_NAME = Nearest Neighbor
    SOURCE = Read from feature
    REPROJECTED -> Clipper [input 1]
    REPROJECTED -> Dissolver

Bookmark: Clipper file (any format)
Creator
    NUM = 1
    GEOMTYPE = Geometry Object
    CREATED -> FeatureReader
FeatureReader
    COMBINE_GEOM = Use Result
    ATTRIBUTES = NewFeatureType,
    INTERACT = $(SPATIAL_FILTER)
    FORMAT = GENERIC
    ATTR_ACCUM_MODE = Only Use Result
    GENERIC_REAL_FORMAT = GUESS_FROM_EXTENSION
    OUTPUT_FEATURES_DISPLAY = Based on Connections
    FEATURETYPES_RADIO = FEATURETYPES
    DATASET = $(CLIPPER_FILE)
    <OTHER> -> Reprojector_3
Reprojector_3
    DEST = EPSG:4258
    RASTER_CELL_SIZE = Preserve Cells
    INTERPOLATION_TYPE_NAME = Nearest Neighbor
    SOURCE = Read from feature
    REPROJECTED -> Clipper [input 1]
    REPROJECTED -> Dissolver

Bookmark: Leser features
Dissolver
    NO_OVRLP = No
    ACCUM_INPUT_ATTRS = No
    AREA -> FeatureReader_3
FeatureReader_3
    POSTGIS_HOST = $(PG_HOST)
    POSTGIS_USE_TRUE_POSTGIS_TYPES = yes
    DATASET = $(PG_DB)
    COMBINE_GEOM = Use Result
    POSTGIS_CLIP_TO_ENVELOPE = NO
    FEATURETYPES = stoy_skytebane.stoey stoy_skytebane.stoeygrense
    INTERACT = Intersects
    OUTPUT_FEATURES_DISPLAY = Based on Connections
    POSTGIS_USER_NAME = $(PG_USER)
    POSTGIS_USE_SEARCH_ENVELOPE = NO
    POSTGIS_DISABLE_COLLECTION_SPLITTING = yes
    POSTGIS_QUERY_FEATURE_TYPES_FOR_MERGE_FILTERS = Yes
    POSTGIS_PASSWORD = $(PG_PWD)
    POSTGIS_PORT = $(PG_PORT)
    ATTR_ACCUM_MODE = Only Use Result
    FEATURETYPES_RADIO = FEATURETYPES
    POSTGIS_SCHEMALIST = stoy_skytebane
    FORMAT = POSTGIS
    ATTRIBUTES = stoy_skytebane.stoey,"objid,objtype,stoeysonekategori,stoeykilde,stoeykildeidentifikasjon,stoeykildenavn,stoeymetode,beregnetaar,lokalid,navnerom,versjonid,datafangstdato,oppdateringsdato,maalemetode,noeyaktighet,max_avvik,opphav,kommune,informasjon",stoy_skytebane.stoeygrense,"objid,objtype"
    stoy_skytebane.stoey -> AttributeCreator_12
    stoy_skytebane.stoeygrense -> AttributeCreator_12
AttributeCreator_12
    ATTR_LIST = _clippercoords,$(CLIPPERCOORDS),_clipper_file,$(CLIPPER_FILE),_fnr,$(FNR),_knr,$(KNR)
    -> TestFilter
TestFilter
    TEST_LIST:
      BOOL_OP,AND,COMPOSITE_TEST,<Unused>,TEST_CLAUSE,"TEST _clipper_file ATTRIBUTE_IS_EMPTY """"
      TEST _clippercoords ATTRIBUTE_IS_EMPTY """"
      TEST _fnr ATTRIBUTE_IS_EMPTY """"
      TEST _knr ATTRIBUTE_IS_EMPTY """"",Landsdekkende,BOOL_OP,AND,COMPOSITE_TEST,<Unused>,TEST_CLAUSE,"TEST _clipper_file ATTRIBUTE_IS_EMPTY """"
      TEST _clippercoords ATTRIBUTE_IS_EMPTY """"
      TEST _fnr NOT_ATTRIBUTE_IS_EMPTY """"
      TEST _knr ATTRIBUTE_IS_EMPTY """"",Fylkesvis,BOOL_OP,AND,COMPOSITE_TEST,<Unused>,TEST_CLAUSE,"TEST _clipper_file ATTRIBUTE_IS_EMPTY """"
      TEST _clippercoords ATTRIBUTE_IS_EMPTY """"
      TEST _fnr ATTRIBUTE_IS_EMPTY """"
      TEST _knr NOT_ATTRIBUTE_IS_EMPTY """"",Kommunevis
    DEFAULT_VALUE = <UNFILTERED>
    Fylkesvis -> Clipper [input 2]
    Kommunevis -> Clipper [input 2]
    <UNFILTERED> -> Clipper [input 2]
    Landsdekkende -> SosiFilenameSetter

Bookmark: Klipper
Clipper
    ATTR_CONFLICT_RES = Use Clippee
    PRESERVE_CLIPPEE_EXTENTS = No
    CREATE_AGGREGATES = No
    CLIP_TYPE = Multiple Clippers
    BOUNDARY_CASES = Treat as Inside
    ATTR_ACCUM_MODE = Merge Clipper
    CLIPPED_ATTR = _clipped
    INSIDE -> SosiFilenameSetter

Bookmark: Tagger og reprojiserer
SosiFilenameSetter
    KOMMUNEID = @Value(kommuneid)
    HOVEDTEMA = $(HOVEDTEMA)
    FANOUT = $(FANOUT)
    OPPDATERINGSDATO = @Value(oppdateringsdato)
    PG_HOST:
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------

      import fme
      from xml.etree import ElementTree as ET

      #Read XML config file
      configtree = ET.parse(fme.macroValues['CONFIG_FILE'])
      configdoc = configtree.getroot()
      value = configdoc.find('pghost').text

      return value
    OBJTYPE = @Value(objtype)
    NAVNEROM = @Value(navnerom)
    OUTPUT_EPSG_CODE = $(OUTPUT_EPSG_CODE)
    FYLKEID = @Value(fylkeid)
    PG_USER:
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------

      import fme
      from xml.etree import ElementTree as ET

      #Read XML config file
      configtree = ET.parse(fme.macroValues['CONFIG_FILE'])
      configdoc = configtree.getroot()
      value = configdoc.find('pguser').text

      return value
    NAVN = @Value(navn)
    UNDERTEMA = $(UNDERTEMA)
    INFORMASJON = @Value(informasjon)
    PG_PWD:
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------

      import fme
      from xml.etree import ElementTree as ET

      #Read XML config file
      configtree = ET.parse(fme.macroValues['CONFIG_FILE'])
      configdoc = configtree.getroot()
      value = configdoc.find('pgpwd').text

      return value
    VERSJONID = @Value(versjonid)
    PG_PORT:
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------

      import fme
      from xml.etree import ElementTree as ET

      #Read XML config file
      configtree = ET.parse(fme.macroValues['CONFIG_FILE'])
      configdoc = configtree.getroot()
      value = configdoc.find('pgport').text

      return value
    OBJID = @Value(objid)
    LOKALID = @Value(lokalid)
    PG_DB:
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------

      import fme
      from xml.etree import ElementTree as ET

      #Read XML config file
      configtree = ET.parse(fme.macroValues['CONFIG_FILE'])
      configdoc = configtree.getroot()
      value = configdoc.find('pgdb').text

      return value
    OPPHAV = @Value(opphav)
    -> Reprojector
Reprojector
    DEST = $(DESTCOORDSYS)
    RASTER_CELL_SIZE = Preserve Cells
    INTERPOLATION_TYPE_NAME = Nearest Neighbor
    SOURCE = Read from feature
    REPROJECTED -> AttributeRenamer
AttributeRenamer
    ATTR_LIST = objtype,OBJTYPE,
    -> FeatureTypeFilter
FeatureTypeFilter
    ATTRIBUTES = <BLANK>,<UNFILTERED>,stoy_skytebane.stoey,stoy_skytebane.stoeygrense
    stoy_skytebane.stoey -> stoy_skytebane.stoey (writer SOSI_1)
    stoy_skytebane.stoeygrense -> stoy_skytebane.stoeygrense (writer SOSI_1)

FME custom transformer CreateClipper

Parameters:
- CLIPPERCOORDS = 253577 6650999 253577 6651246 253763 6651246 253763 6650999 253577 6650999   # Clipper Coordinate List
- CLIPPERCOORDSYS = EPSG:25833   # Clipper Coordinate System
- DESTCOORDSYS = "ESRIWKT|ETRS_1989_UTM_Zone_35N|PROJCS["ETRS_1989_UTM_Zone_35N",GEOGCS["GCS_ETRS_1989",DATUM["D_ETRS_1989",SPHEROID["GRS_1980",6378137.0,298.257222101]],PRIMEM["Greenwich",0.0],UNIT["Degree",0.0174532925199433]],PROJECTION["Transverse_Mercator"],PARAMETER["False_Easting",500000.0],PARAMETER["False_Northing",0.0],PARAMETER["Central_Meridian",27.0],PARAMETER["Scale_Factor",0.9996],PARAMETER["Latitude_Of_Origin",0.0],UNIT["Meter",1.0]]"   # Destination Coordinate System

Note: Creating geometry from / the Clipper coords
Creator
    NUM = 1
    GEOMTYPE = 2D Coordinate List
    COORDSYS = $(CLIPPERCOORDSYS)
    COORDS = $(CLIPPERCOORDS)
    CREATED -> BoundingBoxAccumulator
Note: Calculating the bounding / box (envelope) from the geometry
BoundingBoxAccumulator
    TOPFER_INDEX = No
    BOUNDING_BOX -> SpatialFilter [input 1]
    ORIGINAL -> SpatialFilter [input 2]
Note: If the geometry is equal to its / own bounding box - it is a rectangle!
SpatialFilter
    BASE_TYPE = Single Base
    PREDATTR = _predicate
    PASS_CRITERIA = Pass Against One Base
    MERGE_ATTRS = No
    CURVE_BOUNDARY_RULE_PARAM = Default Rule
    PREDICATES = EQUALS
    USE_BOUNDING_BOX = No
    PASSED -> Reprojector
    FAILED -> Reprojector_2
Note: If rectangle, reproject the / geometry to the destination / coordinate system
Reprojector
    DEST = $(DESTCOORDSYS)
    RASTER_CELL_SIZE = Preserve Cells
    STROKE_ARCS = Yes
    INTERPOLATION_TYPE_NAME = Nearest Neighbor
    SOURCE = Read from feature
    REPROJECTED -> BoundingBoxAccumulator_2
Note: Then calculate the bounding / box from the projected geoemtry
BoundingBoxAccumulator_2
    TOPFER_INDEX = No
    BOUNDING_BOX -> Reprojector_3
Note: Reproject the geometry back to / the DB coordsys (LL/EUREF89)
Reprojector_3
    DEST = EPSG:4258
    RASTER_CELL_SIZE = Preserve Cells
    STROKE_ARCS = Yes
    INTERPOLATION_TYPE_NAME = Nearest Neighbor
    SOURCE = Read from feature
    REPROJECTED -> GeometryFilter
Note: Reproject clipper to / the DB coordsys (LL/EUREF89)
Reprojector_2
    DEST = EPSG:4258
    RASTER_CELL_SIZE = Preserve Cells
    STROKE_ARCS = Yes
    INTERPOLATION_TYPE_NAME = Nearest Neighbor
    SOURCE = Read from feature
    REPROJECTED -> GeometryFilter
Note: Getting rid of dummies
GeometryFilter
    BREAK_AGG = No
    GEOM_PORT_NAMES = Area
    AREA -> Output (output)
Output (output)

FME custom transformer SosiFilenameSetter

Parameters:
- OUTPUT_EPSG_CODE = 25832   # Destination coordinate system
- FANOUT = Kommuner   # Fanout områder
- UNDERTEMA =   # Undertema
- HOVEDTEMA =   # Hovedtema
- FYLKEID = @Value(fylkeid)   # fylkeid
- INFORMASJON = @Value(informasjon)   # informasjon
- KOMMUNEID = @Value(kommuneid)   # kommuneid
- LOKALID = @Value(lokalid)   # lokalid
- NAVN = @Value(navn)   # navn
- NAVNEROM = @Value(navnerom)   # navnerom
- OBJID = @Value(objid)   # objid
- OBJTYPE = @Value(objtype)   # objtype
- OPPDATERINGSDATO = @Value(oppdateringsdato)   # oppdateringsdato
- OPPHAV = @Value(opphav)   # opphav
- VERSJONID = @Value(versjonid)   # versjonid
- PG_DB:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgdb').text
      
      return value
- PG_HOST:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pghost').text
      
      return value
- PG_PORT:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgport').text
      
      return value
- PG_PWD:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgpwd').text
      
      return value
- PG_USER:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pguser').text
      
      return value

Input (input)
    -> ParameterFetcher
ParameterFetcher
    ATTR_LIST = _output_epsg_code {$(OUTPUT_EPSG_CODE)} _fanout {$(FANOUT)}
    -> AttributeValueMapper
Note: Fikser kjente feil i kommunenummer
AttributeValueMapper
    VAL_ATTR = kommuneid
    DEFAULT_VALUE = @Value(kommuneid)
    LUT = 1901,1903
    DIRECTION = Forward (Source To Destination)
    SRC = kommuneid
    -> TestFilter_2
TestFilter_2
    TEST_LIST = BOOL_OP,OR,COMPOSITE_TEST,<Unused>,TEST_CLAUSE,"TEST $(FANOUT) = Kommuner",Kommuner,BOOL_OP,OR,COMPOSITE_TEST,<Unused>,TEST_CLAUSE,"TEST $(FANOUT) = Fylker",Fylker
    DEFAULT_VALUE = Ufiltrert
    Kommuner -> Joiner
    Fylker -> Joiner_2
    Ufiltrert -> AttributeCreator_13
Joiner
    POSTGIS_HOST = $(PG_HOST)
    JOIN_KEYS = kommuneid kommuneid
    CACHE_SIZE = 5000
    POSTGIS_DISABLE_COLLECTION_SPLITTING = yes
    FORMAT = POSTGIS
    PREFETCH_EXHAUSTIVE = Yes
    TABLE = admingrense.kommuner
    POSTGIS_PASSWORD = $(PG_PWD)
    POSTGIS_PORT = $(PG_PORT)
    MATCH_RULE_DISPLAY = Must Match Exactly One (1:1)
    POSTGIS_USER_NAME = $(PG_USER)
    DATASET = $(PG_DB)
    POSTGIS_USE_TRUE_POSTGIS_TYPES = yes
    POSTGIS_QUERY_FEATURE_TYPES_FOR_MERGE_FILTERS = Yes
    ADDED_FIELDS = navn
    JOINED -> StringReplacer_2
Joiner_2
    POSTGIS_HOST = $(PG_HOST)
    JOIN_KEYS = fylkeid fylkeid
    CACHE_SIZE = 5000
    POSTGIS_DISABLE_COLLECTION_SPLITTING = yes
    FORMAT = POSTGIS
    PREFETCH_EXHAUSTIVE = Yes
    TABLE = admingrense.fylkeflate
    POSTGIS_PASSWORD = $(PG_PWD)
    POSTGIS_PORT = $(PG_PORT)
    MATCH_RULE_DISPLAY = Must Match Exactly One (1:1)
    POSTGIS_USER_NAME = $(PG_USER)
    DATASET = $(PG_DB)
    POSTGIS_USE_TRUE_POSTGIS_TYPES = yes
    POSTGIS_QUERY_FEATURE_TYPES_FOR_MERGE_FILTERS = Yes
    ADDED_FIELDS = navn
    JOINED -> StringReplacer_2
AttributeCreator_13
    ATTR_LIST = sosifile,"FME_CONDITIONAL:DEFAULT_VALUE'$(HOVEDTEMA)_$(OUTPUT_EPSG_CODE)_$(UNDERTEMA)_SOSI'BOOL_OP;OR;COMPOSITE_TEST;<Unused>;TEST $(FANOUT) LIKE Kommuner'$(HOVEDTEMA)_@PadLeft(@Value(kommuneid),4,0)_@Value(navn)_$(OUTPUT_EPSG_CODE)_$(UNDERTEMA)_SOSI'BOOL_OP;OR;COMPOSITE_TEST;<Unused>;TEST $(FANOUT) LIKE Fylker'$(HOVEDTEMA)_@PadLeft(@Value(fylkeid),2,0)_@Value(navn)_$(OUTPUT_EPSG_CODE)_$(UNDERTEMA)_SOSI'BOOL_OP;OR;COMPOSITE_TEST;<Unused>;TEST $(FANOUT) LIKE Norge'$(HOVEDTEMA)_0000_Norge_$(OUTPUT_EPSG_CODE)_$(UNDERTEMA)_SOSI'FME_NUM_CONDITIONS4___"
    -> Output (output)
Output (output)

Bookmark: Substituerer ÆØÅ og mellomrom
StringReplacer_2
    FIND_TEXT = " "
    REPLACE_TEXT = _
    NO_MATCH = _FME_NO_OP_
    SRC_ATTRS = navn
    CASE = no
    REGEXP = no
    -> StringReplacer_3
StringReplacer_3
    FIND_TEXT = Æ
    REPLACE_TEXT = E
    NO_MATCH = _FME_NO_OP_
    SRC_ATTRS = navn
    CASE = yes
    REGEXP = no
    -> StringReplacer_4
StringReplacer_4
    FIND_TEXT = Ø
    REPLACE_TEXT = O
    NO_MATCH = _FME_NO_OP_
    SRC_ATTRS = navn
    CASE = yes
    REGEXP = no
    -> StringReplacer_5
StringReplacer_5
    FIND_TEXT = Å
    REPLACE_TEXT = A
    NO_MATCH = _FME_NO_OP_
    SRC_ATTRS = navn
    CASE = yes
    REGEXP = no
    -> StringReplacer_6
StringReplacer_6
    FIND_TEXT = æ
    REPLACE_TEXT = e
    NO_MATCH = _FME_NO_OP_
    SRC_ATTRS = navn
    CASE = yes
    REGEXP = no
    -> StringReplacer_7
StringReplacer_7
    FIND_TEXT = ø
    REPLACE_TEXT = o
    NO_MATCH = _FME_NO_OP_
    SRC_ATTRS = navn
    CASE = yes
    REGEXP = no
    -> StringReplacer_8
StringReplacer_8
    FIND_TEXT = å
    REPLACE_TEXT = a
    NO_MATCH = _FME_NO_OP_
    SRC_ATTRS = navn
    CASE = yes
    REGEXP = no
    -> AttributeCreator_13
