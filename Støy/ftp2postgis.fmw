FME workspace ftp2postgis.fmw

Parameters:
- URL_FORSVARETSTOY = ftp://ftp.statkart.no/Forsvaret_Støy/Stoy_skytefelt_og_baner_FB.gdb.zip   # FTP-link til zip-fil med støydata for Forsvaret
- DEST_FORSVARETSTOY = .\Forsvaret_Stoy.zip   # Målfil for støydata fra forsvaret
- URL_AVINORSTOY = ftp://ftp.statkart.no/Avinor/Støy/Stoysoner.gdb/**   # Ftp-link til zip-fil med støydata fra Avinor
- DEST_AVINORSTOY = .\Avinor_stoy.gdb   # Målfil for støydata fra Avinor

Creator [off]
    NUM = 1
    GEOMTYPE = Geometry Object
    CREATED -> FTPCaller_3 [off]
    CREATED -> FTPCaller_2 [off]
FTPCaller_2 [off]
    VERIFY_SSL_CERTIFICATES = Yes
    MODE = Binary
    REMOTE_URL = $(URL_FORSVARETSTOY)
    ERROR_ATTR = _error
    FTP_USERNAME = geonorge
    TRANSFER_TYPE = Download to a File
    FTP_PASSWORD =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
    DOWNLOAD_FILE = $(DEST_FORSVARETSTOY)
    -> FeatureReader [off]
FeatureReader [off]
    FORMAT = FILEGDB
    INTERACT = <No Spatial Filter>
    FEATURETYPES_RADIO = FEATURETYPES
    COMBINE_GEOM = Use Result
    DATASET = $(DEST_FORSVARETSTOY)
    OUTPUT_FEATURES_DISPLAY = Based on Connections
    FILEGDB_CLIP_TO_ENVELOPE = NO
    ATTRIBUTES = STOY_FELT_BANER_FLATE,"OBJECTID,MALEMETODE,STOYMETODE,STOYKILDENAVN,OBJTYPE,STOYENHET,STOYKILDE,STOYSONEKATEGORI,INDIKATOR,STOYINTERVALL,BEREGNETAAR,KOMM,OPPHAV,STEDKVAL,REFERANSE,STOYKILDEIDENTIFIKASJON,DATAFANGSTDATO,SHAPE_Length,SHAPE_Area",STOY_FELT_BANER_LINJE,"OBJECTID,OBJTYPE,STOYSONEKATEGORI,STOYKILDE,STOYNIVA,STOYINTERVALL,STOYENHET,STOYKILDENAVN,STOYMETODE,BEREGNETAAR,MALEMETODE,NOYAKTIGHET,SYNBARHET,MAX_AVVIK,REFERANSE,SHAPE_Length",STOY_FLYPLASSER_FLATE_FRA_AVINOR_2014,"OBJECTID,PERIMETER,OPPR,X,Y,KOORDH,ICAO,LHSTOY,ENDRETAV,LUKKET,STOYSONEKATEGORI,FTEMA,MALEMETODE,NOYAKTIGHE,SYNBARHET,H_MALEMETODE,H_NOYAKTIGHET,MAX_AVVIK,OBJTYPE,STOYKILDENAVN,PRODUKT,VERSJON,DATFGSTDATO,STOEYKILDE,DATO,SHAPE_Length,SHAPE_Area",STOY_FLYPLASSER_LINJE_FRA_AVINOR_2014,"OBJECTID,LENGTH,OPPR,KOORDH,ICAO,ENDRETAV,PERIMETER,AVINORKODE,LUKKET,MALEMETODE,NOYAKTIGHE,SYNBARHET,H_MALEMETODE,H_NOYAKTIGHET,MAX_AVVIK,HOEYDE,AREAL,OBJTYPE,LTEMA,PRODUKT,VERSJON,DATFGSTDATDATO,DATO,STOYSONEKATEGORI,SHAPE_Length"
    FEATURETYPES = STOY_FELT_BANER_FLATE STOY_FELT_BANER_LINJE STOY_FLYPLASSER_FLATE_FRA_AVINOR_2014 STOY_FLYPLASSER_LINJE_FRA_AVINOR_2014
    ATTR_ACCUM_MODE = Only Use Result
    FILEGDB_USE_SEARCH_ENVELOPE = NO
    FILEGDB_QUERY_FEATURE_TYPES_FOR_MERGE_FILTERS = Yes
FTPCaller_3 [off]
    VERIFY_SSL_CERTIFICATES = Yes
    MODE = Binary
    REMOTE_URL = $(URL_AVINORSTOY)/**/*
    ERROR_ATTR = _error
    FTP_USERNAME = geonorge
    TRANSFER_TYPE = Download to a File
    FTP_PASSWORD =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
    DOWNLOAD_FILE = $(DEST_AVINORSTOY)/**/*
    -> FeatureReader_2 [off]
FeatureReader_2 [off]
    FORMAT = FILEGDB
    INTERACT = <No Spatial Filter>
    FEATURETYPES_RADIO = FEATURETYPES
    COMBINE_GEOM = Use Result
    DATASET = ftp://ftp.statkart.no/Avinor/Støy/Stoysoner.gdb
    OUTPUT_FEATURES_DISPLAY = Based on Connections
    FILEGDB_CLIP_TO_ENVELOPE = NO
    FEATURETYPES = STOY_FELT_BANER_FLATE STOY_FELT_BANER_LINJE STOY_FLYPLASSER_FLATE_FRA_AVINOR_2014 STOY_FLYPLASSER_LINJE_FRA_AVINOR_2014
    FILEGDB_NETWORK_AUTHENTICATION = AUTH_INFO_GROUP,YES,AUTH_METHOD,Basic,NAMED_CONNECTION,<Unused>,AUTH_USERNAME,geonorge,AUTH_PASSWORD,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
    ATTR_ACCUM_MODE = Only Use Result
    FILEGDB_USE_SEARCH_ENVELOPE = NO
    FILEGDB_QUERY_FEATURE_TYPES_FOR_MERGE_FILTERS = Yes
    <SCHEMA> -> FeatureReader_2__Schema_ [off]
    <OTHER> -> FeatureReader_2__Generic_ [off]
    INITIATOR -> FeatureReader_2__Initiator_ [off]
    <REJECTED> -> FeatureReader_2__Rejected_ [off]
FeatureReader_2__Schema_: Inspector [off]
FeatureReader_2__Generic_: Inspector [off]
FeatureReader_2__Initiator_: Inspector [off]
FeatureReader_2__Rejected_: Inspector [off]
PythonCreator
    PYTHONSOURCE:
      import fmeobjects
      import ftplib
      # Template Class
      class FeatureCreator(object):
          def __init__(self):
              ftp = ftplib.FTP('ftp.statkart.no')
              ftp.login('geonorge','GeoData2All')
              ftp.cwd('Avinor/Støy/Stoysoner.gdb')
              list = ftp.nlst()
          def close(self):
              for f in list:
                  feature = fmeobjects.FMEFeature()
              self.pyoutput(feature)
    PYTHONSYMBOL = FeatureCreator
    -> PythonCreator_Output
PythonCreator_Output: Inspector
