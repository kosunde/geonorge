FME workspace sentrumsOmrader_sosi2postgis.fmw

Parameters:
- file_content =   # Innhold i SOSI-fil
- CONFIG_FILE:   # Python Script
      #-------------------------------------------------------------------------------
      # Name:        GetConfigFile
      # Purpose:
      #
      # Author:      xsunknu
      #
      # Created:     21.08.2015
      # Copyright:   (c) xsunknu 2015
      # Licence:     <your licence>
      #-------------------------------------------------------------------------------
      
      import os, fme
      
      fmwdir = fme.macroValues['FME_MF_DIR']
      fmwfile = fme.macroValues['FME_MF_NAME']
      
      fmwfile = os.path.join(fmwdir, fmwfile)
      configfile = os.path.splitext(fmwfile)[0] + '_config.xml'
      
      return configfile
- DestDataset_POSTGIS:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgdb').text
      
      return value

Writers:
- POSTGIS_1: POSTGIS to $(DestDataset_POSTGIS)

Creator
    GEOMTYPE = Geometry Object
    NUM = 1
    CREATED -> HTTPCaller
HTTPCaller
    RESPONSE_HEADER_LIST_ATTR = _headers
    STATUS_CODE_ATTR = _http_status_code
    FILE_PATH_ATTR = _response_file_path
    SAVE_MULTI = No
    VERIFY_SSL_CERTIFICATES = Yes
    HTTP_METHOD = GET
    TARGET_URL = https://www.ssb.no/natur-og-miljo/_attachment/211004?_ts=14a340be350
    OUTPUT_FILENAME = C:\temp\temp.zip
    FOLLOW_REDIRECTS = Yes
    USE_COOKIES = No
    SAVE_FILE = File
    ERROR_ATTR = _error
    TRANSFER_TIMEOUT_LENGTH = 90
    CONNECTION_TIMEOUT_LENGTH = 60
    -> AttributeCreator
AttributeCreator
    ATTR_LIST = _file_content,""
    -> PythonCaller
PythonCaller
    PYTHONSOURCE:
      import sys, os, zipfile, fme, tempfile, fmeobjects

      def main(feature):
          fileFormats=['sos']

          fil = unicode(feature.getAttribute("_response_file_path"))
          tmpDir=tempfile.mkdtemp()
          z=zipfile.ZipFile(fil)
          zipfile.ZipFile.extractall(z,tmpDir)

          for file in os.listdir(tmpDir):
              newFile=tmpDir+'\\'+file
              if file.split('.')[1].lower() in fileFormats:
                  #fme.macroValues['file_content']=open(newFile).read()
                  feature.setAttribute('_file_content',open(newFile).read())
    PYTHONSYMBOL = main
    -> AttributeFileWriter
AttributeFileWriter
    CHAR_ENCODING = iso-8859-1
    SOURCE_ATTR = _file_content
    OVERWRITE_FILE = Overwrite file
    FILE_NAME = C:\temp\temp.sos
    -> FeatureReader
FeatureReader
    FEATURETYPES = SENTRUMSSONE SENTRUMSSONEGRENSE
    SOSI_READER_ATTRIBUTE_VALIDATION_LEVEL = Basic
    ATTRIBUTES = SENTRUMSSONE,"fme_geometry{0},SOSI_id",SENTRUMSSONEGRENSE,fme_geometry{0}
    SOSI_READER_MISSING_Z_VALUE = -9999
    FORMAT = SOSI
    SOSI_READER_LOG_WARNINGS = no
    COMBINE_GEOM = Use Result
    OUTPUT_FEATURES_DISPLAY = Based on Connections
    ATTR_ACCUM_MODE = Only Use Result
    SOSI_READER_REFERENCE_SCALE = 1
    DATASET = c:\temp\temp.sos
    SOSI_READER_ENFORCE_Z_VALUES = Auto-detect
    SOSI_READER_ALLOW_MISSING_MANDATORY_ATTRS = yes
    SOSI_READER_LOG_ERRORS = yes
    FEATURETYPES_RADIO = FEATURETYPES
    INTERACT = <No Spatial Filter>
    SENTRUMSSONE -> AttributeExposer
    SENTRUMSSONEGRENSE -> AttributeExposer
    <SCHEMA> -> AttributeExposer
Note: Eksponerer attributtene
AttributeExposer
    ATTR_LIST = SOSI_id,OBJTYPE,KOMM,NAVN,KOMMNR,TETTNR,TETTSTEDSN,OPPHAV,AREAL,HOVEDS,AJOUR,VERIFISERI,TSTED,KVALITET
    -> BulkAttributeRenamer
Note: Renamer attributtene til / lowercase
BulkAttributeRenamer
    ATTRCHOICE = All Attributes
    PATTERN_ACTION_DISP = Change Case
    CASE_CHANGE_TYPE = lowercase
    -> AttributeCreator_2
Note: Setter ID'er
AttributeCreator_2
    ATTR_LIST = objid,@Value(sosi_id)
    -> Reprojector
Note: Reprojiserer
Reprojector
    RASTER_CELL_SIZE = Preserve Cells
    INTERPOLATION_TYPE_NAME = Nearest Neighbor
    DEST = EPSG:4258
    SOURCE = Read from feature
    REPROJECTED -> GeometryFilter
Note: Skiller flater og linjer
GeometryFilter
    GEOM_PORT_NAMES = Point Line Arc Area
    BREAK_AGG = No
    AREA -> UUIDGenerator
    LINE -> sentrumsomrader.sentrumsomradergrense (writer POSTGIS_1)
    ARC -> sentrumsomrader.sentrumsomradergrense (writer POSTGIS_1)
sentrumsomrader.sentrumsomradergrense (writer POSTGIS_1)
    attributes: objtype char(200), objid char(200)
UUIDGenerator
    UUID_ATTR = lokalid
    -> AttributeCreator_3
AttributeCreator_3
    ATTR_LIST = navnerom,RA_Trehusmiljoer_DOK
    -> sentrumsomrader.sentrumsomrader (writer POSTGIS_1)
sentrumsomrader.sentrumsomrader (writer POSTGIS_1)
    attributes: objtype char(200), komm char(200), navn char(200), kommnr char(200), tettnr char(200), tettstedsn char(200), opphav char(200), areal char(200), hoveds char(200), ajour char(200), verifiseri char(200), tsted char(200), kvalitet char(200), objid char(200), lokalid char(200), navnerom char(200)
