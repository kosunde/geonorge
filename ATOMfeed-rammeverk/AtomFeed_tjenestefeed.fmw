FME workspace AtomFeed_tjenestefeed.fmw
Title: SOSI ATOM Data Download Feed
Description: Pakka data for SOSI tilbys.
Requirements: FME 2015.0+
History: 23/02/2015,N Wlock,Created

Parameters:
- DestDataset_TEXTLINE = \\nnrifs517\geonorge\Tjenestefeed.xml   # Destination Text File
- CONFIG_FILE:   # Python Script
      #-------------------------------------------------------------------------------
      # Name:        GetConfigFile
      # Purpose:
      #
      # Author:      xsunknu
      #
      # Created:     21.08.2015
      # Copyright:   (c) xsunknu 2015
      # Licence:     <your licence>
      #-------------------------------------------------------------------------------
      
      import os, fme
      
      fmwdir = fme.macroValues['FME_MF_DIR']
      fmwfile = fme.macroValues['FME_MF_NAME']
      
      fmwfile = os.path.join(fmwdir, fmwfile)
      configfile = os.path.splitext(fmwfile)[0] + '_config.xml'
      
      return configfile
- DESCRIPTION:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('description').text
      
      return value
- TITLE:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('title').text
      
      return value
- COPYRIGHT:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('copyright').text
      
      return value
- FORMAT:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('format').text
      
      return value
- UPDATED:   # Python Script
      #-------------------------------------------------------------------------------
      # Name:        GetUTCTimeStamp
      # Purpose:
      #
      # Author:      xsunknu
      #
      # Created:     25.09.2015
      # Copyright:   (c) xsunknu 2015
      # Licence:     <your licence>
      #-------------------------------------------------------------------------------
      
      import datetime
      
      # Finner og formaterer Zulu-tid (UTC)
      ztime = datetime.datetime.utcnow()
      timestring = ztime.strftime('%Y-%m-%dT%H:%MZ')
      
      return timestring

Writers:
- TEXTLINE_1: TEXTLINE to $(DestDataset_TEXTLINE)

Bookmark: Hele landet
Creator_3
    GEOMTYPE = Geometry Object
    NUM = 1
    CREATED -> HTTPCaller
HTTPCaller
    STATUS_CODE_ATTR = _http_status_code
    ERROR_ATTR = _error
    AUTH_METHOD = Basic
    TARGET_ATTR = _response_body
    HTTP_METHOD = GET
    CUSTOM_HEADERS = Accept;application/json
    CONNECTION_TIMEOUT_LENGTH = 60
    TRANSFER_TIMEOUT_LENGTH = 90
    RESPONSE_HEADER_LIST_ATTR = _headers
    FOLLOW_REDIRECTS = Yes
    AUTH_PASSWORD =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
    TARGET_ATTR_ENCODING = auto-detect
    SAVE_FILE = Attribute
    USE_COOKIES = No
    AUTH_USERNAME = admin
    TARGET_URL = http://nnrite507/fmerest/v2/repositories/ATOM-feeds/items?detail=high&type=WORKSPACE
    VERIFY_SSL_CERTIFICATES = Yes
    -> JSONFragmenter
JSONFragmenter
    EXPLODE_FORMAT = JSON
    EXTRACT_ATTR = No
    JSON_ATTR = _response_body
    JSON_QUERY = json[*]
    EXPLODED -> JSONFlattener
JSONFlattener
    NEW_ATTRIBUTES = description lastSaveDate name title type
    JSON_ATTR = _response_body
    RECURSIVE = Yes
    -> StringSearcher
StringSearcher
    REGEXP = >(.*?)<
    STRING_TO_SEARCH = @Value(description)
    MATCHED_PARTS_ATTR = _matched_parts
    MATCHED_RESULT_ATTR = _matched_characters
    CASE = no
    MATCHED -> AttributeCreator_3
AttributeCreator_3
    ATTR_LIST = description,@Value(_matched_parts{0})
    -> AttributeCreator_2
AttributeCreator_2
    ATTR_LIST = Title,@Value(title),Description,@Value(description),ContentType,html,LastUpdate,@Value(lastSaveDate),Id,@Value(name),Category{0}.Category,EPSG:25833,Category{0}.Domain,http://www.opengis.net/def/crs/,Category{0}.Label,EPSG/0/25833,Copyright,$(COPYRIGHT),LinkURI,http://testnedlasting.geonorge.no/fmedatastreaming/ATOM-feeds/@Value(name),LinkRelation,alternate,LinkType,application/atom+xml,LinkTitle,Dataset feed,Content,@Value(description)
    -> BulkAttributeRenamer
BulkAttributeRenamer
    ATTRCHOICE = All Attributes
    PATTERN_ACTION_DISP = Add String Prefix
    REPLACE_STR = Element_
    -> Tester
Tester
    TEST_MODE = Automatic
    TEST_DESCRIPTION = ""
    BOOL_OP = OR
    TEST_CLAUSE = TEST @Value(Element_name) NOT_= AtomFeed_tjenestefeed.fmw
    PASSED -> Joiner
Joiner
    JOIN_KEYS = Element_Description Tittel
    MSSQL_ADO_ENCRYPT_CONNECTION = NO
    MSSQL_ADO_USE_SSPI = NO
    MATCH_RULE_DISPLAY = Match First (1:0..1+)
    TABLE = dbo.Dataset
    MSSQL_ADO_QUERY_FEATURE_TYPES_FOR_MERGE_FILTERS = Yes
    CACHE_SIZE = 5000
    MSSQL_ADO_PASSWORD =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
    MSSQL_ADO_SERVER = 159.162.102.151,1433
    DATASET = kartverket_nedlasting
    PREFETCH_EXHAUSTIVE = Yes
    ADDED_FIELDS = metadataUuid
    MSSQL_ADO_USER_NAME = geodata
    MSSQL_ADO_COMMAND_TIMEOUT = 30
    FORMAT = MSSQL_ADO
    JOINED -> HTTPCaller_2
HTTPCaller_2
    STATUS_CODE_ATTR = _http_status_code
    ERROR_ATTR = _error
    TARGET_ATTR = _response_body
    HTTP_METHOD = GET
    CONNECTION_TIMEOUT_LENGTH = 60
    TRANSFER_TIMEOUT_LENGTH = 90
    RESPONSE_HEADER_LIST_ATTR = _headers
    FOLLOW_REDIRECTS = Yes
    TARGET_ATTR_ENCODING = auto-detect
    SAVE_FILE = Attribute
    USE_COOKIES = No
    TARGET_URL = https://www.geonorge.no/geonetwork/srv/nor/xml_iso19139?uuid=@Value(metadataUuid)
    VERIFY_SSL_CERTIFICATES = Yes
    -> XMLFlattener
XMLFlattener
    NEW_ATTRIBUTES = abstract.CharacterString CI_ResponsibleParty.individualName.CharacterString CI_ResponsibleParty.organisationName.CharacterString
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    EMBEDDED_EXPRESSIONS = *
    XML_SOURCE_TYPE = Attribute with XML document
    ATTRIBUTE_XML = _response_body
    -> Sorter
Sorter
    SORT_PARM = Element_Title ALPHA ASCENDING
    SORTED -> XMLTemplater [input 2]

Bookmark: Feed
Creator_2
    GEOMTYPE = Geometry Object
    NUM = 1
    CREATED -> AttributeCreator
AttributeCreator
    ATTR_LIST = Title,$(TITLE),Description,$(DESCRIPTION),LinkURI,http://testnedlasting.geonorge.no/fmedatastreaming/ATOM-feeds/AtomFeed_tjenestefeed.fmw,Id,http://testnedlasting.geonorge.no/fmedatastreaming/ATOM-feeds/AtomFeed_tjenestefeed.fmw,LastUpdate,$(UPDATED),LinkRelation,self,LinkType,application/atom+xml,Copyright,$(COPYRIGHT),Author,Geonorge,AuthorEmail,post@kartverket.no
    -> XMLTemplater [input 1]
XMLTemplater
    RESULT_ATTRIBUTE = text_line_data
    SUB_QUERY_EXPR:
        <entry>
          <title>{fme:get-attribute("Element_Title")}</title>
      	<summary>{fme:get-attribute("abstract.CharacterString")}</summary>
          <spatial_dataset_identifier_code>{fme:get-attribute("metadataUuid")}</spatial_dataset_identifier_code>
          <spatial_dataset_identifier_namespace>http://www.geonorge.no/</spatial_dataset_identifier_namespace>
          <id>{fme:get-attribute("Element_LinkURI")}</id>
          <rights>Geonorge</rights>
          <updated>2015-10-28T13:11:49</updated>
          <author>
            <name>{fme:get-attribute("Author")}</name>
          </author>
          <category term="EPSG:25833" scheme="http://www.opengis.net/def/crs/" label="EPSG/0/25833"/>
          <content type="html">{fme:get-attribute("abstract.CharacterString")}</content>
          <link href="https://www.geonorge.no/geonetwork/srv/nor/xml_iso19139?uuid={fme:get-attribute("metadataUuid")}" rel="describedby" type="application/vnd.ogc.csw.GetRecordByIdResponse_xml" title="Dataset Metadata" />
          <link rel="{fme:get-attribute("Element_LinkRelation")}" href="{fme:get-attribute("Element_LinkURI")}" type="{fme:get-attribute("Element_LinkType")}" title="{fme:get-attribute("Element_LinkTitle")}"/>
          <published>2015-11-05T14:38:49+01:00</published>
        </entry>
    ROOT_QUERY_EXPR:
      <?xml version="1.0" encoding="UTF-8"?>
      <feed xmlns="http://www.w3.org/2005/Atom" xmlns:georss="http://www.georss.org/georss" xmlns:inspire_dls="http://inspire.ec.europa.eu/schemas/inspire_dls/1.0">
        <title>Geonorge AtomFeeds</title>
        <subtitle>Tjenestefeed for alle datasett tilgjengelige i Geonorge</subtitle>
        <link href="http://www.geonorge.no" rel="describedby" type="application/html" title="Download Service Feed Metadata" />
        <link href="http://testnedlasting.geonorge.no/Tjenestefeed.xml" hreflang="no-nb" rel="self" type="application/atom+xml" title="Download Service Feed" />
        <link href="http://www.weichand.de:8080/opensearchdls/verwaltungsgrenzen" hreflang="de" rel="search" type="application/opensearchdescription+xml" title="OpenSearch Description" />
        <id>http://testnedlasting.geonorge.no/Tjenestefeed.xml</id>
        <rights>Copyright den enkelte dataeier</rights>
        <updated>2013-01-03T00:00:00+02:00</updated>
        <author>
          <name>Geonorge</name>
          <email>post@geonorge.no</email>
        </author>
      {fme:process-features("SUB")}

      </feed>
    VISIBLE_QUERY_VALIDATE = Yes
    OUTPUT_XML_HEADER = Yes
    -> StringReplacer
StringReplacer
    REGEXP = no
    NO_MATCH = _FME_NO_OP_
    REPLACE_TEXT = inspire_dls:spatial_dataset_
    CASE = no
    SRC_ATTRS = text_line_data
    FIND_TEXT = spatial_dataset_
    -> StringReplacer_2
StringReplacer_2
    REGEXP = no
    NO_MATCH = _FME_NO_OP_
    REPLACE_TEXT = entry>
    CASE = no
    SRC_ATTRS = text_line_data
    FIND_TEXT = entry xmlns="">
    -> text_line (writer TEXTLINE_1)
text_line (writer TEXTLINE_1)
    attributes: text_line_data buffer
