FME workspace Grunnskoler_xsl2postgis.fmw

Parameters:
- CONFIG_FILE:   # Python Script
      #-------------------------------------------------------------------------------
      # Name:        GetConfigFile
      # Purpose:
      #
      # Author:      xsunknu
      #
      # Created:     21.08.2015
      # Copyright:   (c) xsunknu 2015
      # Licence:     <your licence>
      #-------------------------------------------------------------------------------
      
      import os, fme
      
      fmwdir = fme.macroValues['FME_MF_DIR']
      fmwfile = fme.macroValues['FME_MF_NAME']
      
      fmwfile = os.path.join(fmwdir, fmwfile)
      configfile = os.path.splitext(fmwfile)[0] + '_config.xml'
      
      return configfile
- XLS_IN:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('xlsin').text
      
      return value
- PG_DB:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgdb').text
      
      return value
- LOG_FILE:   # Python Script
      #-------------------------------------------------------------------------------
      # Name:        GetConfigFile
      # Purpose:
      #
      # Author:      xsunknu
      #
      # Created:     21.08.2015
      # Copyright:   (c) xsunknu 2015
      # Licence:     <your licence>
      #-------------------------------------------------------------------------------
      
      import os, uuid, fme
      
      fmwdir = fme.macroValues['FME_MF_DIR']
      fmwfile = fme.macroValues['FME_MF_NAME']
      
      logdir = os.path.join(fmwdir, 'log')
      if not os.path.isdir(logdir):
          os.mkdir(logdir)
      
      logfile = os.path.splitext(fmwfile)[0] + '_' + str(uuid.uuid1()).replace('-','') + '.log'
      logfile = os.path.join(logdir, logfile)
      
      return logfile

Readers:
- XLSXR_1: XLSXR from $(XLS_IN)

Writers:
- POSTGIS_1: POSTGIS to $(PG_DB)

Egendefinert (reader XLSXR_1)
    attributes: Navn char(57), År char(8), C-41_d257 number(3,0), C-43_d266 number(2,0), C-44_d774 number(3,0), C-45_d1321 number(3,0), A-15_d57 number(4,0), G_d900 char(10), G_d902 char(10), G_u3 number(10,0), G_u6 number(10,0), G_u1 number(3,0), G_eu1 char(9), G_u2 number(5,0), G_eu2 char(16), G_uName char(57), G_u10 char(38), G_u4 number(5,0), G_eu4 char(19), G_uCustomId number(6,0), G_u11 char(33), G_u5 number(6,0), G_eu5 char(18), G_u16 char(50), G_u14 char(13), G_u12 char(58)
    -> AttributeRenamer
Note: Navner om til "vennlige" / attributtnavn
AttributeRenamer
    ATTR_LIST = C-41_d257,ant_larere,,C-43_d266,ant_utdogyrkrradg,,C-44_d774,ant_sospedradg,,C-45_d1321,ant_ass,,A-15_d57,ant_elever,,G_d900,laveste_trinn,,G_d902,hoyeste_trinn,,G_u3,orgnr_bedrift,,G_u6,orgnr_foretak,,G_u1,fylkesnr,,G_eu1,fylkesnavn,,G_u2,kommunenr,,G_eu2,kommunenavn,,G_uName,navn_enhet,,G_u10,post_postadresse,,G_u4,post_postnummer,,G_eu4,post_poststed,,G_u11,besok_postadresse,,G_u5,besok_postnummer,,G_eu5,besok_poststed,,G_uCustomId,gsi_id,,G_u16,navn_leder,,G_u14,enhet_telefon,,G_u12,enhet_epost,
    -> Tester
Note: Tar ikke med overordnede enheter / Antall elever = 0
Tester
    BOOL_OP = OR
    TEST_MODE = Automatic
    TEST_DESCRIPTION = ""
    TEST_CLAUSE = TEST @Value(ant_elever) > 0
    PASSED -> AttributeCreator_3
undervisning.skole (writer POSTGIS_1)
    attributes: objid int4,PRIKEY, objtype varchar(32), gsi_id int4,BTREE, navn varchar(80), laveste_trinn int4, hoyeste_trinn varchar(80), antall_ansatte int4, antall_elever int4, oppfortdato timestamp, kommunenavn varchar(80), bygningstype varchar(80), malemetode varchar(80), noyaktighet int4, postnummer varchar(80), poststed varchar(80), fylkesnr varchar(80), komm varchar(80), adressekode int4, nummer int4, bokstav varchar(80), adressenavn varchar(80), epostadresse varchar(80), kontaktperson varchar(80), organisasjonsnavn varchar(80), organisasjonsnummer varchar(80), telefonnummer varchar(80), eierforhold varchar(80), webadresse varchar(255)

Bookmark: Henter eieroinfo i BRREG
AttributeCreator_3
    ATTR_LIST = _url,http://data.brreg.no/enhetsregisteret/enhet/@Value(orgnr_foretak).json
    -> HTTPCaller_3
HTTPCaller_3
    TARGET_ATTR = _response_body
    HTTP_METHOD = GET
    TARGET_URL = @Value(_url)
    STATUS_CODE_ATTR = _http_status_code
    USE_COOKIES = No
    ERROR_ATTR = _error
    SAVE_FILE = Attribute
    RESPONSE_HEADER_LIST_ATTR = _headers
    VERIFY_SSL_CERTIFICATES = Yes
    TARGET_ATTR_ENCODING = auto-detect
    TRANSFER_TIMEOUT_LENGTH = 90
    FOLLOW_REDIRECTS = Yes
    CONNECTION_TIMEOUT_LENGTH = 60
    -> JSONFlattener_3
JSONFlattener_3
    RECURSIVE = Yes
    PREFIX_STRING = enhet_
    NEW_ATTRIBUTES = enhet_navn enhet_organisasjonsnummer enhet_naeringskode1.kode enhet_naeringskode1.beskrivelse
    JSON_ATTR = _response_body
    -> AttributeRemover
AttributeRemover
    LIST_ATTRS = _headers{} _headers{}.name _headers{}.value
    REMOVE_ATTRS = _http_status_code,_response_body,_url
    -> AttributeRenamer_3
AttributeRenamer_3
    ATTR_LIST = enhet_navn,eier_orgnavn,,enhet_organisasjonsnummer,eier_orgnr,
    -> AttributeTrimmer

Bookmark: Vasker data
AttributeTrimmer
    SRC_ATTRS = hoyeste_trinn,laveste_trinn
    TRIM_TO_NONE = Yes
    TRIM_CHARS = . trinn
    TRIM_TYPE = Both
    -> NullAttributeMapper
NullAttributeMapper
    REG_EXP = Ikke satt
    ATTRCHOICE = Selected Attributes
    ATTRLIST = hoyeste_trinn laveste_trinn
    NULL_TREATMENT = Missing
    SOURCE_ATTR_VAL = Empty "Missing (Selected Attributes Only)" Null
    OTHER_VALUE = " "
    -> StringReplacer_2
StringReplacer_2
    SRC_ATTRS = enhet_telefon
    CASE = no
    NO_MATCH = _FME_NO_OP_
    FIND_TEXT = " "
    REGEXP = no
    -> HTTPCaller

Bookmark: Geokoder
HTTPCaller
    TARGET_ATTR = _response_body
    HTTP_METHOD = GET
    TARGET_URL = http://services2.geodataonline.no/arcgis/tokens/generateToken?username=gdinternal&password=HomeUser20%23%23&client=requestip&expiration=60&f=json
    STATUS_CODE_ATTR = _http_status_code
    USE_COOKIES = No
    ERROR_ATTR = _error
    SAVE_FILE = Attribute
    RESPONSE_HEADER_LIST_ATTR = _headers
    VERIFY_SSL_CERTIFICATES = Yes
    TARGET_ATTR_ENCODING = auto-detect
    TRANSFER_TIMEOUT_LENGTH = 90
    FOLLOW_REDIRECTS = Yes
    CONNECTION_TIMEOUT_LENGTH = 60
    -> JSONFlattener
JSONFlattener
    RECURSIVE = Yes
    NEW_ATTRIBUTES = token
    JSON_ATTR = _response_body
    -> AttributeCreator
AttributeCreator
    ATTR_LIST = url,http://services2.geodataonline.no/arcgis/rest/services/Geosok/GeosokLokasjon2/GeocodeServer/findAddressCandidates?Adresse=@Value(besok_postadresse)&Postnummer=@Value(besok_postnummer)&Poststed=@Value(besok_poststed)&token=@Value(token)&f=pjson
    -> HTTPCaller_2
HTTPCaller_2
    TARGET_ATTR = _response_body
    HTTP_METHOD = GET
    TARGET_URL = @Value(url)
    STATUS_CODE_ATTR = _http_status_code
    USE_COOKIES = No
    ERROR_ATTR = _error
    SAVE_FILE = Attribute
    RESPONSE_HEADER_LIST_ATTR = _headers
    VERIFY_SSL_CERTIFICATES = Yes
    TARGET_ATTR_ENCODING = auto-detect
    TRANSFER_TIMEOUT_LENGTH = 90
    FOLLOW_REDIRECTS = Yes
    CONNECTION_TIMEOUT_LENGTH = 60
    -> JSONFlattener_2
JSONFlattener_2
    RECURSIVE = Yes
    NEW_ATTRIBUTES = candidates{0}.location.x candidates{0}.location.y candidates{0}.score
    JSON_ATTR = _response_body
    -> VertexCreator

Bookmark: Geometri
VertexCreator
    XVAL = @Value(candidates{0}.location.x)
    MODE_NAME = Add Point
    YVAL = @Value(candidates{0}.location.y)
    -> CoordinateSystemSetter
CoordinateSystemSetter
    COORDSYS = EPSG:25833
    -> Reprojector
Reprojector
    RASTER_CELL_SIZE = Preserve Cells
    DEST = EPSG:4258
    SOURCE = Read from feature
    INTERPOLATION_TYPE_NAME = Nearest Neighbor
    REPROJECTED -> AttributeRenamer_2

Bookmark: Mapper til endelig skjema
AttributeRenamer_2
    ATTR_LIST = candidates{0}.score,posisjon_kvalitet,,ant_elever,antall_elever,,navn_enhet,navn,,eier_orgnavn,organisasjonsnavn,,eier_orgnr,organisasjonsnummer,,navn_leder,kontaktperson,
    -> AttributeCreator_2
AttributeCreator_2
    ATTR_LIST = objid,@Evaluate(@Count(grunnskoler, 1)),objtype,Skole,antall_ansatte,@Evaluate(@Value(ant_larere)+@Value(ant_sospedradg)+@Value(ant_utdogyrkrradg)+@Value(ant_ass)),bygningstype,"FME_CONDITIONAL:DEFAULT_VALUE'_FME_NO_OP_'BOOL_OP;AND;COMPOSITE_TEST;<Unused>;TEST @Value(laveste_trinn) = 1;TEST @Value(hoyeste_trinn) = 7'613'BOOL_OP;AND;COMPOSITE_TEST;<Unused>;TEST @Value(laveste_trinn) = 1;TEST @Value(hoyeste_trinn) = 3'613'BOOL_OP;AND;COMPOSITE_TEST;<Unused>;TEST @Value(laveste_trinn) = 1;TEST @Value(hoyeste_trinn) = 4'613'BOOL_OP;AND;COMPOSITE_TEST;<Unused>;TEST @Value(laveste_trinn) = 1;TEST @Value(hoyeste_trinn) = 5'613'BOOL_OP;AND;COMPOSITE_TEST;<Unused>;TEST @Value(laveste_trinn) = 1;TEST @Value(hoyeste_trinn) = 6'613'BOOL_OP;AND;COMPOSITE_TEST;<Unused>;TEST @Value(laveste_trinn) = 8;TEST @Value(hoyeste_trinn) = 10'614'BOOL_OP;AND;COMPOSITE_TEST;<Unused>;TEST @Value(laveste_trinn) = 1;TEST @Value(hoyeste_trinn) = 10'615'FME_NUM_CONDITIONS8___",malemetode,63,noyaktighet,"FME_CONDITIONAL:DEFAULT_VALUE'_FME_NO_OP_'BOOL_OP;OR;COMPOSITE_TEST;<Unused>;TEST @Value(posisjon_kvalitet) = 100'100'FME_NUM_CONDITIONS2___",postnummer,@Value(besok_postnummer),poststed,@Value(besok_poststed),komm,@Value(kommunenr),eierforhold,"FME_CONDITIONAL:DEFAULT_VALUE'Annet'BOOL_OP;AND;COMPOSITE_TEST;<Unused>;TEST @Value(enhet_naeringskode1.kode) > 84;TEST @Value(enhet_naeringskode1.kode) < 85'Offentlig'BOOL_OP;AND;COMPOSITE_TEST;<Unused>;TEST @Value(enhet_naeringskode1.kode) > 85;TEST @Value(enhet_naeringskode1.kode) < 86'Privat'FME_NUM_CONDITIONS3___"
    -> StringSearcher
StringSearcher
    CASE = no
    STRING_TO_SEARCH = @Value(besok_postadresse)
    MATCHED_PARTS_ATTR = _matched_parts
    REGEXP = ([0-9])+
    MATCHED_RESULT_ATTR = nummer
    NOT_MATCHED -> Tester_2
    MATCHED -> Tester_2
Tester_2
    BOOL_OP = AND
    TEST_MODE = Automatic
    TEST_DESCRIPTION = ""
    TEST_CLAUSE:
      TEST nummer NOT_ATTRIBUTE_VALUE_NULL ""
      TEST nummer NOT_ATTRIBUTE_IS_EMPTY ""
      TEST nummer NOT_ATTRIBUTE_IS_MISSING ""
    PASSED -> StringSearcher_2
    FAILED -> StringReplacer
StringSearcher_2
    CASE = no
    STRING_TO_SEARCH = @Value(besok_postadresse)
    MATCHED_PARTS_ATTR = _matched_parts
    REGEXP = \D{1}$
    MATCHED_RESULT_ATTR = bokstav
    MATCHED -> AttributeTrimmer_2
    NOT_MATCHED -> AttributeTrimmer_2
AttributeTrimmer_2
    SRC_ATTRS = besok_postadresse
    TRIM_TO_NONE = Yes
    TRIM_CHARS = @Value(bokstav)
    TRIM_TYPE = Right
    -> StringReplacer
StringReplacer
    SRC_ATTRS = besok_postadresse
    CASE = no
    NO_MATCH = _FME_NO_OP_
    FIND_TEXT = @Value(nummer)
    REGEXP = no
    -> StringCaseChanger
StringCaseChanger
    ATTRCHOICE = Selected Attributes
    ATTRLIST = bokstav
    CHANGE_TYPE = UPPERCASE
    -> AttributeRenamer_4
AttributeRenamer_4
    ATTR_LIST = besok_postadresse,adressenavn,,enhet_epost,epostadresse,,enhet_telefon,telefonnummer,
    -> undervisning.skole (writer POSTGIS_1)
