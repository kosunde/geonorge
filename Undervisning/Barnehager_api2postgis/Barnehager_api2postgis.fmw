FME workspace Barnehager_api2postgis.fmw

Parameters:
- CONFIG_FILE:   # Python Script
      #-------------------------------------------------------------------------------
      # Name:        GetConfigFile
      # Purpose:
      #
      # Author:      xsunknu
      #
      # Created:     21.08.2015
      # Copyright:   (c) xsunknu 2015
      # Licence:     <your licence>
      #-------------------------------------------------------------------------------
      
      import os, fme
      
      fmwdir = fme.macroValues['FME_MF_DIR']
      fmwfile = fme.macroValues['FME_MF_NAME']
      
      fmwfile = os.path.join(fmwdir, fmwfile)
      configfile = os.path.splitext(fmwfile)[0] + '_config.xml'
      
      return configfile
- PG_DB:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgdb').text
      
      return value
- LOG_FILE:   # Python Script
      #-------------------------------------------------------------------------------
      # Name:        GetConfigFile
      # Purpose:
      #
      # Author:      xsunknu
      #
      # Created:     21.08.2015
      # Copyright:   (c) xsunknu 2015
      # Licence:     <your licence>
      #-------------------------------------------------------------------------------
      
      import os, uuid, fme
      
      fmwdir = fme.macroValues['FME_MF_DIR']
      fmwfile = fme.macroValues['FME_MF_NAME']
      
      logdir = os.path.join(fmwdir, 'log')
      if not os.path.isdir(logdir):
          os.mkdir(logdir)
      
      logfile = os.path.splitext(fmwfile)[0] + '_' + str(uuid.uuid1()).replace('-','') + '.log'
      logfile = os.path.join(logdir, logfile)
      
      return logfile

Readers:
- POSTGRES_1: POSTGRES from $(PG_DB)

Writers:
- POSTGIS_1: POSTGIS to $(PG_DB)

AttributeRemover
    REMOVE_ATTRS = _http_status_code,_matched_characters,_response_body,_url,text_line_data
    LIST_ATTRS = _headers{} _headers{}.name _headers{}.value _matched_parts{} parts{}
    -> HTTPCaller_3
undervisning.barnehage (writer POSTGIS_1)
    attributes: objid int4,PRIKEY, objtype varchar(32), nbr_id int4,BTREE, navn varchar(80), hoyeste_alder int4, laveste_alder int4, apningstidfra varchar(20), apningstidtil varchar(20), barnehagetype varchar(80), status varchar(80), pedagogiskprofil varchar(80), antall_ansatte int4, antall_elever int4, oppfortdato timestamp, kommunenavn varchar(80), bygningstype varchar(80), malemetode varchar(80), noyaktighet int4, postnummer varchar(80), poststed varchar(80), fylkesnr varchar(80), komm varchar(80), adressekode int4, nummer int4, bokstav varchar(80), adressenavn varchar(80), epostadresse varchar(80), kontaktperson varchar(80), organisasjonsnavn varchar(80), organisasjonsnummer varchar(80),
      telefonnummer varchar(80), eierforhold varchar(80), webadresse varchar(255)
Note: Logger features som ikke / har fått gyldig geometri
VertexCreator__Rejected_: Logger
    MAXFEATS = 10000
    MESSAGE = Feature is:
    MAXCOORDS = 20
Note: Logger barnehager i NBR / som ikke finnes i BAF
HTTPCaller_2__Rejected_: Logger
    MAXFEATS = 10000
    MESSAGE = Feature is:
    MAXCOORDS = 20

Bookmark: Finner liste over ID'er for alle landets barnehager fra NBR
admingrense.fylker (reader POSTGRES_1)
    attributes: fylkeid int2,PRIKEY, navn varchar(80)
    -> AttributeCreator_2
AttributeCreator_2
    ATTR_LIST = url,https://nbr.udir.no/kart/fylke/@PadLeft(@Value(fylkeid),2,0)
    -> HTTPCaller
HTTPCaller
    TARGET_URL = @Value(url)
    USE_COOKIES = No
    STATUS_CODE_ATTR = _http_status_code
    VERIFY_SSL_CERTIFICATES = Yes
    ERROR_ATTR = _error
    TRANSFER_TIMEOUT_LENGTH = 90
    RESPONSE_HEADER_LIST_ATTR = _headers
    FOLLOW_REDIRECTS = Yes
    TARGET_ATTR_ENCODING = auto-detect
    TARGET_ATTR = _response_body
    HTTP_METHOD = GET
    SAVE_FILE = Attribute
    CONNECTION_TIMEOUT_LENGTH = 60
    -> AttributeFileWriter
AttributeFileWriter
    FILE_NAME = D:\scratch\barnehager.htm
    SOURCE_ATTR = _response_body
    OVERWRITE_FILE = Overwrite file
    CHAR_ENCODING = fme-system
    -> FeatureReader
FeatureReader
    OUTPUT_FEATURES_DISPLAY = Based on Connections
    DATASET = D:\scratch\barnehager.htm
    COMBINE_GEOM = Use Result
    FORMAT = TEXTLINE
    TEXTLINE_SKIP_FOOTER = 0
    TEXTLINE_READ_WHOLE_FILE_AT_ONCE = NO
    TEXTLINE_READ_BOTTOM_UP = No
    FEATURETYPES_RADIO = FEATURETYPES
    ATTR_ACCUM_MODE = Only Use Result
    TEXTLINE_SKIP_LINES = 0
    ATTRIBUTES = text_line,"text_line_data,fme_geometry{0}"
    text_line -> StringSearcher
StringSearcher
    MATCHED_PARTS_ATTR = _matched_parts
    STRING_TO_SEARCH = @Value(text_line_data)
    REGEXP = /enhet/\d\d\d\d\d\d\d
    MATCHED_RESULT_ATTR = _matched_characters
    CASE = no
    MATCHED -> AttributeSplitter
AttributeSplitter
    DELIMITER = /
    TRIM_OPTION = Both
    LIST_NAME = parts
    ATTR_NAME = _matched_characters
    DROP_EMPTY_PARTS = No
    -> AttributeCreator
AttributeCreator
    ATTR_LIST = barnehage_id,@Value(parts{2})
    -> AttributeCreator_3

Bookmark: Henter data for barnehagen ved bruk av API
AttributeCreator_3
    ATTR_LIST = _url,http://barnehagefakta.no/api/barnehage/@Value(barnehage_id)#
    -> HTTPCaller_2
HTTPCaller_2
    TARGET_URL = @Value(_url)
    USE_COOKIES = No
    STATUS_CODE_ATTR = _http_status_code
    VERIFY_SSL_CERTIFICATES = Yes
    ERROR_ATTR = _error
    TRANSFER_TIMEOUT_LENGTH = 90
    RESPONSE_HEADER_LIST_ATTR = _headers
    FOLLOW_REDIRECTS = Yes
    TARGET_ATTR_ENCODING = auto-detect
    TARGET_ATTR = _response_body
    HTTP_METHOD = GET
    SAVE_FILE = Attribute
    CONNECTION_TIMEOUT_LENGTH = 60
    -> JSONFlattener
    <Rejected> -> HTTPCaller_2__Rejected_
JSONFlattener
    NEW_ATTRIBUTES = id alder ansatte.antallFra ansatte.antallTil eierform basilId erAktiv erBarnehage erBarnehageEier erPrivatBarnehage fylke.fylkesnavn fylke.fylkesnummer kommune.kommunenavn kommune.kommunenummer kontaktinformasjon.postAdresse.adresselinje kontaktinformasjon.postAdresse.postnr kontaktinformasjon.postAdresse.poststed kontaktinformasjon.besoksAdresse.adresselinje kontaktinformasjon.besoksAdresse.postnr kontaktinformasjon.besoksAdresse.poststed kontaktinformasjon.epost kontaktinformasjon.url kontaktinformasjon.telefon koordinatLatLng malform.malformType malform.malformNavn opprettetDato navn orgnr nsrId indikatorDataBarnehage.antallBarn indikatorDataBarnehage.antallBarnPerAnsatt indikatorDataBarnehage.andelAnsatteMedBarneOgUngdomsarbeiderfag indikatorDataBarnehage.andelAnsatteMedAnnenPedagogiskUtdanning indikatorDataBarnehage.andelAnsatteBarnehagelarer indikatorDataBarnehage.andelAnsatteMedAnnenBakgrunn indikatorDataBarnehage.andelAnsatteMedPedagogiskUtdanning indikatorDataBarnehage.lekeOgOppholdsarealPerBarn indikatorDataKommune.antallBarn indikatorDataKommune.antallBarnPerAnsatt indikatorDataKommune.andelAnsatteMedBarneOgUngdomsarbeiderfag indikatorDataKommune.andelAnsatteMedAnnenPedagogiskUtdanning indikatorDataKommune.andelAnsatteBarnehagelarer indikatorDataKommune.andelAnsatteMedAnnenBakgrunn indikatorDataKommune.andelAnsatteMedPedagogiskUtdanning indikatorDataKommune.lekeOgOppholdsarealPerBarn kostpenger type pedagogiskProfil apningstidFra apningstidTil oppfyllerPedagognorm urlTilSoknadOmBarnehageplass
    JSON_ATTR = _response_body
    RECURSIVE = Yes
    -> AttributeCreator_7

Bookmark: Finner underenhet i BRREG
AttributeCreator_7
    ATTR_LIST = _url,http://data.brreg.no/enhetsregisteret/underenhet/@Value(orgnr).json
    -> HTTPCaller_5
HTTPCaller_5
    TARGET_URL = @Value(_url)
    USE_COOKIES = No
    STATUS_CODE_ATTR = _http_status_code
    VERIFY_SSL_CERTIFICATES = Yes
    ERROR_ATTR = _error
    TRANSFER_TIMEOUT_LENGTH = 90
    RESPONSE_HEADER_LIST_ATTR = _headers
    FOLLOW_REDIRECTS = Yes
    TARGET_ATTR_ENCODING = auto-detect
    TARGET_ATTR = _response_body
    HTTP_METHOD = GET
    SAVE_FILE = Attribute
    CONNECTION_TIMEOUT_LENGTH = 60
    -> JSONFlattener_4
JSONFlattener_4
    NEW_ATTRIBUTES = overordnetEnhet
    JSON_ATTR = _response_body
    RECURSIVE = Yes
    -> AttributeCreator_8

Bookmark: Finner enhet i BRREG
AttributeCreator_8
    ATTR_LIST = _url,http://data.brreg.no/enhetsregisteret/enhet/@Value(overordnetEnhet).json
    -> HTTPCaller_6
HTTPCaller_6
    TARGET_URL = @Value(_url)
    USE_COOKIES = No
    STATUS_CODE_ATTR = _http_status_code
    VERIFY_SSL_CERTIFICATES = Yes
    ERROR_ATTR = _error
    TRANSFER_TIMEOUT_LENGTH = 90
    RESPONSE_HEADER_LIST_ATTR = _headers
    FOLLOW_REDIRECTS = Yes
    TARGET_ATTR_ENCODING = auto-detect
    TARGET_ATTR = _response_body
    HTTP_METHOD = GET
    SAVE_FILE = Attribute
    CONNECTION_TIMEOUT_LENGTH = 60
    -> JSONFlattener_5
JSONFlattener_5
    NEW_ATTRIBUTES = overordnetEnhet_navn overordnetEnhet_naeringskode1.kode
    JSON_ATTR = _response_body
    PREFIX_STRING = overordnetEnhet_
    RECURSIVE = Yes
    -> AttributeRemover

Bookmark: Geokoder
HTTPCaller_3
    TARGET_URL = http://services2.geodataonline.no/arcgis/tokens/generateToken?username=gdinternal&password=HomeUser20%23%23&client=requestip&expiration=60&f=json
    USE_COOKIES = No
    STATUS_CODE_ATTR = _http_status_code
    VERIFY_SSL_CERTIFICATES = Yes
    ERROR_ATTR = _error
    TRANSFER_TIMEOUT_LENGTH = 90
    RESPONSE_HEADER_LIST_ATTR = _headers
    FOLLOW_REDIRECTS = Yes
    TARGET_ATTR_ENCODING = auto-detect
    TARGET_ATTR = _response_body
    HTTP_METHOD = GET
    SAVE_FILE = Attribute
    CONNECTION_TIMEOUT_LENGTH = 60
    -> JSONFlattener_2
JSONFlattener_2
    NEW_ATTRIBUTES = token
    JSON_ATTR = _response_body
    RECURSIVE = Yes
    -> AttributeCreator_4
AttributeCreator_4
    ATTR_LIST = url,http://services2.geodataonline.no/arcgis/rest/services/Geosok/GeosokLokasjon2/GeocodeServer/findAddressCandidates?Adresse=@Value(kontaktinformasjon.besoksAdresse.adresselinje)&Postnummer=@Value(kontaktinformasjon.besoksAdresse.postnr)&Poststed=@Value(kontaktinformasjon.besoksAdresse.poststed)&token=@Value(token)&f=pjson
    -> HTTPCaller_4
HTTPCaller_4
    TARGET_URL = @Value(url)
    USE_COOKIES = No
    STATUS_CODE_ATTR = _http_status_code
    VERIFY_SSL_CERTIFICATES = Yes
    ERROR_ATTR = _error
    TRANSFER_TIMEOUT_LENGTH = 90
    RESPONSE_HEADER_LIST_ATTR = _headers
    FOLLOW_REDIRECTS = Yes
    TARGET_ATTR_ENCODING = auto-detect
    TARGET_ATTR = _response_body
    HTTP_METHOD = GET
    SAVE_FILE = Attribute
    CONNECTION_TIMEOUT_LENGTH = 60
    -> JSONFlattener_3
JSONFlattener_3
    NEW_ATTRIBUTES = candidates{0}.location.x candidates{0}.location.y candidates{0}.score
    JSON_ATTR = _response_body
    RECURSIVE = Yes
    -> AttributeRemover_2
AttributeRemover_2
    REMOVE_ATTRS = _http_status_code,_response_body
    LIST_ATTRS = _headers{} _headers{}.name _headers{}.value
    -> StringReplacer

Bookmark: Vasker data
StringReplacer
    NO_MATCH = _FME_NO_OP_
    SRC_ATTRS = kontaktinformasjon.telefon
    REGEXP = no
    FIND_TEXT = " "
    CASE = no
    -> AttributeTrimmer
AttributeTrimmer
    TRIM_CHARS = 0
    TRIM_TYPE = Left
    SRC_ATTRS = kontaktinformasjon.telefon
    TRIM_TO_NONE = Yes
    -> AttributeSplitter_2
AttributeSplitter_2
    DELIMITER = -
    TRIM_OPTION = Both
    LIST_NAME = alder
    ATTR_NAME = alder
    DROP_EMPTY_PARTS = No
    -> VertexCreator
VertexCreator
    XVAL = @Value(candidates{0}.location.x)
    YVAL = @Value(candidates{0}.location.y)
    MODE_NAME = Add Point
    -> AttributeRenamer_2
    <REJECTED> -> VertexCreator__Rejected_
AttributeRenamer_2
    ATTR_LIST = candidates{0}.score,posisjon_kvalitet,
    -> AttributeCreator_5
AttributeCreator_5
    ATTR_LIST = fylke,@Value(fylke.fylkesnummer),kommune,@Value(kommune.kommunenummer),besok_postnavn,@Value(kontaktinformasjon.besoksAdresse.adresselinje),besok_postnr,@Value(kontaktinformasjon.besoksAdresse.postnr),besok_poststed,@Value(kontaktinformasjon.besoksAdresse.poststed),post_postnavn,@Value(kontaktinformasjon.postAdresse.adresselinje),post_postnr,@Value(kontaktinformasjon.postAdresse.postnr),post_poststed,@Value(kontaktinformasjon.postAdresse.poststed),telefon,@Value(kontaktinformasjon.telefon),epost,@Value(kontaktinformasjon.epost),alder_fra,@Value(alder{0}),alder_til,@Value(alder{1}),antall_barn,@Value(indikatorDataBarnehage.antallBarn),basil_id,@Value(basilId),objid,@Evaluate(@Count(barnehager, 1))
    -> NullAttributeMapper
NullAttributeMapper
    ATTRCHOICE = Selected Attributes
    ATTRLIST = epost telefon
    SOURCE_ATTR_VAL = Null Empty
    NULL_TREATMENT = Missing
    -> CoordinateSystemSetter

Bookmark: Reprojiserer
CoordinateSystemSetter
    COORDSYS = EPSG:25833
    -> Reprojector
Reprojector
    DEST = EPSG:4258
    INTERPOLATION_TYPE_NAME = Nearest Neighbor
    SOURCE = Read from feature
    RASTER_CELL_SIZE = Preserve Cells
    REPROJECTED -> AttributeSplitter_3

Bookmark: Mapper til endelig skjema
AttributeSplitter_3
    DELIMITER = ,
    TRIM_OPTION = Both
    LIST_NAME = type
    ATTR_NAME = type
    DROP_EMPTY_PARTS = No
    -> AttributeCreator_6
AttributeCreator_6
    ATTR_LIST = objtype,Barnehage,barnehagetype,"FME_CONDITIONAL:DEFAULT_VALUE'FME_NULL_VALUE'BOOL_OP;OR;COMPOSITE_TEST;<Unused>;TEST @Value(type{0}) IN Ordinær barnehage,Åpen barnehage,Familiebarnehage'@Value(type{0})'FME_NUM_CONDITIONS2___",status,"FME_CONDITIONAL:DEFAULT_VALUE'FME_NULL_VALUE'BOOL_OP;OR;COMPOSITE_TEST;<Unused>;TEST @Value(erAktiv) = true'D'FME_NUM_CONDITIONS2___",bygningstype,612,malemetode,63,noyaktighet,"FME_CONDITIONAL:DEFAULT_VALUE'FME_NULL_VALUE'BOOL_OP;OR;COMPOSITE_TEST;<Unused>;TEST @Value(posisjon_kvalitet) = 100'100'FME_NUM_CONDITIONS2___",eierforhold,"FME_CONDITIONAL:DEFAULT_VALUE'Annet'BOOL_OP;OR;COMPOSITE_TEST;<Unused>;TEST @Value(eierform) = Kommunal'Offentlig'BOOL_OP;OR;COMPOSITE_TEST;<Unused>;TEST @Value(eierform) = Privat'Privat'FME_NUM_CONDITIONS3___"
    -> AttributeRenamer
AttributeRenamer
    ATTR_LIST = alder_fra,hoyeste_alder,,alder_til,laveste_alder,,apningstidFra,apningstidfra,,apningstidTil,apningstidtil,,barnehage_id,nbr_id,,ansatte.antallTil,antall_ansatte,,indikatorDataBarnehage.antallBarn,antall_elever,,opprettetDato,oppfortdato,,kommune.kommunenavn,kommunenavn,,besok_postnr,postnummer,,besok_poststed,poststed,,fylke.fylkesnummer,fylkesnr,,kommune.kommunenummer,komm,,pedagogiskProfil,pedagogiskprofil,,urlTilSoknadOmBarnehageplass,webadresse,,overordnetEnhet,organisasjonsnummer,,overordnetEnhet_navn,organisasjonsnavn,
    -> DateFormatter
DateFormatter
    DATE_ATTR = oppfortdato
    SRCFMT = %d/%m/%Y
    INVALID_DATE_VALUE = FME_NULL_VALUE
    FMT = FME Date/Time (%Y%m%d%H%M%S)
    -> StringSearcher_2
StringSearcher_2
    MATCHED_PARTS_ATTR = _matched_parts
    STRING_TO_SEARCH = @Value(besok_postnavn)
    REGEXP = ([0-9])+
    MATCHED_RESULT_ATTR = nummer
    CASE = no
    NOT_MATCHED -> Tester_2
    MATCHED -> Tester_2
Tester_2
    TEST_MODE = Automatic
    BOOL_OP = AND
    TEST_CLAUSE:
      TEST nummer NOT_ATTRIBUTE_VALUE_NULL ""
      TEST nummer NOT_ATTRIBUTE_IS_EMPTY ""
      TEST nummer NOT_ATTRIBUTE_IS_MISSING ""
    TEST_DESCRIPTION = ""
    PASSED -> StringSearcher_3
    FAILED -> StringReplacer_2
StringSearcher_3
    MATCHED_PARTS_ATTR = _matched_parts
    STRING_TO_SEARCH = @Value(besok_postnavn)
    REGEXP = \D{1}$
    MATCHED_RESULT_ATTR = bokstav
    CASE = no
    MATCHED -> AttributeTrimmer_2
    NOT_MATCHED -> AttributeTrimmer_2
AttributeTrimmer_2
    TRIM_CHARS = @Value(bokstav)
    TRIM_TYPE = Right
    SRC_ATTRS = besok_postnavn
    TRIM_TO_NONE = Yes
    -> StringReplacer_2
StringReplacer_2
    NO_MATCH = _FME_NO_OP_
    SRC_ATTRS = besok_postnavn
    REGEXP = no
    FIND_TEXT = @Value(nummer)
    CASE = no
    -> StringCaseChanger
StringCaseChanger
    CHANGE_TYPE = UPPERCASE
    ATTRCHOICE = Selected Attributes
    ATTRLIST = bokstav
    -> AttributeRenamer_4
AttributeRenamer_4
    ATTR_LIST = besok_postnavn,adressenavn,,kontaktinformasjon.epost,epostadresse,,kontaktinformasjon.telefon,telefonnummer,
    -> StringReplacer_3
StringReplacer_3
    NO_MATCH = _FME_NO_OP_
    SRC_ATTRS = telefon
    REGEXP = no
    FIND_TEXT = " "
    CASE = no
    -> NullAttributeMapper_2
NullAttributeMapper_2
    ATTRCHOICE = Selected Attributes
    ATTRLIST = apningstidfra apningstidtil epostadresse pedagogiskprofil telefonnummer
    SOURCE_ATTR_VAL = Null Empty "Missing (Selected Attributes Only)"
    NULL_TREATMENT = Missing
    -> undervisning.barnehage (writer POSTGIS_1)
