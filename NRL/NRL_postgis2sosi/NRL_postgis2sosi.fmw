FME workspace NRL_postgis2sosi.fmw
# Copyright: (c) xgrimor 2015
# Licence: <your licence>
Shutdown Python:
      # -*- coding: utf-8 -*-
      #-------------------------------------------------------------------------------
      # Name:        zipfiles.py
      # Purpose:     Pakker filer i output folderen
      #
      # Author:      xsunknu
      #
      # Created:     18.09.2015
      # Copyright:   (c) xsunknu 2015
      # Licence:     <your licence>
      #-------------------------------------------------------------------------------

      import sys, os, zipfile, fme

      def zip(sosifile, zfile):
          from os.path import basename

          # Lager korresponderende zip-fil av SOSI-fil
          if os.path.isfile(zfile):
              os.remove(zfile)

          zf = zipfile.ZipFile(zfile, "w", zipfile.ZIP_DEFLATED)

          # Ønsker ikke full sti inn i ZIP-filen
          arcname = basename(sosifile)

          # ZIP-formatet støtter ikke non-ascii tegn
          # Erstatter AØÅæøå med ascii-tegn
          arcname = arcname.replace('\xc6', 'E')
          arcname = arcname.replace('\xd8', 'O')
          arcname = arcname.replace('\xc5', 'A')
          arcname = arcname.replace('\xe6', 'e')
          arcname = arcname.replace('\xf8', 'o')
          arcname = arcname.replace('\xe5', 'a')

          zf.write(sosifile, arcname)
          zf.close()
          os.remove(sosifile)

          return

      def main():

          # Kjøres ikke på FME Server, da FME Server selv sørger for pakkingen
          if not 'FME_SERVER_DEST_DIR' in fme.macroValues:
              if 'FANOUT_FOLDER' in fme.macroValues:
                  path = fme.macroValues['FANOUT_FOLDER']
                  for dirpath, dnames, fnames in os.walk(path):
                      for f in fnames:
                          if f.endswith(".sos"):
                              # Scanner gjennom alle SOSI-filer
                              sosifile = os.path.join(path, f)
                              zfile = os.path.splitext(sosifile)[0] + '.zip'
                              if os.path.isfile(zfile):

                                  # Korresponderende ZIP-fil finnes, sjekker timestamps
                                  sositstamp = os.stat(sosifile).st_mtime
                                  ziptstamp = os.stat(zfile).st_mtime

                                  if sositstamp > ziptstamp:
                                      # SOSI-fil er nyere enn ZIP-fila, ZIP-fila oppdateres
                                      # SOSI-fila slettes
                                      try:
                                          zip(sosifile, zfile)
                                      except:
                                          print 'Kunne ikke pakke: ' + sosifile
                                  else:
                                      # SOSI-fila er eldre enn ZIP-fila
                                      # SOSI-fila slettes
                                      try:
                                          os.remove(sosifile)
                                      except:
                                          print 'Kunne ikke slette: ' + sosifile
                              else:
                                  # ZIP-fila eksisterer ikke og lages
                                  # SOSI-fila slettes
                                  try:
                                      zip(sosifile, zfile)
                                  except:
                                      print 'Kunne ikke pakke: ' + sosifile


      if __name__ == '__main__':
          main()

Parameters:
- KNR =   # Kommune(r)
- FNR =   # Fylke(r)
- CLIPPERCOORDS =   # Clipper coordinates
- CLIPPER_EPSG_CODE =   # Clipper coordinate system
- CLIPPER_FILE =   # "" Clipper file (any format)
- OUTPUT_EPSG_CODE = 25833   # Destination coordinate system
- FANOUT =   # Fanout områder
- CONFIG_FILE:   # Python Script
      #-------------------------------------------------------------------------------
      # Name:        GetConfigFile
      # Purpose:
      #
      # Author:      xsunknu
      #
      # Created:     21.08.2015
      # Copyright:   (c) xsunknu 2015
      # Licence:     <your licence>
      #-------------------------------------------------------------------------------
      
      import os, fme
      
      fmwdir = fme.macroValues['FME_MF_DIR']
      fmwfile = fme.macroValues['FME_MF_NAME']
      
      fmwfile = os.path.join(fmwdir, fmwfile)
      configfile = os.path.splitext(fmwfile)[0] + '_config.xml'
      
      return configfile
- PG_DB:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgdb').text
      
      return value
- PG_HOST:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pghost').text
      
      return value
- PG_PORT:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgport').text
      
      return value
- PG_USER:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pguser').text
      
      return value
- PG_PWD:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgpwd').text
      
      return value
- SPATIAL_FILTER:   # Python Script
      #-------------------------------------------------------------------------------
      # Name:        SetSpatialFilter
      # Purpose:
      #
      # Author:      xsunknu
      #
      # Created:     21.08.2015
      # Copyright:   (c) xsunknu 2015
      # Licence:     <your licence>
      #-------------------------------------------------------------------------------
      
      import fme
      
      spatialfilter = 'Intersects'
      
      knr = fme.macroValues['KNR']
      fnr = fme.macroValues['FNR']
      coords = fme.macroValues['CLIPPERCOORDS']
      file = fme.macroValues['CLIPPER_FILE']
      
      if knr == '' and fnr == '' and coords == '' and file == '':
          spatialfilter = '<No Spatial Filter>'
      
      return spatialfilter
- CLIPPERCOORDSYS:   # Python Script
      #-------------------------------------------------------------------------------
      # Name:        SetCoordinateSystem
      # Purpose:
      #
      # Author:      xsunknu
      #
      # Created:     21.08.2015
      # Copyright:   (c) xsunknu 2015
      # Licence:     <your licence>
      #-------------------------------------------------------------------------------
      
      import os, fme
      
      EPSGvalue = fme.macroValues['CLIPPER_EPSG_CODE']
      EPSGcode  = 'EPSG:' + EPSGvalue
      
      return EPSGcode
- FIXEDCLIPPERCOORDS:   # Python Script
      #-------------------------------------------------------------------------------
      # Name:        FixClipperCoords
      # Purpose:
      #
      # Author:      xsunknu
      #
      # Created:     21.08.2015
      # Copyright:   (c) xsunknu 2015
      # Licence:     <your licence>
      #-------------------------------------------------------------------------------
      
      import fme
      clippercoords = fme.macroValues['CLIPPERCOORDS']
      
      if clippercoords == '':
          clippercoords = '1 1'
      
      return clippercoords
- UNDERTEMA = Luftfartshinder   # Undertema
- HOVEDTEMA = Luftfart   # Hovedtema
- DESTCOORDSYS:   # Python Script
      #-------------------------------------------------------------------------------
      # Name:        SetCoordinateSystem
      # Purpose:
      #
      # Author:      xsunknu
      #
      # Created:     21.08.2015
      # Copyright:   (c) xsunknu 2015
      # Licence:     <your licence>
      #-------------------------------------------------------------------------------
      
      import os, fme
      
      EPSGvalue = fme.macroValues['OUTPUT_EPSG_CODE']
      EPSGcode  = 'EPSG:' + EPSGvalue
      
      return EPSGcode
- FANOUT_FOLDER:   # Python Script
      #-------------------------------------------------------------------------------
      # Name:        GetConfigFile
      # Purpose:
      #
      # Author:      xsunknu
      #
      # Created:     21.08.2015
      # Copyright:   (c) xsunknu 2015
      # Licence:     <your licence>
      #-------------------------------------------------------------------------------
      
      import os, fme
      from xml.etree import ElementTree as ET
      
      if 'FME_SERVER_DEST_DIR' in fme.macroValues:
          value = fme.macroValues['FME_SERVER_DEST_DIR']
      else:
          #Read XML config file
          configtree = ET.parse(fme.macroValues['CONFIG_FILE'])
          configdoc = configtree.getroot()
          value = configdoc.find('destdir').text
      
      return value
- LOG_FILE:   # Python Script
      #-------------------------------------------------------------------------------
      # Name:        GetConfigFile
      # Purpose:
      #
      # Author:      xsunknu
      #
      # Created:     21.08.2015
      # Copyright:   (c) xsunknu 2015
      # Licence:     <your licence>
      #-------------------------------------------------------------------------------
      
      import os, uuid, fme
      
      fmwdir = fme.macroValues['FME_MF_DIR']
      fmwfile = fme.macroValues['FME_MF_NAME']
      
      logdir = os.path.join(fmwdir, 'log')
      if not os.path.isdir(logdir):
          os.mkdir(logdir)
      
      logfile = os.path.splitext(fmwfile)[0] + '_' + str(uuid.uuid1()).replace('-','') + '.log'
      logfile = os.path.join(logdir, logfile)
      
      return logfile
- MAPPINGFILE:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme, os
      from xml.etree import ElementTree as ET
      
      #Read XML config file
      configtree = ET.parse(fme.macroValues['CONFIG_FILE'])
      configdoc = configtree.getroot()
      
      value = os.path.join(fme.macroValues['FME_MF_DIR'], configdoc.find('mappingfile').text)
      
      return value
- SOSIDEF_FILE:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme, os
      from xml.etree import ElementTree as ET
      
      #Read XML config file
      configtree = ET.parse(fme.macroValues['CONFIG_FILE'])
      configdoc = configtree.getroot()
      
      value = os.path.join(fme.macroValues['FME_MF_DIR'], configdoc.find('sosideffile').text)
      
      return value

Readers:
- POSTGIS_1: POSTGIS from $(PG_DB)

Writers:
- SOSI_1: SOSI to D:\scratch\Luftfart_25832_Luftfartshinder_SOSI.sos

CreateClipper
    CLIPPERCOORDS = $(FIXEDCLIPPERCOORDS)
    DESTCOORDSYS = $(DESTCOORDSYS)
    CLIPPERCOORDSYS = $(CLIPPERCOORDSYS)
    -> Clipper [input 1]
    -> FeatureReader_3
Note: Må sette DESTCOORDSYS på / tabelldataene som skal ut. Bug i GSP.
CoordinateSystemSetter
    COORDSYS = $(DESTCOORDSYS)
    -> GeometryRemover
Note: Må fjerne den ikke-eksisterende / geometrien også! :-)
GeometryRemover
    -> nrl.vertikalobjekt (writer SOSI_1)

Bookmark: Fylke and/or kommune clippers
Creator_2
    NUM = 1
    GEOMTYPE = Geometry Object
    CREATED -> AttributeCreator_8
AttributeCreator_8
    ATTR_LIST = _clippercoords,$(CLIPPERCOORDS),_clipper_file,$(CLIPPER_FILE),_fnr,$(FNR),_knr,$(KNR)
    -> Tester_4
Note: Sender inn en dummy initiator / dersom alle klippeparametrene er / blanke siden Luftfartshindere / strekker seg utover fastlands- / Norge
Tester_4
    TEST_DESCRIPTION = ""
    BOOL_OP = AND
    TEST_CLAUSE:
      TEST _clipper_file ATTRIBUTE_IS_EMPTY ""
      TEST _clippercoords ATTRIBUTE_IS_EMPTY ""
      TEST _fnr ATTRIBUTE_IS_EMPTY ""
      TEST _knr ATTRIBUTE_IS_EMPTY ""
    TEST_MODE = Automatic
    PASSED -> Reprojector_2
admingrense.fylkeflate (reader POSTGIS_1)
    attributes: fylkeid int4, navn varchar(80)
    -> Tester
Tester
    TEST_DESCRIPTION = ""
    BOOL_OP = OR
    TEST_CLAUSE = TEST @Value(fylkeid) IN $(FNR)
    TEST_MODE = Automatic
    PASSED -> Reprojector_2
admingrense.kommuneflate (reader POSTGIS_1)
    attributes: kommuneid int4, navn varchar(80)
    -> Tester_2
Tester_2
    TEST_DESCRIPTION = ""
    BOOL_OP = OR
    TEST_CLAUSE = TEST @Value(kommuneid) IN $(KNR)
    TEST_MODE = Automatic
    PASSED -> Reprojector_2
Reprojector_2
    SOURCE = Read from feature
    INTERPOLATION_TYPE_NAME = Nearest Neighbor
    DEST = EPSG:4258
    RASTER_CELL_SIZE = Preserve Cells
    REPROJECTED -> Clipper [input 1]
    REPROJECTED -> FeatureReader_3

Bookmark: Clipper file (any format)
Creator
    NUM = 1
    GEOMTYPE = Geometry Object
    CREATED -> FeatureReader
FeatureReader
    INTERACT = $(SPATIAL_FILTER)
    DATASET = $(CLIPPER_FILE)
    GENERIC_REAL_FORMAT = GUESS_FROM_EXTENSION
    ATTR_ACCUM_MODE = Only Use Result
    FEATURETYPES_RADIO = FEATURETYPES
    ATTRIBUTES = NewFeatureType,
    OUTPUT_FEATURES_DISPLAY = Based on Connections
    FORMAT = GENERIC
    COMBINE_GEOM = Use Result
    <OTHER> -> Reprojector_3
Reprojector_3
    SOURCE = Read from feature
    INTERPOLATION_TYPE_NAME = Nearest Neighbor
    DEST = EPSG:4258
    RASTER_CELL_SIZE = Preserve Cells
    REPROJECTED -> Clipper [input 1]
    REPROJECTED -> FeatureReader_3

Bookmark: Leser features og relaterte data
FeatureReader_3
    POSTGIS_SCHEMALIST = nrl
    POSTGIS_PASSWORD = $(PG_PWD)
    FEATURETYPES = nrl.vertikalobjektkomponentlinje nrl.vertikalobjektkomponentpunkt
    FORMAT = POSTGIS
    ATTR_ACCUM_MODE = Only Use Result
    POSTGIS_CLIP_TO_ENVELOPE = NO
    ATTRIBUTES = nrl.vertikalobjektkomponentlinje,"objid,objtype,lengde,lengdeverdienhet,linjespenn,vertikalutstrekning,hoydeverdienhet,merkepliktig,merkepliktigihenholdtil,ansvarligformerking,merkeinformasjon,kommentarmerkeplikt,hrefsystem,href,registernavn,eksternid,mobilitet,komponentsekvnr,bsle21hinder,bestaravvertikalobjektkomponentfk,lokalid,navnerom,versjonid,verifiseringsdato,oppdateringsdato,malemetode,noyaktighet,synbarhet,malemetodehoyde,h_noyaktighet,typeendring,endret_tid,status",nrl.vertikalobjektkomponentpunkt,"objid,objtype,brekkbar,vertikalutstrekning,hoydeverdienhet,merkepliktig,merkepliktigihenholdtil,ansvarligformerking,merkeinformasjon,kommentarmerkeplikt,hrefsystem,href,registernavn,eksternid,mobilitet,komponentsekvnr,bsle21hinder,bestaravvertikalobjektkomponentfk,lokalid,navnerom,versjonid,verifiseringsdato,oppdateringsdato,malemetode,noyaktighet,synbarhet,malemetodehoyde,h_noyaktighet,typeendring,endret_tid,status"
    POSTGIS_QUERY_FEATURE_TYPES_FOR_MERGE_FILTERS = Yes
    POSTGIS_PORT = $(PG_PORT)
    POSTGIS_USE_TRUE_POSTGIS_TYPES = yes
    COMBINE_GEOM = Use Result
    DATASET = $(PG_DB)
    POSTGIS_USE_SEARCH_ENVELOPE = NO
    OUTPUT_FEATURES_DISPLAY = Based on Connections
    POSTGIS_DISABLE_COLLECTION_SPLITTING = yes
    INTERACT = $(SPATIAL_FILTER)
    POSTGIS_HOST = $(PG_HOST)
    POSTGIS_USER_NAME = $(PG_USER)
    FEATURETYPES_RADIO = FEATURETYPES
    nrl.vertikalobjektkomponentlinje -> AttributeCreator_12
    nrl.vertikalobjektkomponentpunkt -> AttributeCreator_12
AttributeCreator_12
    ATTR_LIST = _clippercoords,$(CLIPPERCOORDS),_clipper_file,$(CLIPPER_FILE),_fnr,$(FNR),_knr,$(KNR)
    -> TestFilter
TestFilter
    TEST_LIST:
      BOOL_OP,AND,COMPOSITE_TEST,<Unused>,TEST_CLAUSE,"TEST _clipper_file ATTRIBUTE_IS_EMPTY """"
      TEST _clippercoords ATTRIBUTE_IS_EMPTY """"
      TEST _fnr ATTRIBUTE_IS_EMPTY """"
      TEST _knr ATTRIBUTE_IS_EMPTY """"",Landsdekkende,BOOL_OP,AND,COMPOSITE_TEST,<Unused>,TEST_CLAUSE,"TEST _clipper_file ATTRIBUTE_IS_EMPTY """"
      TEST _clippercoords ATTRIBUTE_IS_EMPTY """"
      TEST _fnr NOT_ATTRIBUTE_IS_EMPTY """"
      TEST _knr ATTRIBUTE_IS_EMPTY """"",Fylkesvis,BOOL_OP,AND,COMPOSITE_TEST,<Unused>,TEST_CLAUSE,"TEST _clipper_file ATTRIBUTE_IS_EMPTY """"
      TEST _clippercoords ATTRIBUTE_IS_EMPTY """"
      TEST _fnr ATTRIBUTE_IS_EMPTY """"
      TEST _knr NOT_ATTRIBUTE_IS_EMPTY """"",Kommunevis
    DEFAULT_VALUE = <UNFILTERED>
    Fylkesvis -> Clipper [input 2]
    Kommunevis -> Clipper [input 2]
    <UNFILTERED> -> Clipper [input 2]
    Landsdekkende -> SosiFilenameSetter
    Landsdekkende -> DuplicateRemover
    Landsdekkende -> DuplicateRemover_2
DuplicateRemover
    KEYATTR = bestaravvertikalobjektkomponentfk
    UNIQUE -> Aggregator_4
Aggregator_4
    ACCUM_ATTRS_NAME = No
    ORDERED = No
    MODE = Attributes Only
    SEP = ,
    CONCAT_ATTRS = bestaravvertikalobjektkomponentfk
    AGGREGATE -> AttributeCreator_9
AttributeCreator_9
    ATTR_LIST = sql,select * from nrl.vertikalobjekt where objid in (@Value(bestaravvertikalobjektkomponentfk));
    -> SQLExecutor
SQLExecutor
    EXPOSED_ATTRIBUTE_LIST = datafangstdato,endret_tid,gyldigfra,gyldigtil,informasjon,kommentarvertobjtype,lokalid,navnerom,objid,objtype,oppdateringsdato,opphav,status,typeendring,versjonid,vertikalobjektgruppe,vertikalobjektnavn,vertikalobjekttype
    POSTGRES_HOST = $(PG_HOST)
    FORMAT = POSTGRES
    COMBINE_GEOM = Initiator Geometry Only
    DATASET = $(PG_DB)
    POSTGRES_PASSWORD = $(PG_PWD)
    SQL_STATEMENT = @Value(sql)
    POSTGRES_PORT = $(PG_PORT)
    COMBINE_ATTRS = Result Attributes Only
    POSTGRES_QUERY_FEATURE_TYPES_FOR_MERGE_FILTERS = Yes
    POSTGRES_USER_NAME = $(PG_USER)
    RESULT -> AttributeCreator_2
DuplicateRemover_2
    KEYATTR = objid
    UNIQUE -> Aggregator_2
Aggregator_2
    ACCUM_ATTRS_NAME = No
    ORDERED = No
    MODE = Attributes Only
    SEP = ,
    CONCAT_ATTRS = objid
    AGGREGATE -> AttributeCreator_10
    AGGREGATE -> AttributeCreator_11
AttributeCreator_10
    ATTR_LIST = sql,select * from nrl.lyssetting where harlyssettingfk in (@Value(objid));
    -> SQLExecutor_2
SQLExecutor_2
    EXPOSED_ATTRIBUTE_LIST = harlyssettingfk,lystype,objid,versjonid
    POSTGRES_HOST = $(PG_HOST)
    FORMAT = POSTGRES
    COMBINE_GEOM = Initiator Geometry Only
    DATASET = $(PG_DB)
    POSTGRES_PASSWORD = $(PG_PWD)
    SQL_STATEMENT = @Value(sql)
    POSTGRES_PORT = $(PG_PORT)
    COMBINE_ATTRS = Result Attributes Only
    POSTGRES_QUERY_FEATURE_TYPES_FOR_MERGE_FILTERS = Yes
    POSTGRES_USER_NAME = $(PG_USER)
    RESULT -> AttributeCreator_5
AttributeCreator_11
    ATTR_LIST = sql,select * from nrl.merking where harmerkingfk in (@Value(objid));
    -> SQLExecutor_3
SQLExecutor_3
    EXPOSED_ATTRIBUTE_LIST = annet1,annet2,fluoriserende1,fluoriserende2,harmerkingfk,kommentarmerkingmonster,kommentarmerkingtype,merkingfarge1,merkingfarge2,merkingicao,merkingmonster,merkingtilstand,merkingtype,objid,reflekterende1,reflekterende2,versjonid
    POSTGRES_HOST = $(PG_HOST)
    FORMAT = POSTGRES
    COMBINE_GEOM = Initiator Geometry Only
    DATASET = $(PG_DB)
    POSTGRES_PASSWORD = $(PG_PWD)
    SQL_STATEMENT = @Value(sql)
    POSTGRES_PORT = $(PG_PORT)
    COMBINE_ATTRS = Result Attributes Only
    POSTGRES_QUERY_FEATURE_TYPES_FOR_MERGE_FILTERS = Yes
    POSTGRES_USER_NAME = $(PG_USER)
    RESULT -> AttributeCreator_7

Bookmark: Klipper
Clipper
    ATTR_CONFLICT_RES = Use Clippee
    CLIPPED_ATTR = _clipped
    CREATE_AGGREGATES = No
    BOUNDARY_CASES = Treat as Inside
    ATTR_ACCUM_MODE = Merge Clipper
    CLIP_TYPE = Multiple Clippers
    PRESERVE_CLIPPEE_EXTENTS = No
    INSIDE -> DuplicateRemover
    INSIDE -> DuplicateRemover_2
    INSIDE -> SosiFilenameSetter

Bookmark: Tagger og reprojiserer
SosiFilenameSetter
    OBJTYPE = @Value(objtype)
    FYLKEID = @Value(fylkeid)
    VERTIKALUTSTREKNING = @Value(vertikalutstrekning)
    LINJESPENN = @Value(linjespenn)
    VERIFISERINGSDATO = @Value(verifiseringsdato)
    BREKKBAR = @Value(brekkbar)
    BESTARAVVERTIKALOBJEKTKOMPONENTFK = @Value(bestaravvertikalobjektkomponentfk)
    KOMMUNEID = @Value(kommuneid)
    _KNR = @Value(_knr)
    KOMMENTARMERKEPLIKT = @Value(kommentarmerkeplikt)
    STATUS = @Value(status)
    SYNBARHET = @Value(synbarhet)
    MERKEPLIKTIGIHENHOLDTIL = @Value(merkepliktigihenholdtil)
    UNDERTEMA = $(UNDERTEMA)
    HOVEDTEMA = $(HOVEDTEMA)
    LENGDE = @Value(lengde)
    KOMPONENTSEKVNR = @Value(komponentsekvnr)
    NOYAKTIGHET = @Value(noyaktighet)
    ANSVARLIGFORMERKING = @Value(ansvarligformerking)
    PG_PORT:
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------

      import fme
      from xml.etree import ElementTree as ET

      #Read XML config file
      configtree = ET.parse(fme.macroValues['CONFIG_FILE'])
      configdoc = configtree.getroot()
      value = configdoc.find('pgport').text

      return value
    _CREATION_INSTANCE = @Value(_creation_instance)
    OUTPUT_EPSG_CODE = $(OUTPUT_EPSG_CODE)
    MERKEINFORMASJON = @Value(merkeinformasjon)
    _CLIPPED = @Value(_clipped)
    _FNR = @Value(_fnr)
    NAVN = @Value(navn)
    HREF = @Value(href)
    _CLIPPER_FILE = @Value(_clipper_file)
    H_NOYAKTIGHET = @Value(h_noyaktighet)
    HOYDEVERDIENHET = @Value(hoydeverdienhet)
    OPPDATERINGSDATO = @Value(oppdateringsdato)
    HREFSYSTEM = @Value(hrefsystem)
    LOKALID = @Value(lokalid)
    PG_DB:
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------

      import fme
      from xml.etree import ElementTree as ET

      #Read XML config file
      configtree = ET.parse(fme.macroValues['CONFIG_FILE'])
      configdoc = configtree.getroot()
      value = configdoc.find('pgdb').text

      return value
    BSLE21HINDER = @Value(bsle21hinder)
    OBJID = @Value(objid)
    MALEMETODE = @Value(malemetode)
    PG_HOST:
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------

      import fme
      from xml.etree import ElementTree as ET

      #Read XML config file
      configtree = ET.parse(fme.macroValues['CONFIG_FILE'])
      configdoc = configtree.getroot()
      value = configdoc.find('pghost').text

      return value
    _CLIPPERCOORDS = @Value(_clippercoords)
    MOBILITET = @Value(mobilitet)
    MALEMETODEHOYDE = @Value(malemetodehoyde)
    TYPEENDRING = @Value(typeendring)
    MERKEPLIKTIG = @Value(merkepliktig)
    REGISTERNAVN = @Value(registernavn)
    NAVNEROM = @Value(navnerom)
    ENDRET_TID = @Value(endret_tid)
    PG_PWD:
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------

      import fme
      from xml.etree import ElementTree as ET

      #Read XML config file
      configtree = ET.parse(fme.macroValues['CONFIG_FILE'])
      configdoc = configtree.getroot()
      value = configdoc.find('pgpwd').text

      return value
    VERSJONID = @Value(versjonid)
    EKSTERNID = @Value(eksternid)
    PG_USER:
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------

      import fme
      from xml.etree import ElementTree as ET

      #Read XML config file
      configtree = ET.parse(fme.macroValues['CONFIG_FILE'])
      configdoc = configtree.getroot()
      value = configdoc.find('pguser').text

      return value
    LENGDEVERDIENHET = @Value(lengdeverdienhet)
    FANOUT = $(FANOUT)
    -> AttributeCreator_3
    -> Reprojector
Reprojector
    SOURCE = Read from feature
    INTERPOLATION_TYPE_NAME = Nearest Neighbor
    DEST = $(DESTCOORDSYS)
    RASTER_CELL_SIZE = Preserve Cells
    REPROJECTED -> AttributeCreator
AttributeCreator
    ATTR_LIST = OBJTYPE,@Value(objtype),linjespenn,"FME_CONDITIONAL:DEFAULT_VALUE'FME_NULL_VALUE'BOOL_OP;OR;COMPOSITE_TEST;<Unused>;TEST @Value(linjespenn) = t'1'BOOL_OP;OR;COMPOSITE_TEST;<Unused>;TEST @Value(linjespenn) = f'0'FME_NUM_CONDITIONS3___",mobilitet,"FME_CONDITIONAL:DEFAULT_VALUE'FME_NULL_VALUE'BOOL_OP;OR;COMPOSITE_TEST;<Unused>;TEST @Value(mobilitet) = t'1'BOOL_OP;OR;COMPOSITE_TEST;<Unused>;TEST @Value(mobilitet) = f'0'FME_NUM_CONDITIONS3___",bsle21hinder,"FME_CONDITIONAL:DEFAULT_VALUE'FME_NULL_VALUE'BOOL_OP;OR;COMPOSITE_TEST;<Unused>;TEST @Value(bsle21hinder) = t'1'BOOL_OP;OR;COMPOSITE_TEST;<Unused>;TEST @Value(bsle21hinder) = f'0'FME_NUM_CONDITIONS3___",lokalid,@Value(objid),navnerom,NO.KARTVERKET.NRL
    -> FeatureTypeFilter
FeatureTypeFilter
    ATTRIBUTES = nrl.vertikalobjektkomponentpunkt,nrl.vertikalobjektkomponentlinje,<BLANK>,<UNFILTERED>
    nrl.vertikalobjektkomponentlinje -> SpatialRelator [input 1]
    nrl.vertikalobjektkomponentpunkt -> AttributeCreator_4
    nrl.vertikalobjektkomponentpunkt -> SpatialRelator_2 [input 1]
    nrl.vertikalobjektkomponentlinje -> AttributeCreator_6

Bookmark: Topologiske relasjoner
AttributeCreator_6
    ATTR_LIST = lokalid,@Value(objid),navnerom,NO.KARTVERKET.NRL
    -> AttributeRemover_3
AttributeRemover_3
    REMOVE_ATTRS = ansvarligformerking,bestaravvertikalobjektkomponentfk,brekkbar,bsle21hinder,eksternid,endret_tid,h_noyaktighet,hoydeverdienhet,href,hrefsystem,kommentarmerkeplikt,komponentsekvnr,lengde,lengdeverdienhet,linjespenn,malemetode,malemetodehoyde,merkeinformasjon,merkepliktig,merkepliktigihenholdtil,mobilitet,noyaktighet,objid,objtype,OBJTYPE,oppdateringsdato,registernavn,status,synbarhet,typeendring,verifiseringsdato,vertikalutstrekning
    -> SpatialRelator_2 [input 2]
SpatialRelator_2
    LIST_NAME = L:avgrenserlinje
    CURVE_BOUNDARY_RULE_PARAM = Default Rule
    CALC_CARD = No
    SUCCESS_ATTR = _related_candidates
    PREDICATES = TOUCHES
    -> FeatureMerger_3 [input 1]
AttributeCreator_4
    ATTR_LIST = lokalid,@Value(objid),navnerom,NO.KARTVERKET.NRL
    -> AttributeRemover_2
AttributeRemover_2
    REMOVE_ATTRS = ansvarligformerking,bestaravvertikalobjektkomponentfk,brekkbar,bsle21hinder,eksternid,endret_tid,h_noyaktighet,hoydeverdienhet,href,hrefsystem,kommentarmerkeplikt,komponentsekvnr,lengde,lengdeverdienhet,linjespenn,malemetode,malemetodehoyde,merkeinformasjon,merkepliktig,merkepliktigihenholdtil,mobilitet,noyaktighet,objid,objtype,OBJTYPE,oppdateringsdato,registernavn,status,synbarhet,typeendring,verifiseringsdato,vertikalutstrekning
    -> SpatialRelator [input 2]
SpatialRelator
    LIST_NAME = L:avgrensesav
    CURVE_BOUNDARY_RULE_PARAM = Default Rule
    CALC_CARD = No
    SUCCESS_ATTR = _related_candidates
    PREDICATES = TOUCHES
    -> FeatureMerger_2 [input 1]

Bookmark: Bygger vertikalobjekter
AttributeCreator_3
    ATTR_LIST = lokalid,@Value(objid),navnerom,NO.KARTVERKET.NRL
    -> AttributeRemover
AttributeRemover
    REMOVE_ATTRS = ansvarligformerking,brekkbar,bsle21hinder,eksternid,endret_tid,h_noyaktighet,hoydeverdienhet,href,hrefsystem,kommentarmerkeplikt,komponentsekvnr,lengde,lengdeverdienhet,linjespenn,malemetode,malemetodehoyde,merkeinformasjon,merkepliktig,merkepliktigihenholdtil,mobilitet,noyaktighet,objid,objtype,oppdateringsdato,registernavn,status,synbarhet,typeendring,verifiseringsdato,vertikalutstrekning
    -> FeatureMerger [input 2]
AttributeCreator_2
    ATTR_LIST = OBJTYPE,@Value(objtype),vertikalobjektgruppe,"FME_CONDITIONAL:DEFAULT_VALUE'FME_NULL_VALUE'BOOL_OP;OR;COMPOSITE_TEST;<Unused>;TEST @Value(vertikalobjektgruppe) = t'1'BOOL_OP;OR;COMPOSITE_TEST;<Unused>;TEST @Value(vertikalobjektgruppe) = f'0'FME_NUM_CONDITIONS3___",lokalid,@Value(objid),navnerom,NRL.KARTVERKET.NRL
    -> FeatureMerger [input 1]
FeatureMerger
    ATTR_ACCUM_MODE = Merge Supplier
    PROCESS_DUPS = No
    MERGE_TYPE = Attributes Only
    LIST_NAME = L:komponenter
    ATTR_CONFLICT_RES = Use Requestor
    SUPPLIERS_FIRST = No
    IGNORE_NULLS = No
    JOIN_KEYS = @Value(objid) @Value(bestaravvertikalobjektkomponentfk) AUTO
    MERGED -> CoordinateSystemSetter

Bookmark: SOSI Output
nrl.vertikalobjekt (writer SOSI_1)
    attributes: objtype SOSI_varchar(80), kommentarvertobjtype SOSI_varchar(255), vertikalobjektgruppe SOSI_boolean, vertikalobjektnavn SOSI_varchar(80), vertikalobjekttype SOSI_varchar(80), L:komponenter{}.lokalid SOSI_varchar(80), L:komponenter{}.navnerom SOSI_varchar(80), L:komponenter{}.versjonid SOSI_varchar(80), datafangstdato SOSI_datetime, typeendring SOSI_varchar(80), endret_tid SOSI_datetime, gyldigfra SOSI_datetime, gyldigtil SOSI_datetime, lokalid SOSI_buffer, navnerom SOSI_varchar(80), versjonid SOSI_varchar(80), informasjon SOSI_varchar(255), link SOSI_varchar(255), oppdateringsdato SOSI_datetime, opphav SOSI_varchar(255), status SOSI_varchar(80)
nrl.vertikalobjektkomponentpunkt (writer SOSI_1)
    attributes: objtype SOSI_varchar(80), brekkbar SOSI_boolean, L:avgrenserlinje{}.lokalid SOSI_varchar(80), L:avgrenserlinje{}.navnerom SOSI_varchar(80), L:avgrenserlinje{}.versjonid SOSI_varchar(80), vertikalutstrekning SOSI_real64, hoydeverdienhet SOSI_varchar(80), merkepliktig SOSI_varchar(80), merkepliktigihenholdtil SOSI_varchar(80), ansvarligformerking SOSI_varchar(80), merkeinformasjon SOSI_varchar(80), kommentarmerkeplikt SOSI_varchar(80), hrefsystem SOSI_varchar(80), href SOSI_varchar(80), registernavn SOSI_varchar(80), eksternid SOSI_varchar(80), mobilitet SOSI_boolean, komponentsekvnr SOSI_int32, bsle21hinder SOSI_boolean, bestaravvertikalobjektkomponentfk SOSI_int32, lokalid SOSI_buffer, navnerom SOSI_varchar(80), versjonid SOSI_varchar(80), verifiseringsdato SOSI_datetime, oppdateringsdato SOSI_datetime, malemetode SOSI_varchar(80), noyaktighet SOSI_int32, synbarhet SOSI_varchar(80), malemetodehoyde SOSI_varchar(80), h_noyaktighet SOSI_int32,
      typeendring SOSI_varchar(80), endret_tid SOSI_datetime, status SOSI_varchar(80), L:merking{}.lokalid SOSI_varchar(80), L:merking{}.navnerom SOSI_varchar(80), L:merking{}.versjonid SOSI_varchar(80), L:merking{}.merkingmonster SOSI_varchar(255), L:merking{}.kommentarmerkingmonster SOSI_varchar(255), L:merking{}.merkingtype SOSI_varchar(255), L:merking{}.kommentarmerkingtype SOSI_varchar(255), L:merking{}.merkingicao SOSI_int16, L:merking{}.merkingtilstand SOSI_varchar(255), L:merking{}.merkingfarge1 SOSI_varchar(255), L:merking{}.annet1 SOSI_varchar(255), L:merking{}.fluoriserende1 SOSI_int16, L:merking{}.reflekterende1 SOSI_int16, L:merking{}.merkingfarge2 SOSI_varchar(255), L:merking{}.annet2 SOSI_varchar(255), L:merking{}.fluoriserende2 SOSI_int16, L:merking{}.reflekterende2 SOSI_int16
nrl.vertikalobjektkomponentlinje (writer SOSI_1)
    attributes: objtype SOSI_varchar(80), lengde SOSI_real64, lengdeverdienhet SOSI_varchar(80), linjespenn SOSI_boolean, L:avgrensesav{}.lokalid SOSI_varchar(80), L:avgrensesav{}.navnerom SOSI_varchar(80), L:avgrensesav{}.versjonid SOSI_varchar(80), L:merking{}.lokalid SOSI_varchar(80), L:merking{}.navnerom SOSI_varchar(80), L:merking{}.merkingmonster SOSI_varchar(255), L:merking{}.kommentarmerkingmonster SOSI_varchar(255), L:merking{}.merkingtype SOSI_varchar(255), L:merking{}.kommentarmerkingtype SOSI_varchar(255), L:merking{}.merkingicao SOSI_int16, L:merking{}.merkingtilstand SOSI_varchar(255), L:merking{}.merkingfarge1 SOSI_varchar(255), L:merking{}.annet1 SOSI_varchar(255), L:merking{}.fluoriserende1 SOSI_int16, L:merking{}.reflekterende1 SOSI_int16, L:merking{}.merkingfarge2 SOSI_varchar(255), L:merking{}.annet2 SOSI_varchar(255), L:merking{}.fluoriserende2 SOSI_int16, L:merking{}.reflekterende2 SOSI_int16, vertikalutstrekning SOSI_real64, hoydeverdienhet SOSI_varchar(80), merkepliktig SOSI_varchar(80), merkepliktigihenholdtil SOSI_varchar(80), ansvarligformerking SOSI_varchar(80), merkeinformasjon SOSI_varchar(80), kommentarmerkeplikt SOSI_varchar(80),
      hrefsystem SOSI_varchar(80), href SOSI_varchar(80), registernavn SOSI_varchar(80), eksternid SOSI_varchar(80), mobilitet SOSI_boolean, komponentsekvnr SOSI_int32, bsle21hinder SOSI_boolean, L:lyssetting{}.lystype SOSI_varchar(80), L:lyssetting{}.navnerom SOSI_varchar(80), L:lyssetting{}.versjonid SOSI_varchar(80), bestaravvertikalobjektkomponentfk SOSI_int32, lokalid SOSI_buffer, navnerom SOSI_varchar(80), versjonid SOSI_varchar(80), verifiseringsdato SOSI_datetime, oppdateringsdato SOSI_datetime, malemetode SOSI_varchar(80), noyaktighet SOSI_int32, synbarhet SOSI_varchar(80), malemetodehoyde SOSI_varchar(80), h_noyaktighet SOSI_int32, typeendring SOSI_varchar(80), endret_tid SOSI_datetime, status SOSI_varchar(80)

Bookmark: Setter standardattributter
AttributeCreator_5
    ATTR_LIST = lokalid,@Value(objid),navnerom,NO.KARTVERKET.NRL
    -> FeatureMerger_2 [input 2]
    -> FeatureMerger_3 [input 2]
AttributeCreator_7
    ATTR_LIST = lokalid,@Value(objid),navnerom,NO.KARTVERKET.NRL
    -> FeatureMerger_4 [input 2]
    -> FeatureMerger_5 [input 2]

Bookmark: Lyssetting
FeatureMerger_3
    ATTR_ACCUM_MODE = Merge Supplier
    PROCESS_DUPS = No
    MERGE_TYPE = Attributes Only
    LIST_NAME = L:lyssetting
    ATTR_CONFLICT_RES = Use Requestor
    SUPPLIERS_FIRST = No
    IGNORE_NULLS = No
    JOIN_KEYS = @Value(objid) @Value(harlyssettingfk) AUTO
    MERGED -> FeatureMerger_5 [input 1]
    NOT_MERGED -> FeatureMerger_5 [input 1]
FeatureMerger_2
    ATTR_ACCUM_MODE = Merge Supplier
    PROCESS_DUPS = No
    MERGE_TYPE = Attributes Only
    LIST_NAME = L:lyssetting
    ATTR_CONFLICT_RES = Use Requestor
    SUPPLIERS_FIRST = No
    IGNORE_NULLS = No
    JOIN_KEYS = @Value(objid) @Value(harlyssettingfk) AUTO
    MERGED -> FeatureMerger_4 [input 1]
    NOT_MERGED -> FeatureMerger_4 [input 1]

Bookmark: Merking
FeatureMerger_5
    ATTR_ACCUM_MODE = Merge Supplier
    PROCESS_DUPS = No
    MERGE_TYPE = Attributes Only
    LIST_NAME = L:merking
    ATTR_CONFLICT_RES = Use Requestor
    SUPPLIERS_FIRST = No
    IGNORE_NULLS = No
    JOIN_KEYS = @Value(objid) @Value(harmerkingfk) AUTO
    MERGED -> nrl.vertikalobjektkomponentpunkt (writer SOSI_1)
    NOT_MERGED -> nrl.vertikalobjektkomponentpunkt (writer SOSI_1)
FeatureMerger_4
    ATTR_ACCUM_MODE = Merge Supplier
    PROCESS_DUPS = No
    MERGE_TYPE = Attributes Only
    LIST_NAME = L:merking
    ATTR_CONFLICT_RES = Use Requestor
    SUPPLIERS_FIRST = No
    IGNORE_NULLS = No
    JOIN_KEYS = @Value(objid) @Value(harmerkingfk) AUTO
    NOT_MERGED -> nrl.vertikalobjektkomponentlinje (writer SOSI_1)
    MERGED -> nrl.vertikalobjektkomponentlinje (writer SOSI_1)

FME custom transformer CreateClipper

Parameters:
- CLIPPERCOORDS = 253577 6650999 253577 6651246 253763 6651246 253763 6650999 253577 6650999   # Clipper Coordinate List
- CLIPPERCOORDSYS = EPSG:25833   # Clipper Coordinate System
- DESTCOORDSYS = "ESRIWKT|ETRS_1989_UTM_Zone_35N|PROJCS["ETRS_1989_UTM_Zone_35N",GEOGCS["GCS_ETRS_1989",DATUM["D_ETRS_1989",SPHEROID["GRS_1980",6378137.0,298.257222101]],PRIMEM["Greenwich",0.0],UNIT["Degree",0.0174532925199433]],PROJECTION["Transverse_Mercator"],PARAMETER["False_Easting",500000.0],PARAMETER["False_Northing",0.0],PARAMETER["Central_Meridian",27.0],PARAMETER["Scale_Factor",0.9996],PARAMETER["Latitude_Of_Origin",0.0],UNIT["Meter",1.0]]"   # Destination Coordinate System

Note: Creating geometry from / the Clipper coords
Creator
    COORDS = $(CLIPPERCOORDS)
    NUM = 1
    GEOMTYPE = 2D Coordinate List
    COORDSYS = $(CLIPPERCOORDSYS)
    CREATED -> BoundingBoxAccumulator
Note: Calculating the bounding / box (envelope) from the geometry
BoundingBoxAccumulator
    TOPFER_INDEX = No
    BOUNDING_BOX -> SpatialFilter [input 1]
    ORIGINAL -> SpatialFilter [input 2]
Note: If the geometry is equal to its / own bounding box - it is a rectangle!
SpatialFilter
    PREDATTR = _predicate
    CURVE_BOUNDARY_RULE_PARAM = Default Rule
    USE_BOUNDING_BOX = No
    MERGE_ATTRS = No
    BASE_TYPE = Single Base
    PREDICATES = EQUALS
    PASS_CRITERIA = Pass Against One Base
    PASSED -> Reprojector
    FAILED -> Reprojector_2
Note: If rectangle, reproject the / geometry to the destination / coordinate system
Reprojector
    SOURCE = Read from feature
    INTERPOLATION_TYPE_NAME = Nearest Neighbor
    STROKE_ARCS = Yes
    DEST = $(DESTCOORDSYS)
    RASTER_CELL_SIZE = Preserve Cells
    REPROJECTED -> BoundingBoxAccumulator_2
Note: Then calculate the bounding / box from the projected geoemtry
BoundingBoxAccumulator_2
    TOPFER_INDEX = No
    BOUNDING_BOX -> Reprojector_3
Note: Reproject the geometry back to / the DB coordsys (LL/EUREF89)
Reprojector_3
    SOURCE = Read from feature
    INTERPOLATION_TYPE_NAME = Nearest Neighbor
    STROKE_ARCS = Yes
    DEST = EPSG:4258
    RASTER_CELL_SIZE = Preserve Cells
    REPROJECTED -> GeometryFilter
Note: Reproject clipper to / the DB coordsys (LL/EUREF89)
Reprojector_2
    SOURCE = Read from feature
    INTERPOLATION_TYPE_NAME = Nearest Neighbor
    STROKE_ARCS = Yes
    DEST = EPSG:4258
    RASTER_CELL_SIZE = Preserve Cells
    REPROJECTED -> GeometryFilter
Note: Getting rid of dummies
GeometryFilter
    BREAK_AGG = No
    GEOM_PORT_NAMES = Area
    AREA -> Output (output)
Output (output)

FME custom transformer SosiFilenameSetter

Parameters:
- OUTPUT_EPSG_CODE = 25832   # Destination coordinate system
- FANOUT = Kommuner   # Fanout områder
- _CLIPPED = @Value(_clipped)   # Clipped
- _CLIPPER_FILE = @Value(_clipper_file)   # Clipper File
- _CLIPPERCOORDS = @Value(_clippercoords)   # Clippercoords
- _CREATION_INSTANCE = @Value(_creation_instance)   # Creation Instance
- _FNR = @Value(_fnr)   # Fnr
- _KNR = @Value(_knr)   # Knr
- ANSVARLIGFORMERKING = @Value(ansvarligformerking)   # ansvarligformerking
- BESTARAVVERTIKALOBJEKTKOMPONENTFK = @Value(bestaravvertikalobjektkomponentfk)   # bestaravvertikalobjektkomponentfk
- BREKKBAR = @Value(brekkbar)   # brekkbar
- BSLE21HINDER = @Value(bsle21hinder)   # bsle21hinder
- EKSTERNID = @Value(eksternid)   # eksternid
- ENDRET_TID = @Value(endret_tid)   # Endret Tid
- FYLKEID = @Value(fylkeid)   # fylkeid
- H_NOYAKTIGHET = @Value(h_noyaktighet)   # H Noyaktighet
- HOYDEVERDIENHET = @Value(hoydeverdienhet)   # hoydeverdienhet
- HREF = @Value(href)   # href
- HREFSYSTEM = @Value(hrefsystem)   # hrefsystem
- KOMMENTARMERKEPLIKT = @Value(kommentarmerkeplikt)   # kommentarmerkeplikt
- KOMMUNEID = @Value(kommuneid)   # kommuneid
- KOMPONENTSEKVNR = @Value(komponentsekvnr)   # komponentsekvnr
- LENGDE = @Value(lengde)   # lengde
- LENGDEVERDIENHET = @Value(lengdeverdienhet)   # lengdeverdienhet
- LINJESPENN = @Value(linjespenn)   # linjespenn
- LOKALID = @Value(lokalid)   # lokalid
- MALEMETODE = @Value(malemetode)   # malemetode
- MALEMETODEHOYDE = @Value(malemetodehoyde)   # malemetodehoyde
- MERKEINFORMASJON = @Value(merkeinformasjon)   # merkeinformasjon
- MERKEPLIKTIG = @Value(merkepliktig)   # merkepliktig
- MERKEPLIKTIGIHENHOLDTIL = @Value(merkepliktigihenholdtil)   # merkepliktigihenholdtil
- MOBILITET = @Value(mobilitet)   # mobilitet
- NAVN = @Value(navn)   # navn
- NAVNEROM = @Value(navnerom)   # navnerom
- NOYAKTIGHET = @Value(noyaktighet)   # noyaktighet
- OBJID = @Value(objid)   # objid
- OBJTYPE = @Value(objtype)   # objtype
- OPPDATERINGSDATO = @Value(oppdateringsdato)   # oppdateringsdato
- REGISTERNAVN = @Value(registernavn)   # registernavn
- STATUS = @Value(status)   # status
- SYNBARHET = @Value(synbarhet)   # synbarhet
- TYPEENDRING = @Value(typeendring)   # typeendring
- VERIFISERINGSDATO = @Value(verifiseringsdato)   # verifiseringsdato
- VERSJONID = @Value(versjonid)   # versjonid
- VERTIKALUTSTREKNING = @Value(vertikalutstrekning)   # vertikalutstrekning
- UNDERTEMA =   # Undertema
- HOVEDTEMA =   # Hovedtema
- PG_DB:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgdb').text
      
      return value
- PG_HOST:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pghost').text
      
      return value
- PG_PORT:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgport').text
      
      return value
- PG_PWD:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgpwd').text
      
      return value
- PG_USER:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pguser').text
      
      return value

Input (input)
    -> ParameterFetcher
ParameterFetcher
    ATTR_LIST = _output_epsg_code {$(OUTPUT_EPSG_CODE)} _fanout {$(FANOUT)}
    -> AttributeValueMapper
Note: Fikser kjente feil i kommunenummer
AttributeValueMapper
    LUT = 1901,1903
    DEFAULT_VALUE = @Value(kommuneid)
    VAL_ATTR = kommuneid
    SRC = kommuneid
    DIRECTION = Forward (Source To Destination)
    -> TestFilter_2
TestFilter_2
    TEST_LIST = BOOL_OP,OR,COMPOSITE_TEST,<Unused>,TEST_CLAUSE,"TEST $(FANOUT) = Kommuner",Kommuner,BOOL_OP,OR,COMPOSITE_TEST,<Unused>,TEST_CLAUSE,"TEST $(FANOUT) = Fylker",Fylker
    DEFAULT_VALUE = Ufiltrert
    Kommuner -> Joiner
    Ufiltrert -> AttributeCreator_13
    Fylker -> Joiner_2
Joiner
    TABLE = admingrense.kommuner
    DATASET = $(PG_DB)
    POSTGIS_PASSWORD = $(PG_PWD)
    CACHE_SIZE = 5000
    PREFETCH_EXHAUSTIVE = Yes
    POSTGIS_QUERY_FEATURE_TYPES_FOR_MERGE_FILTERS = Yes
    MATCH_RULE_DISPLAY = Must Match Exactly One (1:1)
    POSTGIS_HOST = $(PG_HOST)
    ADDED_FIELDS = navn
    POSTGIS_USER_NAME = $(PG_USER)
    FORMAT = POSTGIS
    POSTGIS_USE_TRUE_POSTGIS_TYPES = yes
    POSTGIS_DISABLE_COLLECTION_SPLITTING = yes
    JOIN_KEYS = kommuneid kommuneid
    POSTGIS_PORT = $(PG_PORT)
    JOINED -> StringReplacer_2
Joiner_2
    TABLE = admingrense.fylkeflate
    DATASET = $(PG_DB)
    POSTGIS_PASSWORD = $(PG_PWD)
    CACHE_SIZE = 5000
    PREFETCH_EXHAUSTIVE = Yes
    POSTGIS_QUERY_FEATURE_TYPES_FOR_MERGE_FILTERS = Yes
    MATCH_RULE_DISPLAY = Must Match Exactly One (1:1)
    POSTGIS_HOST = $(PG_HOST)
    ADDED_FIELDS = navn
    POSTGIS_USER_NAME = $(PG_USER)
    FORMAT = POSTGIS
    POSTGIS_USE_TRUE_POSTGIS_TYPES = yes
    POSTGIS_DISABLE_COLLECTION_SPLITTING = yes
    JOIN_KEYS = fylkeid fylkeid
    POSTGIS_PORT = $(PG_PORT)
    JOINED -> StringReplacer_2
AttributeCreator_13
    ATTR_LIST = sosifile,"FME_CONDITIONAL:DEFAULT_VALUE'$(HOVEDTEMA)_$(OUTPUT_EPSG_CODE)_$(UNDERTEMA)_SOSI'BOOL_OP;OR;COMPOSITE_TEST;<Unused>;TEST $(FANOUT) LIKE Kommuner'$(HOVEDTEMA)_@PadLeft(@Value(kommuneid),4,0)_@Value(navn)_$(OUTPUT_EPSG_CODE)_$(UNDERTEMA)_SOSI'BOOL_OP;OR;COMPOSITE_TEST;<Unused>;TEST $(FANOUT) LIKE Fylker'$(HOVEDTEMA)_@PadLeft(@Value(fylkeid),2,0)_@Value(navn)_$(OUTPUT_EPSG_CODE)_$(UNDERTEMA)_SOSI'BOOL_OP;OR;COMPOSITE_TEST;<Unused>;TEST $(FANOUT) LIKE Norge'$(HOVEDTEMA)_Norge_$(OUTPUT_EPSG_CODE)_$(UNDERTEMA)_SOSI'FME_NUM_CONDITIONS4___"
    -> Output (output)
Output (output)

Bookmark: Substituerer ÆØÅ og mellomrom
StringReplacer_2
    REGEXP = no
    CASE = no
    NO_MATCH = _FME_NO_OP_
    FIND_TEXT = " "
    REPLACE_TEXT = _
    SRC_ATTRS = navn
    -> StringReplacer_3
StringReplacer_3
    REGEXP = no
    CASE = yes
    NO_MATCH = _FME_NO_OP_
    FIND_TEXT = Æ
    REPLACE_TEXT = E
    SRC_ATTRS = navn
    -> StringReplacer_4
StringReplacer_4
    REGEXP = no
    CASE = yes
    NO_MATCH = _FME_NO_OP_
    FIND_TEXT = Ø
    REPLACE_TEXT = O
    SRC_ATTRS = navn
    -> StringReplacer_5
StringReplacer_5
    REGEXP = no
    CASE = yes
    NO_MATCH = _FME_NO_OP_
    FIND_TEXT = Å
    REPLACE_TEXT = A
    SRC_ATTRS = navn
    -> StringReplacer_6
StringReplacer_6
    REGEXP = no
    CASE = yes
    NO_MATCH = _FME_NO_OP_
    FIND_TEXT = æ
    REPLACE_TEXT = e
    SRC_ATTRS = navn
    -> StringReplacer_7
StringReplacer_7
    REGEXP = no
    CASE = yes
    NO_MATCH = _FME_NO_OP_
    FIND_TEXT = ø
    REPLACE_TEXT = o
    SRC_ATTRS = navn
    -> StringReplacer_8
StringReplacer_8
    REGEXP = no
    CASE = yes
    NO_MATCH = _FME_NO_OP_
    FIND_TEXT = å
    REPLACE_TEXT = a
    SRC_ATTRS = navn
    -> AttributeCreator_13
