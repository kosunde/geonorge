FME workspace NRL_postgis2postgis.fmw

Parameters:
- CONFIG_FILE:   # Python Script
      #-------------------------------------------------------------------------------
      # Name:        GetConfigFile
      # Purpose:
      #
      # Author:      xsunknu
      #
      # Created:     21.08.2015
      # Copyright:   (c) xsunknu 2015
      # Licence:     <your licence>
      #-------------------------------------------------------------------------------
      
      import os, fme
      
      fmwdir = fme.macroValues['FME_MF_DIR']
      fmwfile = fme.macroValues['FME_MF_NAME']
      
      fmwfile = os.path.join(fmwdir, fmwfile)
      configfile = os.path.splitext(fmwfile)[0] + '_config.xml'
      
      return configfile
- PG_INPUT_DB:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pginputdb').text
      
      return value
- DB_SR = EPSG:4258   # Databasens SR
- PG_OUTPUT_DB:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgoutputdb').text
      
      return value
- LOG_FILE:   # Python Script
      #-------------------------------------------------------------------------------
      # Name:        GetConfigFile
      # Purpose:
      #
      # Author:      xsunknu
      #
      # Created:     21.08.2015
      # Copyright:   (c) xsunknu 2015
      # Licence:     <your licence>
      #-------------------------------------------------------------------------------
      
      import os, uuid, fme
      
      fmwdir = fme.macroValues['FME_MF_DIR']
      fmwfile = fme.macroValues['FME_MF_NAME']
      
      logdir = os.path.join(fmwdir, 'log')
      if not os.path.isdir(logdir):
          os.mkdir(logdir)
      
      logfile = os.path.splitext(fmwfile)[0] + '_' + str(uuid.uuid1()).replace('-','') + '.log'
      logfile = os.path.join(logdir, logfile)
      
      return logfile

Readers:
- POSTGIS_1: POSTGIS from $(PG_INPUT_DB)
- POSTGRES_1: POSTGRES from $(PG_INPUT_DB)

Writers:
- POSTGIS_2: POSTGIS to $(PG_OUTPUT_DB)
- POSTGRES_2: POSTGRES to $(PG_OUTPUT_DB)

Reprojector
    SOURCE = Read from feature
    RASTER_CELL_SIZE = Preserve Cells
    INTERPOLATION_TYPE_NAME = Nearest Neighbor
    DEST = $(DB_SR)
    REPROJECTED -> AttributeValueMapper
FeatureTypeFilter
    ATTRIBUTES = data.vertikalobjekt,data.vertikalobjektkomponent,<BLANK>,<UNFILTERED>
    data.vertikalobjekt -> AttributeCreator
    data.vertikalobjektkomponent -> AttributeCreator_2
AttributeCreator
    ATTR_LIST = objtype,VertikalObjekt,objid,@Value(id),gyldigfra,@Value(gyldigfradato),gyldigtil,@Value(gyldigtildato),kommentarvertobjtype,@Value(kommentarvertikalobjekttype),status,@Value(statuskode),typeendring,@Value(typeendringkode),endret_tid,@Value(tidspunktendring),objid,@Value(id)
    -> nrl.vertikalobjekt (writer POSTGRES_2)
AttributeCreator_2
    ATTR_LIST = objid,@Value(id),objtype,@Value(elementtype),bestaravvertikalobjektkomponentfk,@Value(vertikalobjektid),komponentsekvnr,@Value(komponentsekvensnummer),status,@Value(statuskode),hoydeverdienhet,@Value(hoydeverdienhetkode),merkepliktigihenholdtil,@Value(merkepliktihenholdtilkode),ansvarligformerking,@Value(ansvarligkode),merkeinformasjon,@Value(merkeinformasjonkode),kommentarmerkeplikt,@Value(kommentar),hrefsystem,@Value(hoydereferansesystemkode),href,@Value(hoydereferansekode),malemetode,@Value(malemetodeposisjon),noyaktighet,@Value(noyaktighetposisjon),synbarhet,@Value(synbarhetkode),malemetodehoyde,@Value(malemetodehoydekode),h_noyaktighet,@Value(noyaktighethoyde),typeendring,@Value(typeendringkode),endret_tid,@Value(tidspunktendring),linjespenn,@Value(spenn)
    -> TestFilter
TestFilter
    TEST_LIST = BOOL_OP,OR,COMPOSITE_TEST,<Unused>,TEST_CLAUSE,"TEST @Value(objtype) = VertikalObjektKomponentPunkt",VertikalObjektKomponentPunkt,BOOL_OP,OR,COMPOSITE_TEST,<Unused>,TEST_CLAUSE,"TEST @Value(objtype) = VertikalObjektKomponentLinjepunkt",VertikalObjektKomponentLinjepunkt,BOOL_OP,OR,COMPOSITE_TEST,<Unused>,TEST_CLAUSE,"TEST @Value(objtype) = VertikalObjektKomponentLinje",VertikalObjektKomponentLinje
    DEFAULT_VALUE = <UNFILTERED>
    VertikalObjektKomponentLinjepunkt -> nrl.vertikalobjektkomponentpunkt (writer POSTGIS_2)
    VertikalObjektKomponentLinje -> nrl.vertikalobjektkomponentlinje (writer POSTGIS_2)
    VertikalObjektKomponentPunkt -> nrl.vertikalobjektkomponentpunkt (writer POSTGIS_2)
AttributeCreator_3
    ATTR_LIST = objid,@Value(id),harlyssettingfk,@Value(vertikalobjektkomponentid),lystype,@Value(lystypekode)
    -> nrl.lyssetting (writer POSTGRES_2)
AttributeRenamer
    ATTR_LIST = flouriserende1,fluoriserende1,,flouriserende2,fluoriserende2,,farge1kode,merkingfarge1,,farge2kode,merkingfarge2,,merkingmonsterkode,merkingmonster,,merkingtilstandkode,merkingtype,,merkingtypekode,merkingtilstand,
    -> AttributeCreator_4
AttributeCreator_4
    ATTR_LIST = objid,@Value(id),harmerkingfk,@Value(vertikalobjektkomponentid),fluoriserende1,"FME_CONDITIONAL:DEFAULT_VALUE'Annet'BOOL_OP;OR;COMPOSITE_TEST;<Unused>;TEST @Value(fluoriserende1) = 0'Nei'BOOL_OP;OR;COMPOSITE_TEST;<Unused>;TEST @Value(fluoriserende1) = 1'Ja'FME_NUM_CONDITIONS3___",fluoriserende2,"FME_CONDITIONAL:DEFAULT_VALUE'Annet'BOOL_OP;OR;COMPOSITE_TEST;<Unused>;TEST @Value(fluoriserende2) = 0'Nei'BOOL_OP;OR;COMPOSITE_TEST;<Unused>;TEST @Value(fluoriserende2) = 1'Ja'FME_NUM_CONDITIONS3___",reflekterende1,"FME_CONDITIONAL:DEFAULT_VALUE'Annet'BOOL_OP;OR;COMPOSITE_TEST;<Unused>;TEST @Value(reflekterende1) = 0'Nei'BOOL_OP;OR;COMPOSITE_TEST;<Unused>;TEST @Value(reflekterende1) = 1'Ja'FME_NUM_CONDITIONS3___",reflekterende2,"FME_CONDITIONAL:DEFAULT_VALUE'Annet'BOOL_OP;OR;COMPOSITE_TEST;<Unused>;TEST @Value(reflekterende1) = 0'Nei'BOOL_OP;OR;COMPOSITE_TEST;<Unused>;TEST @Value(reflekterende2) = 1'Ja'FME_NUM_CONDITIONS3___"
    -> nrl.merking (writer POSTGRES_2)

Bookmark: PostGIS
data.vertikalobjekt (reader POSTGIS_1)
    attributes: id numeric(19,0),PRIKEY, lfhid numeric(19,0), vertikalobjektnavn varchar(255), hindertype varchar(25), typekodelinje int4, typekodepunkt int4, kommentarvertikalobjekttype varchar(255), statuskode varchar(255), datafangstdato date, gyldigfradato date, gyldigtildato date, oppdateringsdato timestamp, opphav varchar(255), informasjon varchar(255), vertikalobjektgruppe int2, tidspunktendring timestamp, typeendringkode varchar(255), versjon numeric(19,0), versjonid numeric(19,0)
    -> Reprojector
data.vertikalobjektkomponent (reader POSTGIS_1)
    attributes: id numeric(19,0),PRIKEY, vertikalobjektid numeric(19,0), lfhid numeric(19,0), elementtype varchar(35), brekkbar int2, mobilitet int2, verifiseringsdato date, oppdateringsdato timestamp, bsle21hinder int2, statuskode varchar(255), tidspunktendring timestamp, typeendringkode varchar(255), komponentsekvensnummer int4, koordinatsystemkode int4, ansvarligkode varchar(255), kommentar varchar(255), merkeinformasjonkode varchar(255), merkepliktig int2, merkepliktihenholdtilkode varchar(255), vertikalutstrekning float8, hoydeverdienhetkode varchar(255), fraid numeric(19,0), tilid numeric(19,0), spenn int2, lyssatt int2, lengde float8, lengdeverdienhet varchar(255), x float8, y float8, z float8,
      hoydereferansesystemkode varchar(255), hoydereferansekode varchar(255), malemetodeposisjon int4, noyaktighetposisjon int4, noyaktighetenhetkode varchar(255), synbarhetkode varchar(255), malemetodehoydekode int4, noyaktighethoyde int4, maleenhethoydekode varchar(255), versjon numeric(19,0), versjonid numeric(19,0)
    -> Reprojector

Bookmark: Mapper inn VertikalObjektType
AttributeValueMapper
    DIRECTION = Forward (Source To Destination)
    SRC = typekodelinje
    VAL_ATTR = vertikalobjekttype
    LUT = 0,Demning,1,Kraftledning,2,Taubane,3,Stolheis,4,Skitrekk,5,Bru,6,Skogsområde,7,Gondolbane,8,Annet
    DEFAULT_VALUE = FME_NULL_VALUE
    -> AttributeValueMapper_2
AttributeValueMapper_2
    DIRECTION = Forward (Source To Destination)
    SRC = typekodepunkt
    VAL_ATTR = vertikalobjekttype
    LUT = 0,EL_Nettstasjon,1,Bygning,2,Flaggstang,3,Forankret ballong,4,Fornøyelsesparkinnretning,5,Fyrtårn,6,Gjerde,7,Tank,8,Skilt,9,Silo,10,Pipe,11,Raffineri,12,Hopptårn,13,Kjøletårn,14,Kontrolltårn,15,Kraftverk,16,Kran,17,Kuppel,18,Landbruksutstyr,19,Petroleumsinnretning,20,Stolpe,21,Lysmast,22,Monument,23,Navigasjonshjelpemiddel,24,Oljerigg,25,Tårn,26,Vanntårn,27,Vindmølle,28,Vindmøllepark,29,Telemast,30,Terrengpunkt,31,Tre,32,Vindmåler,33,Annet
    DEFAULT_VALUE = @Value(vertikalobjekttype)
    -> Tester

Bookmark: Legger på 3D
Tester
    TEST_CLAUSE:
      TEST z NOT_ATTRIBUTE_VALUE_NULL ""
      TEST z NOT_ATTRIBUTE_IS_EMPTY ""
      TEST z NOT_ATTRIBUTE_IS_MISSING ""
    BOOL_OP = AND
    TEST_DESCRIPTION = ""
    TEST_MODE = Automatic
    PASSED -> 3DForcer
    FAILED -> FeatureTypeFilter
3DForcer
    ZVALATTR = @Value(z)
    -> FeatureTypeFilter

Bookmark: PostgreSQL
nrl.vertikalobjekt (writer POSTGRES_2)
    attributes: objid int4,PRIKEY, objtype varchar(80), kommentarvertobjtype varchar(255), vertikalobjektgruppe bool, vertikalobjektnavn varchar(80), vertikalobjekttype varchar(80), datafangstdato timestamp, typeendring varchar(80), endret_tid timestamp, gyldigfra timestamp, gyldigtil timestamp, lokalid uuid, navnerom varchar(80), versjonid varchar(80), informasjon varchar(255), oppdateringsdato timestamp, opphav varchar(255), status varchar(80)
nrl.lyssetting (writer POSTGRES_2)
    attributes: objid int4,PRIKEY, harlyssettingfk int4,BTREE, lystype varchar(20), versjonid int4
nrl.merking (writer POSTGRES_2)
    attributes: objid numeric(19,0),PRIKEY, harmerkingfk numeric(19,0),BTREE, versjonid numeric(19,0), merkingfarge1 varchar(255), annet1 varchar(255), fluoriserende1 varchar(6), reflekterende1 varchar(6), merkingfarge2 varchar(255), annet2 varchar(255), fluoriserende2 varchar(6), reflekterende2 varchar(6), merkingtype varchar(255), kommentarmerkingtype varchar(255), merkingmonster varchar(255), kommentarmerkingmonster varchar(255), merkingicao int2, merkingtilstand varchar(255)

Bookmark: PostGIS
nrl.vertikalobjektkomponentpunkt (writer POSTGIS_2)
    attributes: objid int4,PRIKEY, objtype varchar(80), brekkbar bool, vertikalutstrekning float8, hoydeverdienhet varchar(80), merkepliktig varchar(80), merkepliktigihenholdtil varchar(80), ansvarligformerking varchar(80), merkeinformasjon varchar(80), kommentarmerkeplikt varchar(80), hrefsystem varchar(80), href varchar(80), registernavn varchar(80), eksternid varchar(80), mobilitet bool, komponentsekvnr int4, bsle21hinder bool, bestaravvertikalobjektkomponentfk int4,BTREE, lokalid uuid, navnerom varchar(80), versjonid varchar(80), verifiseringsdato timestamp, oppdateringsdato timestamp, malemetode varchar(80), noyaktighet int4, synbarhet varchar(80), malemetodehoyde varchar(80), h_noyaktighet int4, typeendring varchar(80), endret_tid timestamp,
      status varchar(80)
nrl.vertikalobjektkomponentlinje (writer POSTGIS_2)
    attributes: objid int4,PRIKEY, objtype varchar(80), lengde float8, lengdeverdienhet varchar(80), linjespenn bool, vertikalutstrekning float8, hoydeverdienhet varchar(80), merkepliktig varchar(80), merkepliktigihenholdtil varchar(80), ansvarligformerking varchar(80), merkeinformasjon varchar(80), kommentarmerkeplikt varchar(80), hrefsystem varchar(80), href varchar(80), registernavn varchar(80), eksternid varchar(80), mobilitet bool, komponentsekvnr int4, bsle21hinder bool, bestaravvertikalobjektkomponentfk int4,BTREE, lokalid uuid, navnerom varchar(80), versjonid varchar(80), verifiseringsdato timestamp, oppdateringsdato timestamp, malemetode varchar(80), noyaktighet int4, synbarhet varchar(80), malemetodehoyde varchar(80), h_noyaktighet int4,
      typeendring varchar(80), endret_tid timestamp, status varchar(80)

Bookmark: PostgreSQL
data.lyssetting (reader POSTGRES_1)
    attributes: id numeric(19,0),PRIKEY, vertikalobjektkomponentid numeric(19,0), lystypekode varchar(255), versjonid numeric(19,0)
    -> AttributeCreator_3
data.merking (reader POSTGRES_1)
    attributes: id numeric(19,0),PRIKEY, vertikalobjektkomponentid numeric(19,0), merkingmonsterkode varchar(255), kommentarmerkingmonster varchar(255), merkingtypekode varchar(255), kommentarmerkingtype varchar(255), merkingicao int2, merkingtilstandkode varchar(255), farge1kode varchar(255), annet1 varchar(255), flouriserende1 int2, reflekterende1 int2, farge2kode varchar(255), annet2 varchar(255), flouriserende2 int2, reflekterende2 int2, versjonid numeric(19,0)
    -> AttributeRenamer
