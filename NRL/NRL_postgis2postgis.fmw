FME workspace NRL_postgis2postgis.fmw

Parameters:
- SourceDataset_POSTGIS = nrl2   # Database
- SourceDataset_POSTGRES = nrl2   # Database
- PG_OUTPUT_DB = geonor01tst   # Database
- PG_OUTPUT_HOST = nnridb504   # Host
- PG_OUTPUT_PORT = 5432   # Port
- PG_OUTPUT_USER = geonortst   # Username
- PG_OUTPUT_PWD =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   # Password

Readers:
- POSTGIS_1: POSTGIS from $(SourceDataset_POSTGIS)
- POSTGRES_1: POSTGRES from $(SourceDataset_POSTGRES)

Writers:
- POSTGIS_3: POSTGIS to $(PG_OUTPUT_DB)
- POSTGRES_3: POSTGRES to $(PG_OUTPUT_DB)

AttributeCreator
    ATTR_LIST = objtype,VertikalObjekt,objid,@Evaluate(@Count(vertikalobjekt, 1)),vertikalobjekttype,@Value(hindertype),gyldigfra,@Value(gyldigfradato),gyldigtil,@Value(gyldigtildato),kommentarvertobjtype,@Value(kommentarvertikalobjekttype),status,@Value(statuskode),typeendring,@Value(typeendringkode),endret_tid,@Value(tidspunktendring),objid,@Value(id)
    -> nrl.vertikalobjekt (writer POSTGRES_3)
AttributeCreator_2
    ATTR_LIST = objid,@Value(id),objtype,@Value(elementtype),bestaravvertikalobjektkomponentfk,@Value(vertikalobjektid),komponentsekvnr,@Value(komponentsekvensnummer),status,@Value(statuskode),hoydeverdienhet,@Value(hoydeverdienhetkode),merkepliktigihenholdtil,@Value(merkepliktihenholdtilkode),ansvarligformerking,@Value(ansvarligkode),merkeinformasjon,@Value(merkeinformasjonkode),kommentarmerkeplikt,@Value(kommentar),hrefsystem,@Value(hoydereferansesystemkode),href,@Value(hoydereferansekode),malemetode,@Value(malemetodeposisjon),noyaktighet,@Value(noyaktighetposisjon),synbarhet,@Value(synbarhetkode),malemetodehoyde,@Value(malemetodehoydekode),h_noyaktighet,@Value(noyaktighethoyde),typeendring,@Value(typeendringkode),endret_tid,@Value(tidspunktendring),linjespenn,@Value(spenn)
    -> TestFilter
TestFilter
    TEST_LIST = BOOL_OP,OR,COMPOSITE_TEST,<Unused>,TEST_CLAUSE,"TEST @Value(objtype) = VertikalObjektKomponentLinjepunkt",VertikalObjektKomponentLinjepunkt,BOOL_OP,OR,COMPOSITE_TEST,<Unused>,TEST_CLAUSE,"TEST @Value(objtype) = VertikalObjektKomponentLinje",VertikalObjektKomponentLinje
    DEFAULT_VALUE = <UNFILTERED>
    VertikalObjektKomponentLinjepunkt -> nrl.vertikalobjektkomponentpunkt (writer POSTGIS_3)
    VertikalObjektKomponentLinje -> nrl.vertikalobjektkomponentlinje (writer POSTGIS_3)
AttributeCreator_3
    ATTR_LIST = objid,@Value(id),harlyssettingfk,@Value(vertikalobjektkomponentid),lystype,@Value(lystypekode)
    -> nrl.lyssetting (writer POSTGRES_3)

Bookmark: PostGIS
data.vertikalobjekt (reader POSTGIS_1)
    attributes: id numeric(19,0),PRIKEY, lfhid numeric(19,0), vertikalobjektnavn varchar(255), hindertype varchar(25), typekodelinje int4, typekodepunkt int4, kommentarvertikalobjekttype varchar(255), statuskode varchar(255), datafangstdato date, gyldigfradato date, gyldigtildato date, oppdateringsdato timestamp, opphav varchar(255), informasjon varchar(255), vertikalobjektgruppe int2, tidspunktendring timestamp, typeendringkode varchar(255), versjon numeric(19,0), versjonid numeric(19,0)
    -> AttributeCreator
data.vertikalobjektkomponent (reader POSTGIS_1)
    attributes: id numeric(19,0),PRIKEY, vertikalobjektid numeric(19,0), lfhid numeric(19,0), elementtype varchar(35), brekkbar int2, mobilitet int2, verifiseringsdato date, oppdateringsdato timestamp, bsle21hinder int2, statuskode varchar(255), tidspunktendring timestamp, typeendringkode varchar(255), komponentsekvensnummer int4, koordinatsystemkode int4, ansvarligkode varchar(255), kommentar varchar(255), merkeinformasjonkode varchar(255), merkepliktig int2, merkepliktihenholdtilkode varchar(255), vertikalutstrekning float8, hoydeverdienhetkode varchar(255), fraid numeric(19,0), tilid numeric(19,0), spenn int2, lyssatt int2, lengde float8, lengdeverdienhet varchar(255), x float8, y float8, z float8,
      hoydereferansesystemkode varchar(255), hoydereferansekode varchar(255), malemetodeposisjon int4, noyaktighetposisjon int4, noyaktighetenhetkode varchar(255), synbarhetkode varchar(255), malemetodehoydekode int4, noyaktighethoyde int4, maleenhethoydekode varchar(255), versjon numeric(19,0), versjonid numeric(19,0)
    -> AttributeCreator_2

Bookmark: PostgreSQL
nrl.vertikalobjekt (writer POSTGRES_3)
    attributes: objid serial,PRIKEY, objtype varchar(80), kommentarvertobjtype varchar(255), vertikalobjektgruppe bool, vertikalobjektnavn varchar(80), vertikalobjekttype varchar(80), datafangstdato timestamp, typeendring varchar(80), endret_tid timestamp, gyldigfra timestamp, gyldigtil timestamp, lokalid uuid,PRIKEY, navnerom varchar(80), versjonid varchar(80), informasjon varchar(255), oppdateringsdato timestamp, opphav varchar(255), status varchar(80)
nrl.lyssetting (writer POSTGRES_3)
    attributes: objid int4,PRIKEY, harlyssettingfk int4,BTREE, lystype varchar(20)

Bookmark: PostGIS
nrl.vertikalobjektkomponentpunkt (writer POSTGIS_3)
    attributes: objid serial,PRIKEY, objtype varchar(80), brekkbar bool, vertikalutstrekning float8, hoydeverdienhet varchar(80), merkepliktig varchar(80), merkepliktigihenholdtil varchar(80), ansvarligformerking varchar(80), merkeinformasjon varchar(80), kommentarmerkeplikt varchar(80), hrefsystem varchar(80), href varchar(80), registernavn varchar(80), eksternid varchar(80), mobilitet bool, komponentsekvnr int4, bsle21hinder bool, bestaravvertikalobjektkomponentfk int4, lokalid uuid,PRIKEY, navnerom varchar(80), versjonid varchar(80), verifiseringsdato timestamp, oppdateringsdato timestamp, malemetode varchar(80), noyaktighet int4, synbarhet varchar(80), malemetodehoyde varchar(80), h_noyaktighet int4, typeendring varchar(80), endret_tid timestamp,
      status varchar(80)
nrl.vertikalobjektkomponentlinje (writer POSTGIS_3)
    attributes: objid serial,PRIKEY, objtype varchar(80), lengde float8, lengdeverdienhet varchar(80), linjespenn bool, vertikalutstrekning float8, hoydeverdienhet varchar(80), merkepliktig varchar(80), merkepliktigihenholdtil varchar(80), ansvarligformerking varchar(80), merkeinformasjon varchar(80), kommentarmerkeplikt varchar(80), hrefsystem varchar(80), href varchar(80), registernavn varchar(80), eksternid varchar(80), mobilitet bool, komponentsekvnr int4, bsle21hinder bool, bestaravvertikalobjektkomponentfk int4, lokalid uuid,PRIKEY, navnerom varchar(80), versjonid varchar(80), verifiseringsdato timestamp, oppdateringsdato timestamp, malemetode varchar(80), noyaktighet int4, synbarhet varchar(80), malemetodehoyde varchar(80), h_noyaktighet int4,
      typeendring varchar(80), endret_tid timestamp, status varchar(80)

Bookmark: PostgreSQL
data.lyssetting (reader POSTGRES_1)
    attributes: id numeric(19,0),PRIKEY, vertikalobjektkomponentid numeric(19,0), lystypekode varchar(255), versjonid numeric(19,0)
    -> AttributeCreator_3
