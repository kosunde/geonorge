FME workspace NRL_postgis2gml.fmw
# Copyright: (c) xgrimor 2015
# Licence: <your licence>
Shutdown Python:
      # -*- coding: utf-8 -*-
      #-------------------------------------------------------------------------------
      # Name:        zipfiles.py
      # Purpose:     Pakker filer i output folderen
      #
      # Author:      xsunknu
      #
      # Created:     18.09.2015
      # Copyright:   (c) xsunknu 2015
      # Licence:     <your licence>
      #-------------------------------------------------------------------------------

      import sys, os, zipfile, fme

      def zip(gmlfile, zfile):
          from os.path import basename

          # Lager korresponderende zip-fil av SOSI-fil
          if os.path.isfile(zfile):
              os.remove(zfile)

          zf = zipfile.ZipFile(zfile, "w", zipfile.ZIP_DEFLATED)

          # Ønsker ikke full sti inn i ZIP-filen
          arcname = basename(gmlfile)

          # ZIP-formatet støtter ikke non-ascii tegn
          # Erstatter AØÅæøå med ascii-tegn
          arcname = arcname.replace('\xc6', 'E')
          arcname = arcname.replace('\xd8', 'O')
          arcname = arcname.replace('\xc5', 'A')
          arcname = arcname.replace('\xe6', 'e')
          arcname = arcname.replace('\xf8', 'o')
          arcname = arcname.replace('\xe5', 'a')

          zf.write(gmlfile, arcname)
          zf.close()
          os.remove(gmlfile)

          return

      def main():

          # Kjøres ikke på FME Server, da FME Server selv sørger for pakkingen
          if not 'FME_SERVER_DEST_DIR' in fme.macroValues:
              if 'FANOUT_FOLDER' in fme.macroValues:
                  path = fme.macroValues['FANOUT_FOLDER']
                  for dirpath, dnames, fnames in os.walk(path):
                      for f in fnames:
                          if f.endswith(".gml"):
                              # Scanner gjennom alle SOSI-filer
                              gmlfile = os.path.join(path, f)
                              zfile = os.path.splitext(gmlfile)[0] + '.zip'
                              if os.path.isfile(zfile):

                                  # Korresponderende ZIP-fil finnes, sjekker timestamps
                                  sositstamp = os.stat(gmlfile).st_mtime
                                  ziptstamp = os.stat(zfile).st_mtime

                                  if sositstamp > ziptstamp:
                                      # SOSI-fil er nyere enn ZIP-fila, ZIP-fila oppdateres
                                      # SOSI-fila slettes
                                      try:
                                          zip(gmlfile, zfile)
                                      except:
                                          print 'Kunne ikke pakke: ' + gmlfile
                                  else:
                                      # SOSI-fila er eldre enn ZIP-fila
                                      # SOSI-fila slettes
                                      try:
                                          os.remove(gmlfile)
                                      except:
                                          print 'Kunne ikke slette: ' + gmlfile
                              else:
                                  # ZIP-fila eksisterer ikke og lages
                                  # SOSI-fila slettes
                                  try:
                                      zip(gmlfile, zfile)
                                  except:
                                      print 'Kunne ikke pakke: ' + gmlfile


      if __name__ == '__main__':
          main()

Parameters:
- KNR =   # Kommune(r)
- FNR =   # Fylke(r)
- CLIPPERCOORDS =   # Clipper coordinates
- CLIPPER_EPSG_CODE =   # Clipper coordinate system
- CLIPPER_FILE =   # "" Clipper file (any format)
- OUTPUT_EPSG_CODE = 25832   # Destination coordinate system
- FANOUT =   # Fanout områder
- DestDataset_GML = $(FME_MF_DIR)nrl.gml   # Destination Geography Markup Language (GML) File
- CONFIG_FILE:   # Python Script
      #-------------------------------------------------------------------------------
      # Name:        GetConfigFile
      # Purpose:
      #
      # Author:      xsunknu
      #
      # Created:     21.08.2015
      # Copyright:   (c) xsunknu 2015
      # Licence:     <your licence>
      #-------------------------------------------------------------------------------
      
      import os, fme
      
      fmwdir = fme.macroValues['FME_MF_DIR']
      fmwfile = fme.macroValues['FME_MF_NAME']
      
      fmwfile = os.path.join(fmwdir, fmwfile)
      configfile = os.path.splitext(fmwfile)[0] + '_config.xml'
      
      return configfile
- PG_DB:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgdb').text
      
      return value
- PG_HOST:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pghost').text
      
      return value
- PG_PORT:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgport').text
      
      return value
- PG_USER:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pguser').text
      
      return value
- PG_PWD:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgpwd').text
      
      return value
- SPATIAL_FILTER:   # Python Script
      #-------------------------------------------------------------------------------
      # Name:        SetSpatialFilter
      # Purpose:
      #
      # Author:      xsunknu
      #
      # Created:     21.08.2015
      # Copyright:   (c) xsunknu 2015
      # Licence:     <your licence>
      #-------------------------------------------------------------------------------
      
      import fme
      
      spatialfilter = 'Intersects'
      
      knr = fme.macroValues['KNR']
      fnr = fme.macroValues['FNR']
      coords = fme.macroValues['CLIPPERCOORDS']
      file = fme.macroValues['CLIPPER_FILE']
      
      if knr == '' and fnr == '' and coords == '' and file == '':
          spatialfilter = '<No Spatial Filter>'
      
      return spatialfilter
- CLIPPERCOORDSYS:   # Python Script
      #-------------------------------------------------------------------------------
      # Name:        SetCoordinateSystem
      # Purpose:
      #
      # Author:      xsunknu
      #
      # Created:     21.08.2015
      # Copyright:   (c) xsunknu 2015
      # Licence:     <your licence>
      #-------------------------------------------------------------------------------
      
      import os, fme
      
      EPSGvalue = fme.macroValues['CLIPPER_EPSG_CODE']
      EPSGcode  = 'EPSG:' + EPSGvalue
      
      return EPSGcode
- FIXEDCLIPPERCOORDS:   # Python Script
      #-------------------------------------------------------------------------------
      # Name:        FixClipperCoords
      # Purpose:
      #
      # Author:      xsunknu
      #
      # Created:     21.08.2015
      # Copyright:   (c) xsunknu 2015
      # Licence:     <your licence>
      #-------------------------------------------------------------------------------
      
      import fme
      clippercoords = fme.macroValues['CLIPPERCOORDS']
      
      if clippercoords == '':
          clippercoords = '1 1'
      
      return clippercoords
- UNDERTEMA = Luftfartshinder   # Undertema
- HOVEDTEMA = Luftfart   # Hovedtema
- DESTCOORDSYS:   # Python Script
      #-------------------------------------------------------------------------------
      # Name:        SetCoordinateSystem
      # Purpose:
      #
      # Author:      xsunknu
      #
      # Created:     21.08.2015
      # Copyright:   (c) xsunknu 2015
      # Licence:     <your licence>
      #-------------------------------------------------------------------------------
      
      import os, fme
      
      EPSGvalue = fme.macroValues['OUTPUT_EPSG_CODE']
      EPSGcode  = 'EPSG:' + EPSGvalue
      
      return EPSGcode
- FANOUT_FOLDER:   # Python Script
      #-------------------------------------------------------------------------------
      # Name:        GetConfigFile
      # Purpose:
      #
      # Author:      xsunknu
      #
      # Created:     21.08.2015
      # Copyright:   (c) xsunknu 2015
      # Licence:     <your licence>
      #-------------------------------------------------------------------------------
      
      import os, fme
      from xml.etree import ElementTree as ET
      
      if 'FME_SERVER_DEST_DIR' in fme.macroValues:
          value = fme.macroValues['FME_SERVER_DEST_DIR']
      else:
          #Read XML config file
          configtree = ET.parse(fme.macroValues['CONFIG_FILE'])
          configdoc = configtree.getroot()
          value = configdoc.find('destdir').text
      
      return value
- LOG_FILE:   # Python Script
      #-------------------------------------------------------------------------------
      # Name:        GetConfigFile
      # Purpose:
      #
      # Author:      xsunknu
      #
      # Created:     21.08.2015
      # Copyright:   (c) xsunknu 2015
      # Licence:     <your licence>
      #-------------------------------------------------------------------------------
      
      import os, uuid, fme
      
      fmwdir = fme.macroValues['FME_MF_DIR']
      fmwfile = fme.macroValues['FME_MF_NAME']
      
      logdir = os.path.join(fmwdir, 'log')
      if not os.path.isdir(logdir):
          os.mkdir(logdir)
      
      logfile = os.path.splitext(fmwfile)[0] + '_' + str(uuid.uuid1()).replace('-','') + '.log'
      logfile = os.path.join(logdir, logfile)
      
      return logfile

Readers:
- POSTGIS_1: POSTGIS from $(PG_DB)

Writers:
- GML_1: GML to $(DestDataset_GML)

CreateClipper
    CLIPPERCOORDS = $(FIXEDCLIPPERCOORDS)
    CLIPPERCOORDSYS = $(CLIPPERCOORDSYS)
    DESTCOORDSYS = $(DESTCOORDSYS)
    -> Clipper [input 1]
    -> FeatureReader_3
UUIDGenerator_2
    UUID_ATTR = gml_id
    -> AttributeCreator_14
AttributeCreator_14
    ATTR_LIST = gml_id,NRL_@Value(gml_id)
    -> AttributeCreator_2
AttributeRenamer_3
    ATTR_LIST = L:lyssetting{0}.lokalid,identifikasjon.Identifikasjon.lokalId,,L:lyssetting{0}.navnerom,identifikasjon.Identifikasjon.navnerom,,L:lyssetting{0}.versjonid,identifikasjon.Identifikasjon.versjonId,,L:lyssetting{0}.gml_id,gml_id,,gml_id,gml_parent_id,,gml_id,gml_parent_id.xlink_href,
    -> Lyssetting (writer GML_1)
Lyssetting (writer GML_1)
    attributes: identifikasjon.Identifikasjon.lokalId xml_buffer, identifikasjon.Identifikasjon.navnerom xml_buffer, identifikasjon.Identifikasjon.versjonId xml_buffer, lystype xml_buffer
Note: Mapping til GML-navn
AttributeRenamer_2
    ATTR_LIST = malemetode,kvalitet.Posisjonskvalitet.målemetode,,malemetodehoyde,kvalitet.Posisjonskvalitet.målemetodeHøyde,,noyaktighet,kvalitet.Posisjonskvalitet.nøyaktighet,,h_noyaktighet,kvalitet.Posisjonskvalitet.nøyaktighetHøyde,,synbarhet,kvalitet.Posisjonskvalitet.synbarhet,,typeendring,endringsflagg.Endringsflagg.typeEndring,,endret_tid,endringsflagg.Endringsflagg.tidspunktEndring,,vertikalutstrekning,vertikalUtstrekning,,hoydeverdienhet,høydeVerdiEnhet,,hrefsystem,hrefSystem,,href,href,,lokalid,identifikasjon.Identifikasjon.lokalId,,navnerom,identifikasjon.Identifikasjon.navnerom,,versjonid,identifikasjon.Identifikasjon.versjonId,,lengdeverdienhet,lengdeVerdiEnhet,,ansvarligformerking,merkepliktig.Merkepliktig.ansvarligForMerking,,merkepliktig,merkepliktig.Merkepliktig.merkepliktig,,merkepliktigihenholdtil,merkepliktig.Merkepliktig.merkepliktigIhenholdTil,,kommentarmerkeplikt,merkepliktig.Merkepliktig.kommentarMerkeplikt,,merkeinformasjon,merkepliktig.Merkepliktig.merkeInformasjon,,komponentsekvnr,komponentsekvensnummer,,bsle21hinder,BSLE-2-1_hinder,
    -> ListRenamer_16
ListRenamer_17
    LIST_NAME = L:avgrenserlinje{}.gml_id
    LIST_COMPONENT_NAMES = L:avgrenserlinje{},avgrenser{},gml_id,xlink_href
    LEAVE_ORIG = No
    LIST_ACTION = Rename
    -> GeometryPropertySetter_2
Note: Geometriegenskaper
GeometryPropertySetter_2
    GEOM_NAME_FIELD = posisjon
    OVERWRITE_CHOICE = Yes
    SETTYPE_PARAM = Geometry Name
    SET -> DateFormatter_2
Note: Til ISO-dato
DateFormatter_2
    INVALID_DATE_VALUE = _FME_NO_OP_
    SRCFMT = Unknown - Automatic Detection
    FMT = ISO DateTime (%Y-%m-%dT%H:%M:%S)
    DATE_ATTR = endringsflagg.Endringsflagg.tidspunktEndring,oppdateringsdato,verifiseringsdato
    -> Tester_5
Tester_5
    TEST_MODE = Automatic
    TEST_CLAUSE = TEST merking{0}.Merking.merkingFarge1.Farge.farge ATTRIBUTE_IS_MISSING ""
    BOOL_OP = OR
    TEST_DESCRIPTION = ""
    PASSED -> AttributeRemover_5
    FAILED -> Tester_7
AttributeRemover_5
    LIST_ATTRS = merking{}.Merking.merkingFarge1.Farge.annet merking{}.Merking.merkingFarge1.Farge.farge merking{}.Merking.merkingFarge1.Farge.fluoriserende merking{}.Merking.merkingFarge1.Farge.reflekterende merking{}.Merking.merkingFarge2.Farge.annet merking{}.Merking.merkingFarge2.Farge.farge merking{}.Merking.merkingFarge2.Farge.fluoriserende merking{}.Merking.merkingFarge2.Farge.reflekterende merking{}.Merking.kommentarMerkingMønster merking{}.Merking.kommentarMerkingType merking{}.Merking.merkingICAO merking{}.Merking.merkingMønster merking{}.Merking.merkingTilstand merking{}.Merking.merkingType
    -> Tester_7
Tester_7
    TEST_MODE = Automatic
    TEST_CLAUSE = TEST @Value(merkepliktig.Merkepliktig.merkepliktig) = 0
    BOOL_OP = OR
    TEST_DESCRIPTION = ""
    PASSED -> AttributeCreator_17
    FAILED -> NullAttributeMapper_4
AttributeCreator_17
    ATTR_LIST = merkepliktig.Merkepliktig.merkepliktig,Nei
    -> NullAttributeMapper_4
NullAttributeMapper_4
    ATTRCHOICE = Selected Attributes
    ATTRLIST = lengdeVerdiEnhet merkepliktig.Merkepliktig.ansvarligForMerking merkepliktig.Merkepliktig.kommentarMerkeplikt merkepliktig.Merkepliktig.merkeInformasjon merkepliktig.Merkepliktig.merkepliktigIhenholdTil brekkbar
    SOURCE_ATTR_VAL = Empty "Missing (Selected Attributes Only)" Null
    NULL_TREATMENT = Missing
    -> NullAttributeMapper_5
NullAttributeMapper_5
    ATTRCHOICE = Selected Attributes
    ATTRLIST = href hrefSystem
    SOURCE_ATTR_VAL = Empty "Missing (Selected Attributes Only)" Null
    NEW_VALUE = other: Ukjent
    NULL_TREATMENT = New Value
    -> VertikalObjektKomponentPunkt (writer GML_1)
VertikalObjektKomponentPunkt (writer GML_1)
    attributes: identifikasjon.Identifikasjon.lokalId xml_buffer, identifikasjon.Identifikasjon.navnerom xml_buffer, identifikasjon.Identifikasjon.versjonId xml_buffer, verifiseringsdato xml_datetime, oppdateringsdato xml_datetime, kvalitet.Posisjonskvalitet.målemetode xml_buffer, kvalitet.Posisjonskvalitet.nøyaktighet xml_int64, kvalitet.Posisjonskvalitet.synbarhet xml_buffer, kvalitet.Posisjonskvalitet.målemetodeHøyde xml_buffer, kvalitet.Posisjonskvalitet.nøyaktighetHøyde xml_int64, endringsflagg.Endringsflagg.typeEndring xml_buffer, endringsflagg.Endringsflagg.tidspunktEndring xml_datetime, status xml_buffer, merking{}.Merking.merkingFarge1.Farge.farge xml_buffer, merking{}.Merking.merkingFarge1.Farge.annet xml_buffer, merking{}.Merking.merkingFarge1.Farge.fluoriserende xml_buffer, merking{}.Merking.merkingFarge1.Farge.reflekterende xml_buffer, merking{}.Merking.merkingFarge2.Farge.farge xml_buffer, merking{}.Merking.merkingFarge2.Farge.annet xml_buffer, merking{}.Merking.merkingFarge2.Farge.fluoriserende xml_buffer, merking{}.Merking.merkingFarge2.Farge.reflekterende xml_buffer, merking{}.Merking.merkingType xml_buffer, merking{}.Merking.kommentarMerkingType xml_buffer, merking{}.Merking.merkingMønster xml_buffer, merking{}.Merking.kommentarMerkingMønster xml_buffer, merking{}.Merking.merkingICAO xml_boolean, merking{}.Merking.merkingTilstand xml_buffer, vertikalUtstrekning xml_real64, høydeVerdiEnhet xml_buffer, merkepliktig.Merkepliktig.merkepliktig xml_buffer,
      merkepliktig.Merkepliktig.merkepliktigIhenholdTil xml_buffer, merkepliktig.Merkepliktig.ansvarligForMerking xml_buffer, merkepliktig.Merkepliktig.merkeInformasjon xml_buffer, merkepliktig.Merkepliktig.kommentarMerkeplikt xml_buffer, hrefSystem xml_buffer, href xml_buffer, eksternReferanse{}.ReferanseTilEksterntRegister.registernavn xml_buffer, eksternReferanse{}.ReferanseTilEksterntRegister.eksternId xml_buffer, mobilitet xml_boolean, komponentsekvensnummer xml_int64, BSLE-2-1_hinder xml_boolean, harLyssetting{}.nilReason xml_buffer, harLyssetting{}.gml_remoteSchema xml_buffer, harLyssetting{}.xlink_href xml_buffer, harLyssetting{}.owns xml_boolean, posisjon xml_geometry, brekkbar xml_boolean, avgrenser{}.nilReason xml_buffer, avgrenser{}.gml_remoteSchema xml_buffer, avgrenser{}.xlink_href xml_buffer, avgrenser{}.owns xml_boolean
AttributeRenamer
    ATTR_LIST = malemetode,kvalitet.Posisjonskvalitet.målemetode,,malemetodehoyde,kvalitet.Posisjonskvalitet.målemetodeHøyde,,noyaktighet,kvalitet.Posisjonskvalitet.nøyaktighet,,h_noyaktighet,kvalitet.Posisjonskvalitet.nøyaktighetHøyde,,synbarhet,kvalitet.Posisjonskvalitet.synbarhet,,typeendring,endringsflagg.Endringsflagg.typeEndring,,endret_tid,endringsflagg.Endringsflagg.tidspunktEndring,,vertikalutstrekning,vertikalUtstrekning,,hoydeverdienhet,høydeVerdiEnhet,,hrefsystem,hrefSystem,,href,href,,lokalid,identifikasjon.Identifikasjon.lokalId,,navnerom,identifikasjon.Identifikasjon.navnerom,,versjonid,identifikasjon.Identifikasjon.versjonId,,lengdeverdienhet,lengdeVerdiEnhet,,ansvarligformerking,merkepliktig.Merkepliktig.ansvarligForMerking,,merkepliktig,merkepliktig.Merkepliktig.merkepliktig,,merkepliktigihenholdtil,merkepliktig.Merkepliktig.merkepliktigIhenholdTil,,kommentarmerkeplikt,merkepliktig.Merkepliktig.kommentarMerkeplikt,,merkeinformasjon,merkepliktig.Merkepliktig.merkeInformasjon,,komponentsekvnr,komponentsekvensnummer,,eksternid,eksternReferanse{0}.ReferanseTilEksterntRegister.eksternId,,registernavn,eksternReferanse{0}.ReferanseTilEksterntRegister.registernavn,,bsle21hinder,BSLE-2-1_hinder,
    -> ListRenamer
NullAttributeMapper
    ATTRCHOICE = All Attributes
    SOURCE_ATTR_VAL = Empty Null
    NULL_TREATMENT = Missing
    -> GeometryPropertySetter
GeometryPropertySetter
    GEOM_NAME_FIELD = linjeElement
    OVERWRITE_CHOICE = Yes
    SETTYPE_PARAM = Geometry Name
    SET -> DateFormatter
DateFormatter
    INVALID_DATE_VALUE = _FME_NO_OP_
    SRCFMT = Unknown - Automatic Detection
    FMT = ISO DateTime (%Y-%m-%dT%H:%M:%S)
    DATE_ATTR = oppdateringsdato,verifiseringsdato,endringsflagg.Endringsflagg.tidspunktEndring
    -> Tester_3
Tester_3
    TEST_MODE = Automatic
    TEST_CLAUSE = TEST merking{0}.Merking.merkingFarge1.Farge.farge ATTRIBUTE_IS_MISSING ""
    BOOL_OP = OR
    TEST_DESCRIPTION = ""
    PASSED -> AttributeRemover_4
    FAILED -> Tester_6
AttributeRemover_4
    LIST_ATTRS = merking{}.Merking.merkingFarge1.Farge.annet merking{}.Merking.merkingFarge1.Farge.farge merking{}.Merking.merkingFarge1.Farge.fluoriserende merking{}.Merking.merkingFarge1.Farge.reflekterende merking{}.Merking.merkingFarge2.Farge.annet merking{}.Merking.merkingFarge2.Farge.farge merking{}.Merking.merkingFarge2.Farge.fluoriserende merking{}.Merking.merkingFarge2.Farge.reflekterende merking{}.Merking.kommentarMerkingMønster merking{}.Merking.kommentarMerkingType merking{}.Merking.merkingICAO merking{}.Merking.merkingMønster merking{}.Merking.merkingTilstand merking{}.Merking.merkingType
    -> Tester_6
Tester_6
    TEST_MODE = Automatic
    TEST_CLAUSE = TEST @Value(merkepliktig.Merkepliktig.merkepliktig) = 0
    BOOL_OP = OR
    TEST_DESCRIPTION = ""
    PASSED -> AttributeCreator_16
    FAILED -> NullAttributeMapper_2
AttributeCreator_16
    ATTR_LIST = merkepliktig.Merkepliktig.merkepliktig,Nei
    -> NullAttributeMapper_2
NullAttributeMapper_2
    ATTRCHOICE = Selected Attributes
    ATTRLIST = lengdeVerdiEnhet merkepliktig.Merkepliktig.ansvarligForMerking merkepliktig.Merkepliktig.kommentarMerkeplikt merkepliktig.Merkepliktig.merkeInformasjon merkepliktig.Merkepliktig.merkepliktigIhenholdTil
    SOURCE_ATTR_VAL = Empty "Missing (Selected Attributes Only)" Null
    NULL_TREATMENT = Missing
    -> NullAttributeMapper_3
NullAttributeMapper_3
    ATTRCHOICE = Selected Attributes
    ATTRLIST = href hrefSystem
    SOURCE_ATTR_VAL = Empty "Missing (Selected Attributes Only)" Null
    NEW_VALUE = other: Ukjent
    NULL_TREATMENT = New Value
    -> VertikalObjektKomponentLinje (writer GML_1)
VertikalObjektKomponentLinje (writer GML_1)
    attributes: identifikasjon.Identifikasjon.lokalId xml_buffer, identifikasjon.Identifikasjon.navnerom xml_buffer, identifikasjon.Identifikasjon.versjonId xml_buffer, verifiseringsdato xml_datetime, oppdateringsdato xml_datetime, kvalitet.Posisjonskvalitet.målemetode xml_buffer, kvalitet.Posisjonskvalitet.nøyaktighet xml_int64, kvalitet.Posisjonskvalitet.synbarhet xml_buffer, kvalitet.Posisjonskvalitet.målemetodeHøyde xml_buffer, kvalitet.Posisjonskvalitet.nøyaktighetHøyde xml_int64, endringsflagg.Endringsflagg.typeEndring xml_buffer, endringsflagg.Endringsflagg.tidspunktEndring xml_datetime, status xml_buffer, merking{}.Merking.merkingFarge1.Farge.farge xml_buffer, merking{}.Merking.merkingFarge1.Farge.annet xml_buffer, merking{}.Merking.merkingFarge1.Farge.fluoriserende xml_buffer, merking{}.Merking.merkingFarge1.Farge.reflekterende xml_buffer, merking{}.Merking.merkingFarge2.Farge.farge xml_buffer, merking{}.Merking.merkingFarge2.Farge.annet xml_buffer, merking{}.Merking.merkingFarge2.Farge.fluoriserende xml_buffer, merking{}.Merking.merkingFarge2.Farge.reflekterende xml_buffer, merking{}.Merking.merkingType xml_buffer, merking{}.Merking.kommentarMerkingType xml_buffer, merking{}.Merking.merkingMønster xml_buffer, merking{}.Merking.kommentarMerkingMønster xml_buffer, merking{}.Merking.merkingICAO xml_boolean, merking{}.Merking.merkingTilstand xml_buffer, vertikalUtstrekning xml_real64, høydeVerdiEnhet xml_buffer, merkepliktig.Merkepliktig.merkepliktig xml_buffer,
      merkepliktig.Merkepliktig.merkepliktigIhenholdTil xml_buffer, merkepliktig.Merkepliktig.ansvarligForMerking xml_buffer, merkepliktig.Merkepliktig.merkeInformasjon xml_buffer, merkepliktig.Merkepliktig.kommentarMerkeplikt xml_buffer, hrefSystem xml_buffer, href xml_buffer, eksternReferanse{}.ReferanseTilEksterntRegister.registernavn xml_buffer, eksternReferanse{}.ReferanseTilEksterntRegister.eksternId xml_buffer, mobilitet xml_boolean, komponentsekvensnummer xml_int64, BSLE-2-1_hinder xml_boolean, harLyssetting{}.nilReason xml_buffer, harLyssetting{}.gml_remoteSchema xml_buffer, harLyssetting{}.xlink_href xml_buffer, harLyssetting{}.owns xml_boolean, linjeElement xml_geometry, lengde xml_real64, lengdeVerdiEnhet xml_buffer, linjespenn xml_boolean, avgrensesAv{}.nilReason xml_buffer, avgrensesAv{}.gml_remoteSchema xml_buffer, avgrensesAv{}.xlink_href xml_buffer, avgrensesAv{}.owns xml_boolean

Bookmark: Fylke and/or kommune clippers
Creator_2
    GEOMTYPE = Geometry Object
    NUM = 1
    CREATED -> AttributeCreator_8
AttributeCreator_8
    ATTR_LIST = _clippercoords,$(CLIPPERCOORDS),_clipper_file,$(CLIPPER_FILE),_fnr,$(FNR),_knr,$(KNR)
    -> Tester_4
Note: Sender inn en dummy initiator / dersom alle klippeparametrene er / blanke siden Luftfartshindere / strekker seg utover fastlands- / Norge
Tester_4
    TEST_MODE = Automatic
    TEST_CLAUSE:
      TEST _clipper_file ATTRIBUTE_IS_EMPTY ""
      TEST _clippercoords ATTRIBUTE_IS_EMPTY ""
      TEST _fnr ATTRIBUTE_IS_EMPTY ""
      TEST _knr ATTRIBUTE_IS_EMPTY ""
    BOOL_OP = AND
    TEST_DESCRIPTION = ""
    PASSED -> Reprojector_2
admingrense.fylkeflate (reader POSTGIS_1)
    attributes: fylkeid int4, navn varchar(80)
    -> Tester
Tester
    TEST_MODE = Automatic
    TEST_CLAUSE = TEST @Value(fylkeid) IN $(FNR)
    BOOL_OP = OR
    TEST_DESCRIPTION = ""
    PASSED -> Reprojector_2
admingrense.kommuneflate (reader POSTGIS_1)
    attributes: kommuneid int4, navn varchar(80)
    -> Tester_2
Tester_2
    TEST_MODE = Automatic
    TEST_CLAUSE = TEST @Value(kommuneid) IN $(KNR)
    BOOL_OP = OR
    TEST_DESCRIPTION = ""
    PASSED -> Reprojector_2
Reprojector_2
    RASTER_CELL_SIZE = Preserve Cells
    INTERPOLATION_TYPE_NAME = Nearest Neighbor
    SOURCE = Read from feature
    DEST = EPSG:4258
    REPROJECTED -> Clipper [input 1]
    REPROJECTED -> FeatureReader_3

Bookmark: Clipper file (any format)
Creator
    GEOMTYPE = Geometry Object
    NUM = 1
    CREATED -> FeatureReader
FeatureReader
    DATASET = $(CLIPPER_FILE)
    ATTR_ACCUM_MODE = Only Use Result
    ATTRIBUTES = NewFeatureType,
    OUTPUT_FEATURES_DISPLAY = Based on Connections
    FEATURETYPES_RADIO = FEATURETYPES
    INTERACT = <No Spatial Filter>
    GENERIC_REAL_FORMAT = GUESS_FROM_EXTENSION
    FORMAT = GENERIC
    COMBINE_GEOM = Use Result
    <OTHER> -> Reprojector_3
Reprojector_3
    RASTER_CELL_SIZE = Preserve Cells
    INTERPOLATION_TYPE_NAME = Nearest Neighbor
    SOURCE = Read from feature
    DEST = EPSG:4258
    REPROJECTED -> Clipper [input 1]
    REPROJECTED -> FeatureReader_3

Bookmark: Leser features og relaterte data
FeatureReader_3
    ATTRIBUTES = nrl.vertikalobjektkomponentlinje,"objid,objtype,lengde,lengdeverdienhet,linjespenn,vertikalutstrekning,hoydeverdienhet,merkepliktig,merkepliktigihenholdtil,ansvarligformerking,merkeinformasjon,kommentarmerkeplikt,hrefsystem,href,registernavn,eksternid,mobilitet,komponentsekvnr,bsle21hinder,bestaravvertikalobjektkomponentfk,lokalid,navnerom,versjonid,verifiseringsdato,oppdateringsdato,malemetode,noyaktighet,synbarhet,malemetodehoyde,h_noyaktighet,typeendring,endret_tid,status",nrl.vertikalobjektkomponentpunkt,"objid,objtype,brekkbar,vertikalutstrekning,hoydeverdienhet,merkepliktig,merkepliktigihenholdtil,ansvarligformerking,merkeinformasjon,kommentarmerkeplikt,hrefsystem,href,registernavn,eksternid,mobilitet,komponentsekvnr,bsle21hinder,bestaravvertikalobjektkomponentfk,lokalid,navnerom,versjonid,verifiseringsdato,oppdateringsdato,malemetode,noyaktighet,synbarhet,malemetodehoyde,h_noyaktighet,typeendring,endret_tid,status"
    INTERACT = $(SPATIAL_FILTER)
    OUTPUT_FEATURES_DISPLAY = Based on Connections
    FEATURETYPES = nrl.vertikalobjektkomponentlinje nrl.vertikalobjektkomponentpunkt
    POSTGIS_SCHEMALIST = nrl
    POSTGIS_USE_SEARCH_ENVELOPE = NO
    POSTGIS_USE_TRUE_POSTGIS_TYPES = yes
    COMBINE_GEOM = Use Result
    POSTGIS_QUERY_FEATURE_TYPES_FOR_MERGE_FILTERS = Yes
    POSTGIS_DISABLE_COLLECTION_SPLITTING = yes
    ATTR_ACCUM_MODE = Only Use Result
    FEATURETYPES_RADIO = FEATURETYPES
    FORMAT = POSTGIS
    DATASET = geonortst@nnridb504:5432/geonor01tst
    POSTGIS_CLIP_TO_ENVELOPE = NO
    nrl.vertikalobjektkomponentpunkt -> AttributeCreator_12
    nrl.vertikalobjektkomponentlinje -> AttributeCreator_12
AttributeCreator_12
    ATTR_LIST = _clippercoords,$(CLIPPERCOORDS),_clipper_file,$(CLIPPER_FILE),_fnr,$(FNR),_knr,$(KNR)
    -> TestFilter
TestFilter
    DEFAULT_VALUE = <UNFILTERED>
    TEST_LIST:
      BOOL_OP,AND,COMPOSITE_TEST,<Unused>,TEST_CLAUSE,"TEST _clipper_file ATTRIBUTE_IS_EMPTY """"
      TEST _clippercoords ATTRIBUTE_IS_EMPTY """"
      TEST _fnr ATTRIBUTE_IS_EMPTY """"
      TEST _knr ATTRIBUTE_IS_EMPTY """"",Landsdekkende,BOOL_OP,AND,COMPOSITE_TEST,<Unused>,TEST_CLAUSE,"TEST _clipper_file ATTRIBUTE_IS_EMPTY """"
      TEST _clippercoords ATTRIBUTE_IS_EMPTY """"
      TEST _fnr NOT_ATTRIBUTE_IS_EMPTY """"
      TEST _knr ATTRIBUTE_IS_EMPTY """"",Fylkesvis,BOOL_OP,AND,COMPOSITE_TEST,<Unused>,TEST_CLAUSE,"TEST _clipper_file ATTRIBUTE_IS_EMPTY """"
      TEST _clippercoords ATTRIBUTE_IS_EMPTY """"
      TEST _fnr ATTRIBUTE_IS_EMPTY """"
      TEST _knr NOT_ATTRIBUTE_IS_EMPTY """"",Kommunevis
    Fylkesvis -> Clipper [input 2]
    Kommunevis -> Clipper [input 2]
    <UNFILTERED> -> Clipper [input 2]
    Landsdekkende -> DuplicateRemover
    Landsdekkende -> DuplicateRemover_2
    Landsdekkende -> UUIDGenerator
DuplicateRemover
    KEYATTR = bestaravvertikalobjektkomponentfk
    UNIQUE -> Aggregator_4
Aggregator_4
    MODE = Attributes Only
    ORDERED = No
    SEP = ,
    CONCAT_ATTRS = bestaravvertikalobjektkomponentfk
    ACCUM_ATTRS_NAME = No
    AGGREGATE -> AttributeCreator_9
AttributeCreator_9
    ATTR_LIST = sql,select * from nrl.vertikalobjekt where objid in (@Value(bestaravvertikalobjektkomponentfk));
    -> SQLExecutor
SQLExecutor
    POSTGRES_HOST = $(PG_HOST)
    DATASET = $(PG_DB)
    SQL_STATEMENT = @Value(sql)
    POSTGRES_PORT = $(PG_PORT)
    COMBINE_GEOM = Initiator Geometry Only
    POSTGRES_USER_NAME = $(PG_USER)
    COMBINE_ATTRS = Result Attributes Only
    POSTGRES_QUERY_FEATURE_TYPES_FOR_MERGE_FILTERS = Yes
    POSTGRES_PASSWORD = $(PG_PWD)
    EXPOSED_ATTRIBUTE_LIST = datafangstdato,endret_tid,gyldigfra,gyldigtil,informasjon,kommentarvertobjtype,lokalid,navnerom,objid,objtype,oppdateringsdato,opphav,status,typeendring,versjonid,vertikalobjektgruppe,vertikalobjektnavn,vertikalobjekttype
    FORMAT = POSTGRES
    RESULT -> UUIDGenerator_2
DuplicateRemover_2
    KEYATTR = objid
    UNIQUE -> Aggregator_2
Aggregator_2
    MODE = Attributes Only
    ORDERED = No
    SEP = ,
    CONCAT_ATTRS = objid
    ACCUM_ATTRS_NAME = No
    AGGREGATE -> AttributeCreator_10
    AGGREGATE -> AttributeCreator_11
AttributeCreator_11
    ATTR_LIST = sql,select * from nrl.merking where harmerkingfk in (@Value(objid));
    -> SQLExecutor_3
SQLExecutor_3
    POSTGRES_HOST = $(PG_HOST)
    DATASET = $(PG_DB)
    SQL_STATEMENT = @Value(sql)
    POSTGRES_PORT = $(PG_PORT)
    COMBINE_GEOM = Initiator Geometry Only
    POSTGRES_USER_NAME = $(PG_USER)
    COMBINE_ATTRS = Result Attributes Only
    POSTGRES_QUERY_FEATURE_TYPES_FOR_MERGE_FILTERS = Yes
    POSTGRES_PASSWORD = $(PG_PWD)
    EXPOSED_ATTRIBUTE_LIST = annet1,annet2,fluoriserende1,fluoriserende2,harmerkingfk,kommentarmerkingmonster,kommentarmerkingtype,merkingfarge1,merkingfarge2,merkingicao,merkingmonster,merkingtilstand,merkingtype,objid,reflekterende1,reflekterende2,versjonid
    FORMAT = POSTGRES
    RESULT -> AttributeCreator_7
AttributeCreator_10
    ATTR_LIST = sql,select * from nrl.lyssetting where harlyssettingfk in (@Value(objid));
    -> SQLExecutor_2
SQLExecutor_2
    POSTGRES_HOST = $(PG_HOST)
    DATASET = $(PG_DB)
    SQL_STATEMENT = @Value(sql)
    POSTGRES_PORT = $(PG_PORT)
    COMBINE_GEOM = Initiator Geometry Only
    POSTGRES_USER_NAME = $(PG_USER)
    COMBINE_ATTRS = Result Attributes Only
    POSTGRES_QUERY_FEATURE_TYPES_FOR_MERGE_FILTERS = Yes
    POSTGRES_PASSWORD = $(PG_PWD)
    EXPOSED_ATTRIBUTE_LIST = harlyssettingfk,lystype,objid,versjonid
    FORMAT = POSTGRES
    RESULT -> UUIDGenerator_3
UUIDGenerator_3
    UUID_ATTR = gml_id
    -> AttributeCreator_15
AttributeCreator_15
    ATTR_LIST = gml_id,NRL_@Value(gml_id)
    -> AttributeCreator_5

Bookmark: Klipper
Clipper
    CLIP_TYPE = Multiple Clippers
    ATTR_ACCUM_MODE = Merge Clipper
    BOUNDARY_CASES = Treat as Inside
    CLIPPED_ATTR = _clipped
    ATTR_CONFLICT_RES = Use Clippee
    CREATE_AGGREGATES = No
    PRESERVE_CLIPPEE_EXTENTS = No
    INSIDE -> DuplicateRemover
    INSIDE -> DuplicateRemover_2
    INSIDE -> UUIDGenerator
UUIDGenerator
    UUID_ATTR = gml_id
    -> AttributeCreator_13
AttributeCreator_13
    ATTR_LIST = gml_id,NRL_@Value(gml_id)
    -> SosiFilenameSetter

Bookmark: Tagger og reprojiserer
SosiFilenameSetter
    _FNR = @Value(_fnr)
    HOYDEVERDIENHET = @Value(hoydeverdienhet)
    NAVN = @Value(navn)
    HREF = @Value(href)
    OPPDATERINGSDATO = @Value(oppdateringsdato)
    EKSTERNID = @Value(eksternid)
    NAVNEROM = @Value(navnerom)
    _CREATION_INSTANCE = @Value(_creation_instance)
    BSLE21HINDER = @Value(bsle21hinder)
    HREFSYSTEM = @Value(hrefsystem)
    PG_PORT:
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------

      import fme
      from xml.etree import ElementTree as ET

      #Read XML config file
      configtree = ET.parse(fme.macroValues['CONFIG_FILE'])
      configdoc = configtree.getroot()
      value = configdoc.find('pgport').text

      return value
    BESTARAVVERTIKALOBJEKTKOMPONENTFK = @Value(bestaravvertikalobjektkomponentfk)
    MERKEPLIKTIG = @Value(merkepliktig)
    REGISTERNAVN = @Value(registernavn)
    KOMMUNEID = @Value(kommuneid)
    LENGDEVERDIENHET = @Value(lengdeverdienhet)
    SYNBARHET = @Value(synbarhet)
    UNDERTEMA = $(UNDERTEMA)
    LOKALID = @Value(lokalid)
    HOVEDTEMA = $(HOVEDTEMA)
    BREKKBAR = @Value(brekkbar)
    PG_PWD:
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------

      import fme
      from xml.etree import ElementTree as ET

      #Read XML config file
      configtree = ET.parse(fme.macroValues['CONFIG_FILE'])
      configdoc = configtree.getroot()
      value = configdoc.find('pgpwd').text

      return value
    PG_HOST:
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------

      import fme
      from xml.etree import ElementTree as ET

      #Read XML config file
      configtree = ET.parse(fme.macroValues['CONFIG_FILE'])
      configdoc = configtree.getroot()
      value = configdoc.find('pghost').text

      return value
    _CLIPPERCOORDS = @Value(_clippercoords)
    PG_DB:
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------

      import fme
      from xml.etree import ElementTree as ET

      #Read XML config file
      configtree = ET.parse(fme.macroValues['CONFIG_FILE'])
      configdoc = configtree.getroot()
      value = configdoc.find('pgdb').text

      return value
    TYPEENDRING = @Value(typeendring)
    VERSJONID = @Value(versjonid)
    FANOUT = $(FANOUT)
    _CLIPPER_FILE = @Value(_clipper_file)
    OBJID = @Value(objid)
    H_NOYAKTIGHET = @Value(h_noyaktighet)
    VERTIKALUTSTREKNING = @Value(vertikalutstrekning)
    LINJESPENN = @Value(linjespenn)
    NOYAKTIGHET = @Value(noyaktighet)
    MALEMETODEHOYDE = @Value(malemetodehoyde)
    _KNR = @Value(_knr)
    PG_USER:
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------

      import fme
      from xml.etree import ElementTree as ET

      #Read XML config file
      configtree = ET.parse(fme.macroValues['CONFIG_FILE'])
      configdoc = configtree.getroot()
      value = configdoc.find('pguser').text

      return value
    KOMPONENTSEKVNR = @Value(komponentsekvnr)
    MALEMETODE = @Value(malemetode)
    _CLIPPED = @Value(_clipped)
    VERIFISERINGSDATO = @Value(verifiseringsdato)
    MERKEPLIKTIGIHENHOLDTIL = @Value(merkepliktigihenholdtil)
    KOMMENTARMERKEPLIKT = @Value(kommentarmerkeplikt)
    OBJTYPE = @Value(objtype)
    FYLKEID = @Value(fylkeid)
    STATUS = @Value(status)
    OUTPUT_EPSG_CODE = $(OUTPUT_EPSG_CODE)
    MERKEINFORMASJON = @Value(merkeinformasjon)
    ENDRET_TID = @Value(endret_tid)
    LENGDE = @Value(lengde)
    MOBILITET = @Value(mobilitet)
    ANSVARLIGFORMERKING = @Value(ansvarligformerking)
    -> AttributeCreator_3
    -> Reprojector
Reprojector
    RASTER_CELL_SIZE = Preserve Cells
    INTERPOLATION_TYPE_NAME = Nearest Neighbor
    SOURCE = Read from feature
    DEST = $(DESTCOORDSYS)
    REPROJECTED -> AttributeCreator
AttributeCreator
    ATTR_LIST = OBJTYPE,@Value(objtype),linjespenn,"FME_CONDITIONAL:DEFAULT_VALUE'FME_NULL_VALUE'BOOL_OP;OR;COMPOSITE_TEST;<Unused>;TEST @Value(linjespenn) = t'1'BOOL_OP;OR;COMPOSITE_TEST;<Unused>;TEST @Value(linjespenn) = f'0'FME_NUM_CONDITIONS3___",mobilitet,"FME_CONDITIONAL:DEFAULT_VALUE'FME_NULL_VALUE'BOOL_OP;OR;COMPOSITE_TEST;<Unused>;TEST @Value(mobilitet) = t'1'BOOL_OP;OR;COMPOSITE_TEST;<Unused>;TEST @Value(mobilitet) = f'0'FME_NUM_CONDITIONS3___",bsle21hinder,"FME_CONDITIONAL:DEFAULT_VALUE'FME_NULL_VALUE'BOOL_OP;OR;COMPOSITE_TEST;<Unused>;TEST @Value(bsle21hinder) = t'1'BOOL_OP;OR;COMPOSITE_TEST;<Unused>;TEST @Value(bsle21hinder) = f'0'FME_NUM_CONDITIONS3___",lokalid,@Value(objid),navnerom,NO.KARTVERKET.NRL
    -> FeatureTypeFilter
FeatureTypeFilter
    ATTRIBUTES = nrl.vertikalobjektkomponentpunkt,nrl.vertikalobjektkomponentlinje,<BLANK>,<UNFILTERED>
    nrl.vertikalobjektkomponentlinje -> SpatialRelator [input 1]
    nrl.vertikalobjektkomponentpunkt -> AttributeCreator_4
    nrl.vertikalobjektkomponentpunkt -> SpatialRelator_2 [input 1]
    nrl.vertikalobjektkomponentlinje -> AttributeCreator_6

Bookmark: Topologiske relasjoner
AttributeCreator_6
    ATTR_LIST = lokalid,@Value(objid),navnerom,NO.KARTVERKET.NRL
    -> AttributeRemover_3
AttributeRemover_3
    REMOVE_ATTRS = ansvarligformerking,bestaravvertikalobjektkomponentfk,brekkbar,bsle21hinder,eksternid,endret_tid,h_noyaktighet,hoydeverdienhet,href,hrefsystem,kommentarmerkeplikt,komponentsekvnr,lengde,lengdeverdienhet,linjespenn,malemetode,malemetodehoyde,merkeinformasjon,merkepliktig,merkepliktigihenholdtil,mobilitet,noyaktighet,objid,objtype,OBJTYPE,oppdateringsdato,registernavn,status,synbarhet,typeendring,verifiseringsdato,vertikalutstrekning
    -> SpatialRelator_2 [input 2]
SpatialRelator_2
    CURVE_BOUNDARY_RULE_PARAM = Default Rule
    LIST_NAME = L:avgrenserlinje
    PREDICATES = TOUCHES
    CALC_CARD = No
    SUCCESS_ATTR = _related_candidates
    -> FeatureMerger_3 [input 1]
AttributeCreator_4
    ATTR_LIST = lokalid,@Value(objid),navnerom,NO.KARTVERKET.NRL
    -> AttributeRemover_2
AttributeRemover_2
    REMOVE_ATTRS = ansvarligformerking,bestaravvertikalobjektkomponentfk,brekkbar,bsle21hinder,eksternid,endret_tid,h_noyaktighet,hoydeverdienhet,href,hrefsystem,kommentarmerkeplikt,komponentsekvnr,lengde,lengdeverdienhet,linjespenn,malemetode,malemetodehoyde,merkeinformasjon,merkepliktig,merkepliktigihenholdtil,mobilitet,noyaktighet,objid,objtype,OBJTYPE,oppdateringsdato,registernavn,status,synbarhet,typeendring,verifiseringsdato,vertikalutstrekning
    -> SpatialRelator [input 2]
SpatialRelator
    CURVE_BOUNDARY_RULE_PARAM = Default Rule
    LIST_NAME = L:avgrensesav
    PREDICATES = TOUCHES
    CALC_CARD = No
    SUCCESS_ATTR = _related_candidates
    -> FeatureMerger_2 [input 1]

Bookmark: Bygger vertikalobjekter
AttributeCreator_3
    ATTR_LIST = lokalid,@Value(objid),navnerom,NO.KARTVERKET.NRL
    -> AttributeRemover
AttributeRemover
    REMOVE_ATTRS = ansvarligformerking,brekkbar,bsle21hinder,eksternid,endret_tid,h_noyaktighet,hoydeverdienhet,href,hrefsystem,kommentarmerkeplikt,komponentsekvnr,lengde,lengdeverdienhet,linjespenn,malemetode,malemetodehoyde,merkeinformasjon,merkepliktig,merkepliktigihenholdtil,mobilitet,noyaktighet,objid,objtype,oppdateringsdato,registernavn,status,synbarhet,typeendring,verifiseringsdato,vertikalutstrekning
    -> FeatureMerger [input 2]
AttributeCreator_2
    ATTR_LIST = OBJTYPE,@Value(objtype),vertikalobjektgruppe,"FME_CONDITIONAL:DEFAULT_VALUE'FME_NULL_VALUE'BOOL_OP;OR;COMPOSITE_TEST;<Unused>;TEST @Value(vertikalobjektgruppe) = t'1'BOOL_OP;OR;COMPOSITE_TEST;<Unused>;TEST @Value(vertikalobjektgruppe) = f'0'FME_NUM_CONDITIONS3___",lokalid,@Value(objid),navnerom,NRL.KARTVERKET.NRL
    -> FeatureMerger [input 1]
FeatureMerger
    ATTR_ACCUM_MODE = Merge Supplier
    JOIN_KEYS = @Value(objid) @Value(bestaravvertikalobjektkomponentfk) AUTO
    PROCESS_DUPS = No
    MERGE_TYPE = Attributes Only
    SUPPLIERS_FIRST = No
    IGNORE_NULLS = No
    LIST_NAME = L:komponenter
    ATTR_CONFLICT_RES = Use Requestor
    MERGED -> CoordinateSystemSetter

Bookmark: Prosessering av VertikalObjekt
CoordinateSystemSetter
    COORDSYS = $(DESTCOORDSYS)
    -> ListRenamer_15
ListRenamer_15
    LIST_NAME = L:komponenter{}.gml_id
    LIST_COMPONENT_NAMES = L:komponenter{},komponent{},gml_id,xlink_href
    LEAVE_ORIG = No
    LIST_ACTION = Rename
    -> AttributeRenamer_4
AttributeRenamer_4
    ATTR_LIST = vertikalobjektnavn,vertikalObjektNavn,,vertikalobjektgruppe,vertikalObjektGruppe,,vertikalobjekttype,vertikalObjektType,,endret_tid,endringsflagg.Endringsflagg.tidspunktEndring,,typeendring,endringsflagg.Endringsflagg.typeEndring,,gyldigfra,gyldigFra,,gyldigtil,gyldigTil,,navnerom,identifikasjon.Identifikasjon.navnerom,,lokalid,identifikasjon.Identifikasjon.lokalId,,versjonid,identifikasjon.Identifikasjon.versjonId,,informasjon,informasjon{0},,kommentarvertobjtype,kommentarVertikalObjektType,
    -> DateFormatter_3
DateFormatter_3
    INVALID_DATE_VALUE = _FME_NO_OP_
    SRCFMT = Unknown - Automatic Detection
    FMT = ISO DateTime (%Y-%m-%dT%H:%M:%S)
    DATE_ATTR = datafangstdato,gyldigFra,gyldigTil,oppdateringsdato,endringsflagg.Endringsflagg.tidspunktEndring
    -> GeometryRemover
GeometryRemover
    -> VertikalObjekt (writer GML_1)
VertikalObjekt (writer GML_1)
    attributes: datafangstdato xml_datetime, endringsflagg.Endringsflagg.typeEndring xml_buffer, endringsflagg.Endringsflagg.tidspunktEndring xml_datetime, gyldigFra xml_datetime, gyldigTil xml_datetime, identifikasjon.Identifikasjon.lokalId xml_buffer, identifikasjon.Identifikasjon.navnerom xml_buffer, identifikasjon.Identifikasjon.versjonId xml_buffer, informasjon{} xml_buffer, link{} xml_buffer, oppdateringsdato xml_datetime, opphav xml_buffer, status xml_buffer, kommentarVertikalObjektType xml_buffer, kontakt{}.Kontakt.kontaktnavn xml_buffer, kontakt{}.Kontakt.adresse.Vegadresse.adressekode xml_int64, kontakt{}.Kontakt.adresse.Vegadresse.adressenavn xml_buffer, kontakt{}.Kontakt.adresse.Vegadresse.bokstav xml_buffer, kontakt{}.Kontakt.adresse.Vegadresse.kommunenummer xml_int64, kontakt{}.Kontakt.adresse.Vegadresse.nummer xml_int64, kontakt{}.Kontakt.telefon{} xml_buffer, kontakt{}.Kontakt.ePost xml_buffer, kontakt{}.Kontakt.firmanavn xml_buffer, kontakt{}.Kontaktperson.kontaktnavn xml_buffer, kontakt{}.Kontaktperson.adresse.Vegadresse.adressekode xml_int64, kontakt{}.Kontaktperson.adresse.Vegadresse.adressenavn xml_buffer, kontakt{}.Kontaktperson.adresse.Vegadresse.bokstav xml_buffer, kontakt{}.Kontaktperson.adresse.Vegadresse.kommunenummer xml_int64, kontakt{}.Kontaktperson.adresse.Vegadresse.nummer xml_int64, kontakt{}.Kontaktperson.telefon{} xml_buffer,
      kontakt{}.Kontaktperson.ePost xml_buffer, kontakt{}.Kontaktperson.firmanavn xml_buffer, kontakt{}.Eier.kontaktnavn xml_buffer, kontakt{}.Eier.adresse.Vegadresse.adressekode xml_int64, kontakt{}.Eier.adresse.Vegadresse.adressenavn xml_buffer, kontakt{}.Eier.adresse.Vegadresse.bokstav xml_buffer, kontakt{}.Eier.adresse.Vegadresse.kommunenummer xml_int64, kontakt{}.Eier.adresse.Vegadresse.nummer xml_int64, kontakt{}.Eier.telefon{} xml_buffer, kontakt{}.Eier.ePost xml_buffer, kontakt{}.Eier.firmanavn xml_buffer, kontakt{}.Innmelder.kontaktnavn xml_buffer, kontakt{}.Innmelder.adresse.Vegadresse.adressekode xml_int64, kontakt{}.Innmelder.adresse.Vegadresse.adressenavn xml_buffer, kontakt{}.Innmelder.adresse.Vegadresse.bokstav xml_buffer, kontakt{}.Innmelder.adresse.Vegadresse.kommunenummer xml_int64, kontakt{}.Innmelder.adresse.Vegadresse.nummer xml_int64, kontakt{}.Innmelder.telefon{} xml_buffer, kontakt{}.Innmelder.ePost xml_buffer, kontakt{}.Innmelder.firmanavn xml_buffer, matrikkelID{}.Matrikkelnummer.kommunenummer xml_buffer, matrikkelID{}.Matrikkelnummer.gårdsnummer xml_int64, matrikkelID{}.Matrikkelnummer.bruksnummer xml_int64, matrikkelID{}.Matrikkelnummer.festenummer xml_int64, matrikkelID{}.Matrikkelnummer.seksjonsnummer xml_int64, vertikalObjektGruppe xml_boolean, vertikalObjektNavn xml_buffer, vertikalObjektType xml_buffer, komponent{}.nilReason xml_buffer, komponent{}.gml_remoteSchema xml_buffer,
      komponent{}.xlink_href xml_buffer, komponent{}.owns xml_boolean

Bookmark: Setter standardattributter
AttributeCreator_7
    ATTR_LIST = lokalid,@Value(objid),navnerom,NO.KARTVERKET.NRL
    -> FeatureMerger_4 [input 2]
    -> FeatureMerger_5 [input 2]
AttributeCreator_5
    ATTR_LIST = lokalid,@Value(objid),navnerom,NO.KARTVERKET.NRL
    -> FeatureMerger_2 [input 2]
    -> FeatureMerger_3 [input 2]

Bookmark: Lyssetting
FeatureMerger_3
    ATTR_ACCUM_MODE = Merge Supplier
    JOIN_KEYS = @Value(objid) @Value(harlyssettingfk) AUTO
    PROCESS_DUPS = No
    MERGE_TYPE = Attributes Only
    SUPPLIERS_FIRST = No
    IGNORE_NULLS = No
    LIST_NAME = L:lyssetting
    ATTR_CONFLICT_RES = Use Requestor
    NOT_MERGED -> FeatureMerger_5 [input 1]
    MERGED -> AttributeRenamer_3
    MERGED -> FeatureMerger_5 [input 1]
FeatureMerger_2
    ATTR_ACCUM_MODE = Merge Supplier
    JOIN_KEYS = @Value(objid) @Value(harlyssettingfk) AUTO
    PROCESS_DUPS = No
    MERGE_TYPE = Attributes Only
    SUPPLIERS_FIRST = No
    IGNORE_NULLS = No
    LIST_NAME = L:lyssetting
    ATTR_CONFLICT_RES = Use Requestor
    MERGED -> FeatureMerger_4 [input 1]
    NOT_MERGED -> FeatureMerger_4 [input 1]

Bookmark: Merking
FeatureMerger_5
    ATTR_ACCUM_MODE = Merge Supplier
    JOIN_KEYS = @Value(objid) @Value(harmerkingfk) AUTO
    PROCESS_DUPS = No
    MERGE_TYPE = Attributes Only
    SUPPLIERS_FIRST = No
    IGNORE_NULLS = No
    LIST_NAME = L:merking
    ATTR_CONFLICT_RES = Use Requestor
    NOT_MERGED -> AttributeRenamer_2
    MERGED -> AttributeRenamer_2
FeatureMerger_4
    ATTR_ACCUM_MODE = Merge Supplier
    JOIN_KEYS = @Value(objid) @Value(harmerkingfk) AUTO
    PROCESS_DUPS = No
    MERGE_TYPE = Attributes Only
    SUPPLIERS_FIRST = No
    IGNORE_NULLS = No
    LIST_NAME = L:merking
    ATTR_CONFLICT_RES = Use Requestor
    MERGED -> AttributeRenamer
    NOT_MERGED -> AttributeRenamer

Bookmark: Listehåndtering
ListRenamer_16
    LIST_NAME = L:merking{}.fluoriserende1
    LIST_COMPONENT_NAMES = L:merking{},merking{},fluoriserende1,Merking.merkingFarge1.Farge.fluoriserende
    LEAVE_ORIG = Yes
    LIST_ACTION = Rename
    -> ListRenamer_19
ListRenamer_19
    LIST_NAME = L:merking{}.merkingfarge1
    LIST_COMPONENT_NAMES = L:merking{},merking{},merkingfarge1,Merking.merkingFarge1.Farge.farge
    LEAVE_ORIG = Yes
    LIST_ACTION = Rename
    -> ListRenamer_20
ListRenamer_20
    LIST_NAME = L:merking{}.annet1
    LIST_COMPONENT_NAMES = L:merking{},merking{},annet1,Merking.merkingFarge1.Farge.annet
    LEAVE_ORIG = Yes
    LIST_ACTION = Rename
    -> ListRenamer_21
ListRenamer_21
    LIST_NAME = L:merking{}.reflekterende1
    LIST_COMPONENT_NAMES = L:merking{},merking{},reflekterende1,Merking.merkingFarge1.Farge.reflekterende
    LEAVE_ORIG = Yes
    LIST_ACTION = Rename
    -> ListRenamer_22
ListRenamer_22
    LIST_NAME = L:merking{}.fluoriserende2
    LIST_COMPONENT_NAMES = L:merking{},merking{},fluoriserende2,Merking.merkingFarge2.Farge.fluoriserende
    LEAVE_ORIG = Yes
    LIST_ACTION = Rename
    -> ListRenamer_23
ListRenamer_23
    LIST_NAME = L:merking{}.merkingfarge2
    LIST_COMPONENT_NAMES = L:merking{},merking{},merkingfarge2,Merking.merkingFarge2.Farge.farge
    LEAVE_ORIG = Yes
    LIST_ACTION = Rename
    -> ListRenamer_24
ListRenamer_24
    LIST_NAME = L:merking{}.annet2
    LIST_COMPONENT_NAMES = L:merking{},merking{},annet2,Merking.merkingFarge2.Farge.annet
    LEAVE_ORIG = Yes
    LIST_ACTION = Rename
    -> ListRenamer_25
ListRenamer_25
    LIST_NAME = L:merking{}.reflekterende2
    LIST_COMPONENT_NAMES = L:merking{},merking{},reflekterende2,Merking.merkingFarge2.Farge.reflekterende
    LEAVE_ORIG = Yes
    LIST_ACTION = Rename
    -> ListRenamer_26
ListRenamer_26
    LIST_NAME = L:merking{}.merkingtype
    LIST_COMPONENT_NAMES = L:merking{},merking{},merkingtype,Merking.merkingType
    LEAVE_ORIG = Yes
    LIST_ACTION = Rename
    -> ListRenamer_27
ListRenamer_27
    LIST_NAME = L:merking{}.reflekterende2
    LIST_COMPONENT_NAMES = L:merking{},merking{},reflekterende2,Merking.kommentarMerkingType
    LEAVE_ORIG = Yes
    LIST_ACTION = Rename
    -> ListRenamer_28
ListRenamer_28
    LIST_NAME = L:merking{}.merkingmonster
    LIST_COMPONENT_NAMES = L:merking{},merking{},merkingmonster,Merking.merkingMønster
    LEAVE_ORIG = Yes
    LIST_ACTION = Rename
    -> ListRenamer_29
ListRenamer_29
    LIST_NAME = L:merking{}.kommentarmerkingmonster
    LIST_COMPONENT_NAMES = L:merking{},merking{},kommentarmerkingmonster,Merking.kommentarMerkingMønster
    LEAVE_ORIG = Yes
    LIST_ACTION = Rename
    -> ListRenamer_30
ListRenamer_30
    LIST_NAME = L:merking{}.merkingicao
    LIST_COMPONENT_NAMES = L:merking{},merking{},merkingicao,Merking.merkingICAO
    LEAVE_ORIG = Yes
    LIST_ACTION = Rename
    -> ListRenamer_31
ListRenamer_31
    LIST_NAME = L:merking{}.reflekterende2
    LIST_COMPONENT_NAMES = L:merking{},merking{},reflekterende2,Merking.merkingTilstand
    LEAVE_ORIG = Yes
    LIST_ACTION = Rename
    -> ListRenamer_17

Bookmark: Listehåndtering
ListRenamer
    LIST_NAME = L:merking{}.fluoriserende1
    LIST_COMPONENT_NAMES = L:merking{},merking{},fluoriserende1,Merking.merkingFarge1.Farge.fluoriserende
    LEAVE_ORIG = Yes
    LIST_ACTION = Rename
    -> ListRenamer_2
ListRenamer_2
    LIST_NAME = L:merking{}.merkingfarge1
    LIST_COMPONENT_NAMES = L:merking{},merking{},merkingfarge1,Merking.merkingFarge1.Farge.farge
    LEAVE_ORIG = Yes
    LIST_ACTION = Rename
    -> ListRenamer_3
ListRenamer_3
    LIST_NAME = L:merking{}.annet1
    LIST_COMPONENT_NAMES = L:merking{},merking{},annet1,Merking.merkingFarge1.Farge.annet
    LEAVE_ORIG = Yes
    LIST_ACTION = Rename
    -> ListRenamer_4
ListRenamer_4
    LIST_NAME = L:merking{}.reflekterende1
    LIST_COMPONENT_NAMES = L:merking{},merking{},reflekterende1,Merking.merkingFarge1.Farge.reflekterende
    LEAVE_ORIG = Yes
    LIST_ACTION = Rename
    -> ListRenamer_5
ListRenamer_5
    LIST_NAME = L:merking{}.fluoriserende2
    LIST_COMPONENT_NAMES = L:merking{},merking{},fluoriserende2,Merking.merkingFarge2.Farge.fluoriserende
    LEAVE_ORIG = Yes
    LIST_ACTION = Rename
    -> ListRenamer_6
ListRenamer_6
    LIST_NAME = L:merking{}.merkingfarge2
    LIST_COMPONENT_NAMES = L:merking{},merking{},merkingfarge2,Merking.merkingFarge2.Farge.farge
    LEAVE_ORIG = Yes
    LIST_ACTION = Rename
    -> ListRenamer_7
ListRenamer_7
    LIST_NAME = L:merking{}.annet2
    LIST_COMPONENT_NAMES = L:merking{},merking{},annet2,Merking.merkingFarge2.Farge.annet
    LEAVE_ORIG = Yes
    LIST_ACTION = Rename
    -> ListRenamer_8
ListRenamer_8
    LIST_NAME = L:merking{}.reflekterende2
    LIST_COMPONENT_NAMES = L:merking{},merking{},reflekterende2,Merking.merkingFarge2.Farge.reflekterende
    LEAVE_ORIG = Yes
    LIST_ACTION = Rename
    -> ListRenamer_9
ListRenamer_9
    LIST_NAME = L:merking{}.merkingtype
    LIST_COMPONENT_NAMES = L:merking{},merking{},merkingtype,Merking.merkingType
    LEAVE_ORIG = Yes
    LIST_ACTION = Rename
    -> ListRenamer_10
ListRenamer_10
    LIST_NAME = L:merking{}.reflekterende2
    LIST_COMPONENT_NAMES = L:merking{},merking{},reflekterende2,Merking.kommentarMerkingType
    LEAVE_ORIG = Yes
    LIST_ACTION = Rename
    -> ListRenamer_11
ListRenamer_11
    LIST_NAME = L:merking{}.merkingmonster
    LIST_COMPONENT_NAMES = L:merking{},merking{},merkingmonster,Merking.merkingMønster
    LEAVE_ORIG = Yes
    LIST_ACTION = Rename
    -> ListRenamer_12
ListRenamer_12
    LIST_NAME = L:merking{}.kommentarmerkingmonster
    LIST_COMPONENT_NAMES = L:merking{},merking{},kommentarmerkingmonster,Merking.kommentarMerkingMønster
    LEAVE_ORIG = Yes
    LIST_ACTION = Rename
    -> ListRenamer_13
ListRenamer_13
    LIST_NAME = L:merking{}.merkingicao
    LIST_COMPONENT_NAMES = L:merking{},merking{},merkingicao,Merking.merkingICAO
    LEAVE_ORIG = Yes
    LIST_ACTION = Rename
    -> ListRenamer_14
ListRenamer_14
    LIST_NAME = L:merking{}.reflekterende2
    LIST_COMPONENT_NAMES = L:merking{},merking{},reflekterende2,Merking.merkingTilstand
    LEAVE_ORIG = Yes
    LIST_ACTION = Rename
    -> ListRenamer_18
ListRenamer_18
    LIST_NAME = L:avgrensesav{}.gml_id
    LIST_COMPONENT_NAMES = L:avgrensesav{},avgrensesAv{},gml_id,xlink_href
    LEAVE_ORIG = No
    LIST_ACTION = Rename
    -> NullAttributeMapper

FME custom transformer SosiFilenameSetter

Parameters:
- OUTPUT_EPSG_CODE = 25832   # Destination coordinate system
- FANOUT = Kommuner   # Fanout områder
- _CLIPPED = @Value(_clipped)   # Clipped
- _CLIPPER_FILE = @Value(_clipper_file)   # Clipper File
- _CLIPPERCOORDS = @Value(_clippercoords)   # Clippercoords
- _CREATION_INSTANCE = @Value(_creation_instance)   # Creation Instance
- _FNR = @Value(_fnr)   # Fnr
- _KNR = @Value(_knr)   # Knr
- ANSVARLIGFORMERKING = @Value(ansvarligformerking)   # ansvarligformerking
- BESTARAVVERTIKALOBJEKTKOMPONENTFK = @Value(bestaravvertikalobjektkomponentfk)   # bestaravvertikalobjektkomponentfk
- BREKKBAR = @Value(brekkbar)   # brekkbar
- BSLE21HINDER = @Value(bsle21hinder)   # bsle21hinder
- EKSTERNID = @Value(eksternid)   # eksternid
- ENDRET_TID = @Value(endret_tid)   # Endret Tid
- FYLKEID = @Value(fylkeid)   # fylkeid
- H_NOYAKTIGHET = @Value(h_noyaktighet)   # H Noyaktighet
- HOYDEVERDIENHET = @Value(hoydeverdienhet)   # hoydeverdienhet
- HREF = @Value(href)   # href
- HREFSYSTEM = @Value(hrefsystem)   # hrefsystem
- KOMMENTARMERKEPLIKT = @Value(kommentarmerkeplikt)   # kommentarmerkeplikt
- KOMMUNEID = @Value(kommuneid)   # kommuneid
- KOMPONENTSEKVNR = @Value(komponentsekvnr)   # komponentsekvnr
- LENGDE = @Value(lengde)   # lengde
- LENGDEVERDIENHET = @Value(lengdeverdienhet)   # lengdeverdienhet
- LINJESPENN = @Value(linjespenn)   # linjespenn
- LOKALID = @Value(lokalid)   # lokalid
- MALEMETODE = @Value(malemetode)   # malemetode
- MALEMETODEHOYDE = @Value(malemetodehoyde)   # malemetodehoyde
- MERKEINFORMASJON = @Value(merkeinformasjon)   # merkeinformasjon
- MERKEPLIKTIG = @Value(merkepliktig)   # merkepliktig
- MERKEPLIKTIGIHENHOLDTIL = @Value(merkepliktigihenholdtil)   # merkepliktigihenholdtil
- MOBILITET = @Value(mobilitet)   # mobilitet
- NAVN = @Value(navn)   # navn
- NAVNEROM = @Value(navnerom)   # navnerom
- NOYAKTIGHET = @Value(noyaktighet)   # noyaktighet
- OBJID = @Value(objid)   # objid
- OBJTYPE = @Value(objtype)   # objtype
- OPPDATERINGSDATO = @Value(oppdateringsdato)   # oppdateringsdato
- REGISTERNAVN = @Value(registernavn)   # registernavn
- STATUS = @Value(status)   # status
- SYNBARHET = @Value(synbarhet)   # synbarhet
- TYPEENDRING = @Value(typeendring)   # typeendring
- VERIFISERINGSDATO = @Value(verifiseringsdato)   # verifiseringsdato
- VERSJONID = @Value(versjonid)   # versjonid
- VERTIKALUTSTREKNING = @Value(vertikalutstrekning)   # vertikalutstrekning
- UNDERTEMA =   # Undertema
- HOVEDTEMA =   # Hovedtema
- PG_DB:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgdb').text
      
      return value
- PG_HOST:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pghost').text
      
      return value
- PG_PORT:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgport').text
      
      return value
- PG_PWD:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgpwd').text
      
      return value
- PG_USER:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pguser').text
      
      return value

Input (input)
    -> ParameterFetcher
ParameterFetcher
    ATTR_LIST = _output_epsg_code {$(OUTPUT_EPSG_CODE)} _fanout {$(FANOUT)}
    -> AttributeValueMapper
Note: Fikser kjente feil i kommunenummer
AttributeValueMapper
    DIRECTION = Forward (Source To Destination)
    LUT = 1901,1903
    VAL_ATTR = kommuneid
    SRC = kommuneid
    DEFAULT_VALUE = @Value(kommuneid)
    -> TestFilter_2
TestFilter_2
    DEFAULT_VALUE = Ufiltrert
    TEST_LIST = BOOL_OP,OR,COMPOSITE_TEST,<Unused>,TEST_CLAUSE,"TEST $(FANOUT) = Kommuner",Kommuner,BOOL_OP,OR,COMPOSITE_TEST,<Unused>,TEST_CLAUSE,"TEST $(FANOUT) = Fylker",Fylker
    Kommuner -> Joiner
    Ufiltrert -> AttributeCreator_13
    Fylker -> Joiner_2
Joiner
    DATASET = $(PG_DB)
    CACHE_SIZE = 5000
    TABLE = admingrense.kommuner
    JOIN_KEYS = kommuneid kommuneid
    ADDED_FIELDS = navn
    MATCH_RULE_DISPLAY = Must Match Exactly One (1:1)
    POSTGIS_DISABLE_COLLECTION_SPLITTING = yes
    POSTGIS_USE_TRUE_POSTGIS_TYPES = yes
    POSTGIS_QUERY_FEATURE_TYPES_FOR_MERGE_FILTERS = Yes
    POSTGIS_HOST = $(PG_HOST)
    PREFETCH_EXHAUSTIVE = Yes
    POSTGIS_PASSWORD = $(PG_PWD)
    POSTGIS_USER_NAME = $(PG_USER)
    FORMAT = POSTGIS
    POSTGIS_PORT = $(PG_PORT)
    JOINED -> StringReplacer
Joiner_2
    DATASET = $(PG_DB)
    CACHE_SIZE = 5000
    TABLE = admingrense.fylkeflate
    JOIN_KEYS = fylkeid fylkeid
    ADDED_FIELDS = navn
    MATCH_RULE_DISPLAY = Must Match Exactly One (1:1)
    POSTGIS_DISABLE_COLLECTION_SPLITTING = yes
    POSTGIS_USE_TRUE_POSTGIS_TYPES = yes
    POSTGIS_QUERY_FEATURE_TYPES_FOR_MERGE_FILTERS = Yes
    POSTGIS_HOST = $(PG_HOST)
    PREFETCH_EXHAUSTIVE = Yes
    POSTGIS_PASSWORD = $(PG_PWD)
    POSTGIS_USER_NAME = $(PG_USER)
    FORMAT = POSTGIS
    POSTGIS_PORT = $(PG_PORT)
    JOINED -> StringReplacer
StringReplacer
    SRC_ATTRS = navn
    CASE = no
    FIND_TEXT = " "
    REGEXP = no
    NO_MATCH = _FME_NO_OP_
    REPLACE_TEXT = _
    -> AttributeCreator_13
AttributeCreator_13
    ATTR_LIST = sosifile,"FME_CONDITIONAL:DEFAULT_VALUE'$(HOVEDTEMA)_$(OUTPUT_EPSG_CODE)_$(UNDERTEMA)_GML'BOOL_OP;OR;COMPOSITE_TEST;<Unused>;TEST $(FANOUT) LIKE Kommuner'$(HOVEDTEMA)_@PadLeft(@Value(kommuneid),4,0)_@Value(navn)_$(OUTPUT_EPSG_CODE)_$(UNDERTEMA)_GML'BOOL_OP;OR;COMPOSITE_TEST;<Unused>;TEST $(FANOUT) LIKE Fylker'$(HOVEDTEMA)_@PadLeft(@Value(fylkeid),2,0)_@Value(navn)_$(OUTPUT_EPSG_CODE)_$(UNDERTEMA)_GML'BOOL_OP;OR;COMPOSITE_TEST;<Unused>;TEST $(FANOUT) LIKE Norge'$(HOVEDTEMA)_0000_Norge_$(OUTPUT_EPSG_CODE)_$(UNDERTEMA)_GML'FME_NUM_CONDITIONS4___"
    -> Output (output)
Output (output)

FME custom transformer CreateClipper

Parameters:
- CLIPPERCOORDS = 253577 6650999 253577 6651246 253763 6651246 253763 6650999 253577 6650999   # Clipper Coordinate List
- CLIPPERCOORDSYS = EPSG:25833   # Clipper Coordinate System
- DESTCOORDSYS = "ESRIWKT|ETRS_1989_UTM_Zone_35N|PROJCS["ETRS_1989_UTM_Zone_35N",GEOGCS["GCS_ETRS_1989",DATUM["D_ETRS_1989",SPHEROID["GRS_1980",6378137.0,298.257222101]],PRIMEM["Greenwich",0.0],UNIT["Degree",0.0174532925199433]],PROJECTION["Transverse_Mercator"],PARAMETER["False_Easting",500000.0],PARAMETER["False_Northing",0.0],PARAMETER["Central_Meridian",27.0],PARAMETER["Scale_Factor",0.9996],PARAMETER["Latitude_Of_Origin",0.0],UNIT["Meter",1.0]]"   # Destination Coordinate System

Note: Creating geometry from / the Clipper coords
Creator
    GEOMTYPE = 2D Coordinate List
    NUM = 1
    COORDSYS = $(CLIPPERCOORDSYS)
    COORDS = $(CLIPPERCOORDS)
    CREATED -> BoundingBoxAccumulator
Note: Calculating the bounding / box (envelope) from the geometry
BoundingBoxAccumulator
    TOPFER_INDEX = No
    BOUNDING_BOX -> SpatialFilter [input 1]
    ORIGINAL -> SpatialFilter [input 2]
Note: If the geometry is equal to its / own bounding box - it is a rectangle!
SpatialFilter
    MERGE_ATTRS = No
    CURVE_BOUNDARY_RULE_PARAM = Default Rule
    PREDICATES = EQUALS
    PREDATTR = _predicate
    USE_BOUNDING_BOX = No
    PASS_CRITERIA = Pass Against One Base
    BASE_TYPE = Single Base
    PASSED -> Reprojector
    FAILED -> Reprojector_2
Note: If rectangle, reproject the / geometry to the destination / coordinate system
Reprojector
    RASTER_CELL_SIZE = Preserve Cells
    INTERPOLATION_TYPE_NAME = Nearest Neighbor
    SOURCE = Read from feature
    DEST = $(DESTCOORDSYS)
    STROKE_ARCS = Yes
    REPROJECTED -> BoundingBoxAccumulator_2
Note: Then calculate the bounding / box from the projected geoemtry
BoundingBoxAccumulator_2
    TOPFER_INDEX = No
    BOUNDING_BOX -> Reprojector_3
Note: Reproject the geometry back to / the DB coordsys (LL/EUREF89)
Reprojector_3
    RASTER_CELL_SIZE = Preserve Cells
    INTERPOLATION_TYPE_NAME = Nearest Neighbor
    SOURCE = Read from feature
    DEST = EPSG:4258
    STROKE_ARCS = Yes
    REPROJECTED -> GeometryFilter
Note: Reproject clipper to / the DB coordsys (LL/EUREF89)
Reprojector_2
    RASTER_CELL_SIZE = Preserve Cells
    INTERPOLATION_TYPE_NAME = Nearest Neighbor
    SOURCE = Read from feature
    DEST = EPSG:4258
    STROKE_ARCS = Yes
    REPROJECTED -> GeometryFilter
Note: Getting rid of dummies
GeometryFilter
    GEOM_PORT_NAMES = Area
    BREAK_AGG = No
    AREA -> Output (output)
Output (output)
