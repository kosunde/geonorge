FME workspace Dekningsanalyse_Geonorge_datahotell.fmw

Parameters:
- SourceDataset_POSTGIS = geonortst@nnridb504:5432/geonor01tst   # Connection
- DestDataset_POSTGRES = geonortst@nnridb504:5432/geonor01tst   # Connection

Readers:
- POSTGIS_1: POSTGIS from $(SourceDataset_POSTGIS)

Writers:
- POSTGRES_1: POSTGRES to $(DestDataset_POSTGRES)

admingrense.kommuneflate (reader POSTGIS_1)
    attributes: kommuneid int4, navn varchar(80)
    -> Deaggregator
Deaggregator
    GEOM_NAME_FIELD = _geometry_name
    ID_SELECTION = ID and Parent ID
    PART_NUMBER_FIELD = _part_number
    SPLIT_COMPOSITES = No
    MODE = Flatten One Level
    LIST_ATTR_MODE_LOOKUP = LEAN
    PARENT_ID_ATTR = _hierarchy_parent_id
    CHILD_ID_ATTR = _hierarchy_child_id_list
    ID_ATTR = _hierarchy_id
    EXPLODE_INSTANCES = No
    COPY_ATTR = Every Node
    DEAGGREGATED -> SpatialFilter [input 2]
    DEAGGREGATED -> SpatialFilter_2 [input 2]
    DEAGGREGATED -> SpatialFilter_3 [input 2]
    DEAGGREGATED -> SpatialFilter_4 [input 2]
    DEAGGREGATED -> SpatialFilter_5 [input 2]
    DEAGGREGATED -> SpatialFilter_6 [input 2]
    DEAGGREGATED -> SpatialFilter_7 [input 2]
dekningsoversikt.dekningsoversikt (writer POSTGRES_1)
    attributes: kommuneid int4, akvakultur bool, korallrev bool, dsb_110sentral bool, dsb_brannstasjon bool, dsb_distrkont_siv bool, dsb_sivforsvdistr bool, ra_brannsmitteomr bool, ra_tettetrehusm bool, ra_frededebygg bool, ra_enkeltminner bool, ra_kulturmiljo bool, ra_lokaliteter bool, ra_sikringssoner bool, kv_hovedbiled bool, kv_ispshavneanlegg bool, kv_losbordingsfelt bool, kv_losstasjoner bool, nve_flomsoner10 bool, nve_flomsoner20 bool, nve_flomsoner50 bool, nve_flomsoner100 bool, nve_flomsoner200 bool, nve_flomsoner500 bool, nve_flomsoner1000 bool, nve_flomsoner200_i_aar2100 bool, nve_flomsonekartplan bool, nve_elvis_hovedelv bool, nve_elvis_elvenett bool, nve_innsjodata bool,
      nve_dybdekart bool, nve_nedborfelt_regine bool, nve_vassdragsomrade bool, nve_totnedbfelt_mstasjon bool, nve_vannkraftverk bool, nve_vindparkomrader bool, nve_vindturbin bool, nve_kraftlinjer bool, nve_sjokabler bool, nve_transformatorstasjoner bool, nve_omradekonsesjoner bool, nve_sikringstiltak bool, nve_verneplan_vassdrag bool, nve_kvikkleire bool, nve_aktsomhet_snoskred bool, nve_aktsomhet_steinsprang bool, nve_aktsomhet_snosteinsprang bool, nve_aktsomhet_jordflomskred bool, nve_skredhendelser bool, nve_kraftverk_alle_kst bool, nve_magasin bool, nve_dam bool, nve_vanninntak bool, nve_vannvei bool, nve_delfelt_vannkraft bool, nve_vindkraftverk bool, nve_skredsoner bool, dsb_anleggfarligstoff bool, dsb_storulykkeanlegg bool, dsb_eksplosivanlegg bool,
      nibio_jordkvalitet bool, md_forurensetgrunn bool, md_frilstatligsikra bool, md_frilkartlverds bool, md_verdif_kulturlandsk bool, md_viktige_naturt bool, md_villreinomr bool, md_naturvernomr bool, md_naturvernomr_foresl bool, md_arter_nasjon_forv bool, md_naturt_landskap bool, md_naturt_utv bool, fkb_ar5 bool, fkb_adresse bool, fkb_arealbruk bool, fkb_bane bool, fkb_bygnanlegg bool, fkb_bygning bool, fkb_bygningspunkt bool, fkb_hoydekurve-5m bool, fkb_hoydekurve bool, fkb_ledning bool, fkb_ledningva bool, fkb_lufthavn bool, fkb_matrikkelkartdekteig bool, fkb_naturinfo bool, fkb_pbltiltak bool, fkb_servitutt bool, fkb_tekst1000 bool, fkb_tekst5000 bool,
      fkb_traktorvegsti bool, fkb_vann bool, fkb_vbase bool, fkb_veg bool, ldir_reinbeitedistrikt bool, ldir_reinbeiteomrade bool, ldir_reindriftsanlegg bool, ldir_beitehage bool, ldir_flyttlei bool, ldir_trekklei bool, ldir_oppsamlingsomrade bool, ldir_varbeite bool, ldir_sommerbeite bool, ldir_hostbeite bool, ldir_hostvinterbeite bool, ldir_vinterbeite bool, ldir_siidagrense bool, ldir_konvensjonsomrade bool, ldir_konsesjonsomrader bool, ldir_restriksjonsomrader bool, ldir_tamreinlag bool, ldir_restriksjonsgrense bool, ldir_rendal bool, ldir_trollheimen bool, ldir_avtaleomrader bool, ldir_ekspropriasjonsomrader bool, avinor_stoysoner bool, forsvaret_stoysoner bool, matrikkel_vegadresser bool, nibio_ar50 bool,
      sk_vbase bool, sk_n50 bool, sk_n250 bool, sk_n500 bool, sk_n1000 bool, sk_n5000 bool, sk_ssr bool, sk_abas bool, matrikkel_bygningspunkt bool, matrikkel_eiendom bool, ngu_losmasser bool, sk_norgesmargrenser bool, sk_sjokartraster bool, id int4,PRIKEY, svv_trafikkmengde bool, svv_trafikkulykker bool, sk_nrl bool, sk_turogfriluft bool, sk_uu_friluft bool, sk_uu_tettsted bool, sk_planomriss bool

Bookmark: NVDB
nvdb_trafikkmengde.trafikkmengde (reader POSTGIS_1)
    attributes: objid serial,PRIKEY, objtype varchar(32), nvdb_aadttotal int4, nvdb_aadtandellangekjoeretoey int4, nvdb_aargjelderfor int4, nvdb_grunnlagforaadt varchar(80), nvdb_ansvarligid varchar(80), nvdb_aadtstart int4, nvdb_aadtslutt int4, nvdb_oppdatertfra varchar(80), nvdb_trafikkarbeidstall int4, nvdb_tellepunktprimaert int4, nvdb_tellepunktsekundaert int4, nvdb_forholdaadt float8, nvdb_forholdlange float8, nvdb_koplingsaar int4, nvdb_mfaktor float8, datauttaksdato timestamp
    -> Deaggregator_2
Deaggregator_2
    GEOM_NAME_FIELD = _geometry_name
    ID_SELECTION = ID and Parent ID
    PART_NUMBER_FIELD = _part_number
    SPLIT_COMPOSITES = No
    MODE = Flatten One Level
    LIST_ATTR_MODE_LOOKUP = LEAN
    PARENT_ID_ATTR = _hierarchy_parent_id
    CHILD_ID_ATTR = _hierarchy_child_id_list
    ID_ATTR = _hierarchy_id
    EXPLODE_INSTANCES = No
    COPY_ATTR = Every Node
    DEAGGREGATED -> SpatialFilter_2 [input 1]
SpatialFilter_2 [off]
    MERGE_ATTRS = Yes
    PASS_CRITERIA = Pass Against One Filter
    PREDICATE_VALUE = Intersects
    PREDATTR = _predicate
    USE_BOUNDING_BOX = No
    BASE_TYPE = Multiple Filters
    CURVE_BOUNDARY_RULE_PARAM = Default Rule
    PASSED -> AttributeCreator_4
    FAILED -> AttributeCreator_5
AttributeCreator_4
    ATTR_LIST = svv_trafikkmengde,1
    -> dekningsoversikt.dekningsoversikt (writer POSTGRES_1)
AttributeCreator_5
    ATTR_LIST = svv_trafikkmengde,0
    -> dekningsoversikt.dekningsoversikt (writer POSTGRES_1)
nvdb_trafikkulykker.trafikkulykke (reader POSTGIS_1)
    attributes: objid serial,PRIKEY, objtype varchar(32), nvdb_alvorligsteskadegrad varchar(80), nvdb_ulykkesdato date, nvdb_ukedag varchar(80), nvdb_registreringsdatofagdata date, nvdb_uhellkategori varchar(80), nvdb_uhellskode varchar(80), nvdb_antallenheter int4, nvdb_antalldrepteiulykken int4, nvdb_antallmegetalvorligskadet int4, nvdb_antallalvorligskadet int4, nvdb_antalllettereskadet int4, nvdb_vegtype varchar(80), nvdb_stedsforhold varchar(80), nvdb_midtdeler varchar(80), nvdb_dekketype varchar(80), nvdb_foereforhold varchar(80), nvdb_vaerforhold varchar(80), nvdb_lysforhold varchar(80), nvdb_felttype varchar(80), nvdb_antallkjoerefelt int4, nvdb_bebyggelse varchar(80), nvdb_vegbredde float8, nvdb_fartsgrense varchar(80), nvdb_temperatur int4, nvdb_kommunenr int4, nvdb_historiskvegstatus varchar(80), nvdb_historiskvegkategori varchar(80), nvdb_historiskvegnummer int4,
      nvdb_historiskhp int4, nvdb_historiskkilometerverdi int4, nvdb_vegnavn varchar(80), nvdb_stedfestingensnoeyaktighet varchar(80), datauttaksdato timestamp, nvdb_ulykkestidspunkt varchar(20)
    -> SpatialFilter [input 1]
SpatialFilter [off]
    MERGE_ATTRS = Yes
    PASS_CRITERIA = Pass Against One Filter
    PREDICATE_VALUE = Intersects
    PREDATTR = _predicate
    USE_BOUNDING_BOX = No
    BASE_TYPE = Multiple Filters
    CURVE_BOUNDARY_RULE_PARAM = Default Rule
    PASSED -> AttributeCreator_2
    FAILED -> AttributeCreator_3
AttributeCreator_2
    ATTR_LIST = svv_trafikkulykker,1
    -> dekningsoversikt.dekningsoversikt (writer POSTGRES_1)
AttributeCreator_3
    ATTR_LIST = svv_trafikkulykker,0
    -> dekningsoversikt.dekningsoversikt (writer POSTGRES_1)

Bookmark: Planomriss
planomriss.rpomrade (reader POSTGIS_1)
    attributes: objid int4,PRIKEY, objtype varchar(32), landkode varchar(2), fylkesnr int2, komm int2, planid varchar(16), forslagsstillertype int2, gjennomforingsfrist date, ikrafttredelsesdato date, kunngjoringsdato date, lovreferanse int2, lovreferansebeskrivelse varchar(255), opprinneligadministrativenhet int2, opprinneligplanid varchar(16), planbestemmelse int2, plannavn varchar(255), planstatus int2, plantype int2, vedtakendeligplandato date, vertikalniva int4
    -> SpatialFilter_3 [input 1]
planomriss.kpomrade (reader POSTGIS_1)
    attributes: objid int4,PRIKEY, objtype varchar(32), landkode varchar(2), fylkesnr int2, komm int2, planid varchar(16), ikrafttredelsesdato date, kunngjoringsdato date, lovreferanse int2, lovreferansebeskrivelse varchar(255), opprinneligadministrativenhet int2, opprinneligplanid varchar(16), planbestemmelse int2, plannavn varchar(255), planstatus int2, plantype int2, vedtakendeligplandato date
    -> SpatialFilter_3 [input 1]
SpatialFilter_3 [off]
    MERGE_ATTRS = Yes
    PASS_CRITERIA = Pass Against One Filter
    PREDICATE_VALUE = Intersects
    PREDATTR = _predicate
    USE_BOUNDING_BOX = No
    BASE_TYPE = Multiple Filters
    CURVE_BOUNDARY_RULE_PARAM = Default Rule
    PASSED -> AttributeCreator_6 [off]
    FAILED -> AttributeCreator_7 [off]
AttributeCreator_6
    ATTR_LIST = sk_planomriss,1
    -> dekningsoversikt.dekningsoversikt (writer POSTGRES_1)
AttributeCreator_7
    ATTR_LIST = sk_planomriss,0
    -> dekningsoversikt.dekningsoversikt (writer POSTGRES_1)

Bookmark: NRL
nrl.vertikalobjektkomponentlinje (reader POSTGIS_1)
    attributes: objid int4,PRIKEY, objtype varchar(80), lengde float8, lengdeverdienhet varchar(80), linjespenn bool, vertikalutstrekning float8, hoydeverdienhet varchar(80), merkepliktig varchar(80), merkepliktigihenholdtil varchar(80), ansvarligformerking varchar(80), merkeinformasjon varchar(80), kommentarmerkeplikt varchar(80), hrefsystem varchar(80), href varchar(80), registernavn varchar(80), eksternid varchar(80), mobilitet bool, komponentsekvnr int4, bsle21hinder bool, bestaravvertikalobjektkomponentfk int4, lokalid uuid, navnerom varchar(80), versjonid varchar(80), verifiseringsdato timestamp, oppdateringsdato timestamp, malemetode varchar(80), noyaktighet int4, synbarhet varchar(80), malemetodehoyde varchar(80), h_noyaktighet int4,
      typeendring varchar(80), endret_tid timestamp, status varchar(80)
    -> SpatialFilter_4 [input 1]
nrl.vertikalobjektkomponentpunkt (reader POSTGIS_1)
    attributes: objid int4,PRIKEY, objtype varchar(80), brekkbar bool, vertikalutstrekning float8, hoydeverdienhet varchar(80), merkepliktig varchar(80), merkepliktigihenholdtil varchar(80), ansvarligformerking varchar(80), merkeinformasjon varchar(80), kommentarmerkeplikt varchar(80), hrefsystem varchar(80), href varchar(80), registernavn varchar(80), eksternid varchar(80), mobilitet bool, komponentsekvnr int4, bsle21hinder bool, bestaravvertikalobjektkomponentfk int4, lokalid uuid, navnerom varchar(80), versjonid varchar(80), verifiseringsdato timestamp, oppdateringsdato timestamp, malemetode varchar(80), noyaktighet int4, synbarhet varchar(80), malemetodehoyde varchar(80), h_noyaktighet int4, typeendring varchar(80), endret_tid timestamp,
      status varchar(80)
    -> SpatialFilter_4 [input 1]
SpatialFilter_4 [off]
    MERGE_ATTRS = Yes
    PASS_CRITERIA = Pass Against One Filter
    PREDICATE_VALUE = Intersects
    PREDATTR = _predicate
    USE_BOUNDING_BOX = No
    BASE_TYPE = Multiple Filters
    CURVE_BOUNDARY_RULE_PARAM = Default Rule
    PASSED -> AttributeCreator_8
    FAILED -> AttributeCreator_9
AttributeCreator_8
    ATTR_LIST = sk_nrl,1
    -> dekningsoversikt.dekningsoversikt (writer POSTGRES_1)
AttributeCreator_9
    ATTR_LIST = sk_nrl,0
    -> dekningsoversikt.dekningsoversikt (writer POSTGRES_1)

Bookmark: Tur og friluftsruter
turogfriluftsruter.sykkelrute (reader POSTGIS_1)
    attributes: objid int4,PRIKEY, objtype varchar(32), spesialsykkelrutetype varchar(80), trafikkbelastning varchar(80), vedlikeh varchar(80), frilufteierforhold varchar(80), belysning varchar(80), rutemerking varchar(80), skilting bool, rutefolger varchar(80), rutebredde varchar(80), opparbeiding varchar(80), rutebetydning varchar(80), rutevanskelighetsgrad varchar(80), underlagstype varchar(80), lengde int4, stigning int4, tilgjengelighetsgruppe varchar(80), rutetype varchar(80), navn varchar(80), rutenr varchar(80), lokalid uuid,PRIKEY, datafangstdato timestamp, oppdateringsdato timestamp, malemetode varchar(80), noyaktighet int4, synbarhet varchar(80), malemetodehoyde varchar(80), h_noyaktighet int4, opphav varchar(80),
      kommune varchar(80), informasjon varchar(80), link varchar(80)
    -> SpatialFilter_5 [input 1]
turogfriluftsruter.skiloype (reader POSTGIS_1)
    attributes: objid int4,PRIKEY, objtype varchar(32), spes_skiloypetype varchar(80), preparering varchar(80), ryddebredde varchar(80), antallskispor int4, skoytetrase bool, vedlikeh varchar(80), frilufteierforhold varchar(80), belysning varchar(80), rutemerking varchar(80), skilting bool, rutefolger varchar(80), rutebredde varchar(80), opparbeiding varchar(80), rutebetydning varchar(80), rutevanskelighetsgrad varchar(80), underlagstype varchar(80), lengde int4, stigning int4, tilgjengelighetsgruppe varchar(80), rutetype varchar(80), navn varchar(80), rutenr varchar(80), lokalid uuid,PRIKEY, datafangstdato timestamp, oppdateringsdato timestamp, malemetode varchar(80), noyaktighet int4, synbarhet varchar(80),
      malemetodehoyde varchar(80), h_noyaktighet int4, opphav varchar(80), kommune varchar(80), informasjon varchar(80), link varchar(80)
    -> SpatialFilter_5 [input 1]
turogfriluftsruter.friluftslivtilrettelegging (reader POSTGIS_1)
    attributes: objid int4,PRIKEY, objtype varchar(32), vedlikeh varchar(80), fritilrettelegging varchar(80), lokalid uuid,PRIKEY, datafangstdato timestamp, oppdateringsdato timestamp, malemetode varchar(80), noyaktighet int4, synbarhet varchar(80), malemetodehoyde varchar(80), h_noyaktighet int4, opphav varchar(80), kommune varchar(80), informasjon varchar(80), link varchar(80)
    -> SpatialFilter_5 [input 1]
turogfriluftsruter.fotrute (reader POSTGIS_1)
    attributes: objid int4,PRIKEY, objtype varchar(32), sfotrutetype varchar(80), sesong varchar(80), vedlikeh varchar(80), frilufteierforhold varchar(80), belysning varchar(80), rutemerking varchar(80), skilting bool, rutefolger varchar(80), rutebredde varchar(80), opparbeiding varchar(80), rutebetydning varchar(80), rutevanskelighetsgrad varchar(80), underlagstype varchar(80), lengde int4, stigning int4, tilgjengelighetsgruppe varchar(80), rutetype varchar(80), navn varchar(80), rutenr varchar(80), lokalid uuid,PRIKEY, datafangstdato timestamp, oppdateringsdato timestamp, malemetode varchar(80), noyaktighet int4, synbarhet varchar(80), malemetodehoyde varchar(80), h_noyaktighet int4, opphav varchar(80),
      kommune varchar(80), informasjon varchar(80), link varchar(80)
    -> SpatialFilter_5 [input 1]
turogfriluftsruter.annenrute (reader POSTGIS_1)
    attributes: objid int4,PRIKEY, objtype varchar(32), arutetype varchar(80), vedlikeh varchar(80), frilufteierforhold varchar(80), belysning varchar(80), rutemerking varchar(80), skilting bool, rutefolger varchar(80), rutebredde varchar(80), opparbeiding varchar(80), rutebetydning varchar(80), rutevanskelighetsgrad varchar(80), underlagstype varchar(80), lengde int4, stigning int4, tilgjengelighetsgruppe varchar(80), rutetype varchar(80), navn varchar(80), rutenr varchar(80), lokalid uuid,PRIKEY, datafangstdato timestamp, oppdateringsdato timestamp, malemetode varchar(80), noyaktighet int4, synbarhet varchar(80), malemetodehoyde varchar(80), h_noyaktighet int4, opphav varchar(80), kommune varchar(80),
      informasjon varchar(80), link varchar(80)
    -> SpatialFilter_5 [input 1]
SpatialFilter_5 [off]
    MERGE_ATTRS = Yes
    PASS_CRITERIA = Pass Against One Filter
    PREDICATE_VALUE = Intersects
    PREDATTR = _predicate
    USE_BOUNDING_BOX = No
    BASE_TYPE = Multiple Filters
    CURVE_BOUNDARY_RULE_PARAM = Default Rule
    PASSED -> AttributeCreator_10
    FAILED -> AttributeCreator_11
AttributeCreator_10
    ATTR_LIST = sk_turogfriluft,1
    -> dekningsoversikt.dekningsoversikt (writer POSTGRES_1)
AttributeCreator_11
    ATTR_LIST = sk_turogfriluft,0
    -> dekningsoversikt.dekningsoversikt (writer POSTGRES_1)

Bookmark: UU Tettsted
uutettsted.uutettstedvei (reader POSTGIS_1)
    attributes: objid int4,PRIKEY, objtype varchar(32), gatetype varchar(80), dekke varchar(80), dekketilstand varchar(80), bredde int4, nedsenk1 float8, nedsenk2 float8, stigning float8, tverrfall float8, moteplass varchar(80), varmekabel varchar(80), lyssignal varchar(80), lydsignal varchar(80), ledelinje varchar(80), ledelinjekontrast varchar(80), tilgjengvurderingrullestol varchar(80), tilgjengvurderingelrullestol varchar(80), tilgjengvurderingsyn varchar(80), ogcfid int4, kommune varchar(80), opphav varchar(80), registrert timestamp, oppdatert timestamp, byggingpagar varchar(80), bilde varchar(80), kommentar varchar(500)
    -> Deaggregator_3
uutettsted.uutettstedparkeringsomrade (reader POSTGIS_1)
    attributes: objid int4,PRIKEY, objtype varchar(32), kapasitetpersonbiler int4, kapasitetuu int4, eierforhold varchar(80), arstidsbruk varchar(80), overbygg varchar(80), varmekabel varchar(80), dekke varchar(80), dekketilstand varchar(80), tilgjengvurderingrullestol varchar(80), tilgjengvurderingelrullestol varchar(80), ogcfid int4, kommune varchar(80), opphav varchar(80), registrert timestamp, oppdatert timestamp, byggingpagar varchar(80), bilde varchar(80), kommentar varchar(500)
    -> Deaggregator_3
uutettsted.uutettstedinngangbygg (reader POSTGIS_1)
    attributes: objid int4,PRIKEY, objtype varchar(32), byggfunksjon varchar(80), avstandvanligparkering int4, avstandhc int4, rampe varchar(80), rampebredde int4, rampestigning float8, handlist varchar(80), handlisthoyde1 int4, handlisthoyde2 int4, rampeterskel float8, rampetilgjengelig varchar(80), dortype varchar(80), dorapner varchar(80), manoverknapphoyde int4, inngangbredde int4, terskelhoyde float8, ringeklokke varchar(80), ringeklokkehoyde int4, stigningadkomstvei float8, kontrast varchar(80), tilgjengvurderingrullestol varchar(80), tilgjengvurderingelrullestol varchar(80), tilgjengvurderingsyn varchar(80), ogcfid int4, kommune varchar(80), opphav varchar(80), registrert timestamp, oppdatert timestamp,
      byggingpagar varchar(80), bilde varchar(80), kommentar varchar(500)
    -> Deaggregator_3
uutettsted.uutettstedhcparkering (reader POSTGIS_1)
    attributes: objid int4,PRIKEY, objtype varchar(32), overbygg varchar(80), varmekabel varchar(80), skiltet varchar(80), merket varchar(80), bredde int4, lengde int4, avstandservicebygg int4, avgift varchar(80), automathoyde int4, tilgjengeligautomat varchar(80), tilgjengvurderingrullestol varchar(80), tilgjengvurderingelrullestol varchar(80), ogcfid int4, kommune varchar(80), opphav varchar(80), registrert timestamp, oppdatert timestamp, byggingpagar varchar(80), bilde varchar(80), kommentar varchar(500)
    -> Deaggregator_3
Deaggregator_3
    GEOM_NAME_FIELD = _geometry_name
    ID_SELECTION = ID and Parent ID
    PART_NUMBER_FIELD = _part_number
    SPLIT_COMPOSITES = No
    MODE = Flatten One Level
    LIST_ATTR_MODE_LOOKUP = LEAN
    PARENT_ID_ATTR = _hierarchy_parent_id
    CHILD_ID_ATTR = _hierarchy_child_id_list
    ID_ATTR = _hierarchy_id
    EXPLODE_INSTANCES = No
    COPY_ATTR = Every Node
    DEAGGREGATED -> SpatialFilter_6 [input 1]
SpatialFilter_6
    MERGE_ATTRS = Yes
    PASS_CRITERIA = Pass Against One Filter
    PREDICATE_VALUE = Intersects
    PREDATTR = _predicate
    USE_BOUNDING_BOX = No
    BASE_TYPE = Multiple Filters
    CURVE_BOUNDARY_RULE_PARAM = Default Rule
    PASSED -> AttributeCreator_12
    FAILED -> AttributeCreator_13
AttributeCreator_12
    ATTR_LIST = sk_uu_tettsted,1
    -> dekningsoversikt.dekningsoversikt (writer POSTGRES_1)
AttributeCreator_13
    ATTR_LIST = sk_uu_tettsted,0
    -> dekningsoversikt.dekningsoversikt (writer POSTGRES_1)

Bookmark: UU Friluft
uufriluftsomrader.uufriluftturvei (reader POSTGIS_1)
    attributes: objid int4,PRIKEY, objtype varchar(32), veitype varchar(80), spesialfotrutetype varchar(80), arstidsbruk varchar(80), sperrebom varchar(80), sperrebomtilgjengelig varchar(80), dekke varchar(80), dekketilstand varchar(80), motehvileplass varchar(80), antalltilstrekkelig varchar(80), belysning varchar(80), bredde int4, stigning float8, tverrfall float8, frihoyde varchar(80), ledelinje varchar(80), ledelinjekontrast varchar(80), tilgjengvurderingrullestol varchar(80), tilgjengvurderingelrullestol varchar(80), tilgjengvurderingsyn varchar(80), ogcfid int4, opphav varchar(80), kommune varchar(80), bilde varchar(80), registrert timestamp, oppdatert timestamp, kommentar varchar(500), forbedringsforslag varchar(255)
    -> Deaggregator_4
uufriluftsomrader.uufrilufttoalett (reader POSTGIS_1)
    attributes: objid int4,PRIKEY, objtype varchar(32), byggtype varchar(80), rampe varchar(80), rampebredde int4, rampestigning float8, handlist varchar(80), handlisthoyde1 int4, handlisthoyde2 int4, rampeterskel float8, rampetilgjengelighet varchar(80), avstandhc int4, dortype varchar(80), dorapner varchar(80), manoverknapphoyde int4, breddeinngang int4, kontrastinngang varchar(80), terskelhoyde float8, diametersnusirkel int4, belysning varchar(80), omkledningtilgjengelig varchar(80), servanttilgjengelig varchar(80), wctilgjengelig varchar(80), tilgjengvurderingrullestol varchar(80), tilgjengvurderingelrullestol varchar(80), tilgjengvurderingsyn varchar(80), ogcfid int4, opphav varchar(80), kommune varchar(80), bilde varchar(80),
      registrert timestamp, oppdatert timestamp, kommentar varchar(500), forbedringsforslag varchar(500)
    -> Deaggregator_4
uufriluftsomrader.uufriluftstatligsikrafriluftsomrader (reader POSTGIS_1)
    attributes: objid int4,PRIKEY, objtype varchar(80), linkbilde varchar(255), linkskjema varchar(255), naturbasenr varchar(80), navn varchar(80), ogcfid int4, opphav varchar(80), kommune varchar(80), bilde varchar(80), registrert timestamp, oppdatert timestamp, kommentar varchar(2000), forbedringsforslag varchar(2000)
    -> Deaggregator_4
uufriluftsomrader.uufriluftsittegruppe (reader POSTGIS_1)
    attributes: objid int4,PRIKEY, objtype varchar(32), dekke varchar(80), dekketilstand varchar(80), helning float8, hoydebord int4, utstikkbord int4, tilgjengvurderingrullestol varchar(80), ogcfid int4, opphav varchar(80), kommune varchar(80), bilde varchar(80), registrert timestamp, oppdatert timestamp, kommentar varchar(500), forbedringsforslag varchar(255)
    -> Deaggregator_4
uufriluftsomrader.uufriluftparkeringsomrade (reader POSTGIS_1)
    attributes: objid int4,PRIKEY, objtype varchar(32), kapasitetpersonbiler int4, kapasitetuu int4, arstidsbruk varchar(80), dekke varchar(80), dekketilstand varchar(80), tilgjengvurderingrullestol varchar(80), tilgjengvurderingelrullestol varchar(80), ogcfid int4, opphav varchar(80), kommune varchar(80), bilde varchar(80), registrert timestamp, oppdatert timestamp, kommentar varchar(500), forbedringsforslag varchar(500)
    -> Deaggregator_4
uufriluftsomrader.uufrilufthyttertilrettelagt (reader POSTGIS_1)
    attributes: objid int4,PRIKEY, objtype varchar(32), eier varchar(80), lenke varchar(255), navn varchar(80), tilrettelagt varchar(80), ogcfid int4, opphav varchar(80), kommune varchar(80), bilde varchar(80), registrert timestamp, oppdatert timestamp, kommentar varchar(500), forbedringsforslag varchar(500)
    -> Deaggregator_4
uufriluftsomrader.uufrilufthcparkering (reader POSTGIS_1)
    attributes: objid int4,PRIKEY, objtype varchar(32), skiltet varchar(80), merket varchar(80), bredde int4, lengde int4, avstandfasilitet int4, avgift varchar(80), automathoyde int4, tilgjengeligautomat varchar(80), tilgjengvurderingrullestol varchar(80), tilgjengvurderingelrullestol varchar(80), ogcfid int4, opphav varchar(80), kommune varchar(80), bilde varchar(80), registrert timestamp, oppdatert timestamp, kommentar varchar(500), forbedringsforslag varchar(255)
    -> Deaggregator_4
uufriluftsomrader.uufriluftgrillbalplass (reader POSTGIS_1)
    attributes: objid int4,PRIKEY, objtype varchar(32), dekke varchar(80), dekketilstand varchar(80), helning float8, tilgjengvurderingrullestol varchar(80), ogcfid int4, opphav varchar(80), kommune varchar(80), bilde varchar(80), registrert timestamp, oppdatert timestamp, kommentar varchar(500), forbedringsforslag varchar(500)
    -> Deaggregator_4
uufriluftsomrader.uufriluftgapahuk (reader POSTGIS_1)
    attributes: objid int4,PRIKEY, objtype varchar(32), rampe varchar(80), rampebredde int4, rampestigning float8, handlist varchar(80), handlisthoyde1 int4, handlisthoyde2 int4, rampeterskel float8, rampetilgjengelig varchar(80), breddeinngang int4, hoydeinngang int4, terskelhoyde float8, kontrastinngang varchar(80), diametersnusirkel int4, dekke varchar(80), dekketilstand varchar(80), tilgjengvurderingrullestol varchar(80), tilgjengvurderingelrullestol varchar(80), tilgjengvurderingsyn varchar(80), ogcfid int4, opphav varchar(80), kommune varchar(80), bilde varchar(80), registrert timestamp, oppdatert timestamp, kommentar varchar(500), forbedringsforslag varchar(255)
    -> Deaggregator_4
uufriluftsomrader.uufriluftfriluftsomrade (reader POSTGIS_1)
    attributes: objid int4,PRIKEY, objtype varchar(32), navn varchar(80), naturbasenr int4, parkeringsomrade varchar(80), hcparkeringsplass varchar(80), toalett varchar(80), turvei varchar(80), baderampe varchar(80), fiskeplass varchar(80), grillbalplass varchar(80), sittegruppe varchar(80), gapahuk varchar(80), informasjon varchar(80), annen varchar(80), ogcfid int4, opphav varchar(80), kommune varchar(80), bilde varchar(80), registrert timestamp, oppdatert timestamp, kommentar varchar(500), forbedringsforslag varchar(500)
    -> Deaggregator_4
uufriluftsomrader.uufriluftfiskeplass (reader POSTGIS_1)
    attributes: objid int4,PRIKEY, objtype varchar(32), flytebrygge varchar(80), rampe varchar(80), rampebredde int4, rampestigning float8, handlist varchar(80), handlisthoyde1 int4, handlisthoyde2 int4, rampeterskel float8, rampetilgjengelig varchar(80), dekke varchar(80), plankeavstand float8, dekketilstand varchar(80), diametersnusirkel int4, rekkverk varchar(80), stoppkant varchar(80), stoppkanthoyde float8, tilgjengvurderingrullestol varchar(80), tilgjengvurderingelrullestol varchar(80), tilgjengvurderingsyn varchar(80), ogcfid int4, opphav varchar(80), kommune varchar(80), bilde varchar(80), registrert timestamp, oppdatert timestamp, kommentar varchar(500), forbedringsforslag varchar(500)
    -> Deaggregator_4
uufriluftsomrader.uufriluftbaderampe (reader POSTGIS_1)
    attributes: objid int4,PRIKEY, objtype varchar(32), rampe varchar(80), rampebredde int4, rampestigning float8, handlist varchar(80), handlisthoyde1 int4, handlisthoyde2 int4, rampeterskel float8, rampetilgjengelig varchar(80), tilgjengvurderingrullestol varchar(80), tilgjengvurderingsyn varchar(80), ogcfid int4, opphav varchar(80), kommune varchar(80), bilde varchar(80), registrert timestamp, oppdatert timestamp, kommentar varchar(500), forbedringsforslag varchar(500)
    -> Deaggregator_4
Deaggregator_4
    GEOM_NAME_FIELD = _geometry_name
    ID_SELECTION = ID and Parent ID
    PART_NUMBER_FIELD = _part_number
    SPLIT_COMPOSITES = No
    MODE = Flatten One Level
    LIST_ATTR_MODE_LOOKUP = LEAN
    PARENT_ID_ATTR = _hierarchy_parent_id
    CHILD_ID_ATTR = _hierarchy_child_id_list
    ID_ATTR = _hierarchy_id
    EXPLODE_INSTANCES = No
    COPY_ATTR = Every Node
    DEAGGREGATED -> SpatialFilter_7 [input 1]
SpatialFilter_7
    MERGE_ATTRS = Yes
    PASS_CRITERIA = Pass Against One Filter
    PREDICATE_VALUE = Intersects
    PREDATTR = _predicate
    USE_BOUNDING_BOX = No
    BASE_TYPE = Multiple Filters
    CURVE_BOUNDARY_RULE_PARAM = Default Rule
    PASSED -> AttributeCreator_14
    FAILED -> AttributeCreator_15
AttributeCreator_14
    ATTR_LIST = sk_uu_friluft,1
    -> dekningsoversikt.dekningsoversikt (writer POSTGRES_1)
AttributeCreator_15
    ATTR_LIST = sk_uu_friluft,0
    -> dekningsoversikt.dekningsoversikt (writer POSTGRES_1)
