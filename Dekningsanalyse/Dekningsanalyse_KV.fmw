FME workspace Dekningsanalyse_KV.fmw

Parameters:
- DestDataset_POSTGIS = geonortst@nnridb504:5432/geonor01tst   # Connection
- MINX = -75911   # Minimum X
- MINY = 6451497   # Minimum Y
- MAXX = 1115104   # Maximum X
- MAXY = 7939276   # Maximum Y
- SourceDataset_GEOJSON = http://gis3.nve.no/map/rest/services/Elvenett/MapServer/1/query?where=&text=&objectIds=&time=&geometry=&geometryType=esriGeometryEnvelope&inSR=&spatialRel=esriSpatialRelIntersects&relationParam=&outFields=&returnGeometry=true&maxAllowableOffset=&geometryPrecision=&outSR=&returnIdsOnly=false&returnCountOnly=false&orderByFields=&groupByFieldsForStatistics=&outStatistics=&returnZ=false&returnM=false&gdbVersion=&returnDistinctValues=false&returnTrueCurves=false&resultOffset=&resultRecordCount=&f=pjson   # Source GeoJSON File or URL
- DestDataset_SHAPE = $(FME_MF_DIR)Temp_data   # Destination Esri Shape Folder
- SourceDataset_POSTGIS = geonortst@nnridb504:5432/geonor01tst   # Connection
- SourceDataset_WFS = http://153.44.6.24/a3_mapserver/wfs.ashx   # Source WFS (Web Feature Service) URL
- TILESIZE = 100000   # Tile Width (ground units)

Readers:
- POSTGIS_1: POSTGIS from $(SourceDataset_POSTGIS)
- WFS_1: WFS from $(SourceDataset_WFS)
- GEOJSON_1: GEOJSON from $(SourceDataset_GEOJSON)

Writers:
- POSTGIS_2: POSTGIS to $(DestDataset_POSTGIS)
- SHAPE_1: SHAPE to $(DestDataset_SHAPE)

admingrense.kommuneflate (reader POSTGIS_1)
    attributes: kommuneid int4
    -> Reprojector
Reprojector
    INTERPOLATION_TYPE_NAME = Nearest Neighbor
    SOURCE = Read from feature
    RASTER_CELL_SIZE = Preserve Cells
    DEST = EPSG:32633
    REPROJECTED -> Deaggregator
Deaggregator
    SPLIT_COMPOSITES = No
    GEOM_NAME_FIELD = _geometry_name
    CHILD_ID_ATTR = _hierarchy_child_id_list
    PARENT_ID_ATTR = _hierarchy_parent_id
    LIST_ATTR_MODE_LOOKUP = LEAN
    EXPLODE_INSTANCES = No
    COPY_ATTR = Every Node
    MODE = Flatten One Level
    ID_ATTR = _hierarchy_id
    PART_NUMBER_FIELD = _part_number
    ID_SELECTION = ID and Parent ID
    DEAGGREGATED -> GeometryCoercer
GeometryCoercer
    GQUERY:
      for $geom in //geometry
      where $geom/count(parent::geometry) = 0
      return number($geom/@fme_id)
    KIND = fme_polygon
    UNTOUCHED -> SpatialFilter_7 [input 2]
    COERCED -> SpatialFilter_7 [input 2]
    COERCED -> SpatialFilter_8 [input 2]
    UNTOUCHED -> SpatialFilter_8 [input 2]
    COERCED -> SpatialFilter_9 [input 2]
    UNTOUCHED -> SpatialFilter_9 [input 2]
    COERCED -> SpatialFilter_10 [input 2]
    UNTOUCHED -> SpatialFilter_10 [input 2]
    UNTOUCHED -> dekningsoversikt.dekningsoversikt (writer POSTGIS_2)
    COERCED -> dekningsoversikt.dekningsoversikt (writer POSTGIS_2)
dekningsoversikt.dekningsoversikt (writer POSTGIS_2)
    attributes: kommuneid int4, akvakultur bool, dsb_sivforsvdistr bool, korallrev bool, dsb_brannstasjon bool, dsb_110sentral bool, dsb_distrkont_siv bool, ra_brannsmitteomr bool, ra_tettetrehusm bool, ra_frededebygg bool, ra_enkeltminner bool, ra_kulturmiljo bool, ra_lokaliteter bool, ra_sikringssoner bool, kv_hovedbiled bool, kv_ispshavneanlegg bool, kv_losbordingsfelt bool, kv_losstasjoner bool

Bookmark: Elvis
Note: Lager polygon av / envelope
Creator_2 [off]
    COORDS = $(MINX) $(MINY) $(MAXX) $(MINY) $(MAXX) $(MAXY)  $(MINX) $(MAXY)  $(MINX) $(MINY)
    GEOMTYPE = 2D Coordinate List
    COORDSYS = EPSG:25833
    NUM = 1
    CREATED -> Reprojector_2 [off]
Note: Projiserer envelopen til 25833
Reprojector_2 [off]
    INTERPOLATION_TYPE_NAME = Nearest Neighbor
    SOURCE = Read from feature
    RASTER_CELL_SIZE = Preserve Cells
    STROKE_ARCS = Yes
    DEST = EPSG:25833
    REPROJECTED -> Tiler [off]
Note: Tiler opp envelopen i mindre / områder
Tiler [off]
    XINC = $(TILESIZE)
    ROW_ATTR = _row
    YINC = $(TILESIZE)
    COL_ATTR = _column
    TILING_TYPE = Tile Size
    TILED -> BoundsExtractor [off]
BoundsExtractor [off]
    YMIN = _ymin
    YMAX = _ymax
    ZMIN = _zmin
    ZMAX = _zmax
    XMIN = _xmin
    XMAX = _xmax
    -> AttributeCreator [off]
AttributeCreator [off]
    ATTR_LIST = Query,http://gis3.nve.no/map/rest/services/Elvenett/MapServer/1/query?where=1%3D1&text=&objectIds=&time=&geometry=@Value(_xmin),@Value(_ymin),@Value(_xmax),@Value(_ymax)&geometryType=esriGeometryEnvelope&inSR=&spatialRel=esriSpatialRelIntersects&relationParam=&outFields=&returnGeometry=true&maxAllowableOffset=&geometryPrecision=&outSR=&returnIdsOnly=false&returnCountOnly=false&orderByFields=&groupByFieldsForStatistics=&outStatistics=&returnZ=false&returnM=false&gdbVersion=&returnDistinctValues=false&returnTrueCurves=false&resultOffset=&resultRecordCount=&f=pjson
    -> FeatureReader [off]
FeatureReader [off]
    ESRIJSON_MAKE_PATHS = No
    ESRIJSON_CLIP_TO_ENVELOPE = NO
    ESRIJSON_DELETE_DOWNLOAD_FILE = Yes
    FEATURETYPES_RADIO = FEATURETYPES
    ESRIJSON_MAKE_DONUTS = No
    INTERACT = <No Spatial Filter>
    ESRIJSON_USE_BASENAME_AS_DEFAULT_FEATURE_TYPE = No
    ATTR_ACCUM_MODE = Only Use Result
    ESRIJSON_USE_SEARCH_ENVELOPE = NO
    DATASET = @Value(Query)
    ESRIJSON_SIMPLIFY_MULTIS = Yes
    OUTPUT_FEATURES_DISPLAY = Only Data Features
    FORMAT = ESRIJSON
    COMBINE_GEOM = Use Result
    <OTHER> -> Matcher [off]
Matcher [off]
    BLANK_AND_MISSING_DIFFER = No
    LENIENT_MATCH = No
    MATCH_STRATEGY = Match Selected Attributes
    CNT_ATTR = _match_id
    MATCH = 2D
    SINGLE_MATCHED -> Elvis_hovedneett (writer SHAPE_1) [off]
    NOT_MATCHED -> Elvis_hovedneett (writer SHAPE_1) [off]
Elvis_hovedneett (writer SHAPE_1) [off]
    attributes: _match_id char(200)
Note: Lager polygon av / envelope
Creator_3 [off]
    COORDS = $(MINX) $(MINY) $(MAXX) $(MINY) $(MAXX) $(MAXY)  $(MINX) $(MAXY)  $(MINX) $(MINY)
    GEOMTYPE = 2D Coordinate List
    COORDSYS = EPSG:25833
    NUM = 1
    CREATED -> Reprojector_3 [off]
Note: Projiserer envelopen til 25833
Reprojector_3 [off]
    INTERPOLATION_TYPE_NAME = Nearest Neighbor
    SOURCE = Read from feature
    RASTER_CELL_SIZE = Preserve Cells
    STROKE_ARCS = Yes
    DEST = EPSG:25833
    REPROJECTED -> Tiler_2 [off]
Note: Tiler opp envelopen i mindre / områder
Tiler_2 [off]
    XINC = 25000
    ROW_ATTR = _row
    YINC = 25000
    COL_ATTR = _column
    TILING_TYPE = Tile Size
    TILED -> BoundsExtractor_2 [off]
BoundsExtractor_2 [off]
    YMIN = _ymin
    YMAX = _ymax
    ZMIN = _zmin
    ZMAX = _zmax
    XMIN = _xmin
    XMAX = _xmax
    -> AttributeCreator_2 [off]
AttributeCreator_2 [off]
    ATTR_LIST = Query2,http://gis3.nve.no/map/rest/services/Elvenett/MapServer/2/query?where=1%3D1&text=&objectIds=&time=&geometry=@Value(_xmin),@Value(_ymin),@Value(_xmax),@Value(_ymax)&geometryType=esriGeometryEnvelope&inSR=&spatialRel=esriSpatialRelIntersects&relationParam=&outFields=&returnGeometry=true&maxAllowableOffset=&geometryPrecision=&outSR=&returnIdsOnly=false&returnCountOnly=false&orderByFields=&groupByFieldsForStatistics=&outStatistics=&returnZ=false&returnM=false&gdbVersion=&returnDistinctValues=false&returnTrueCurves=false&resultOffset=&resultRecordCount=&f=pjson
    -> FeatureReader_2 [off]
FeatureReader_2 [off]
    ESRIJSON_MAKE_PATHS = No
    ESRIJSON_CLIP_TO_ENVELOPE = NO
    ESRIJSON_DELETE_DOWNLOAD_FILE = Yes
    FEATURETYPES_RADIO = FEATURETYPES
    ESRIJSON_MAKE_DONUTS = No
    INTERACT = <No Spatial Filter>
    ESRIJSON_USE_BASENAME_AS_DEFAULT_FEATURE_TYPE = No
    ATTR_ACCUM_MODE = Only Use Result
    ESRIJSON_USE_SEARCH_ENVELOPE = NO
    DATASET = @Value(Query2)
    ESRIJSON_SIMPLIFY_MULTIS = Yes
    OUTPUT_FEATURES_DISPLAY = Only Data Features
    FORMAT = ESRIJSON
    COMBINE_GEOM = Use Result
    <OTHER> -> Matcher_2 [off]
Matcher_2 [off]
    BLANK_AND_MISSING_DIFFER = No
    LENIENT_MATCH = No
    MATCH_STRATEGY = Match Selected Attributes
    CNT_ATTR = _match_id
    MATCH = 2D
    SINGLE_MATCHED -> Elvis_elvenett (writer SHAPE_1) [off]
    NOT_MATCHED -> Elvis_elvenett (writer SHAPE_1) [off]
Elvis_elvenett (writer SHAPE_1) [off]
    attributes: _match_id char(200)
Note: Lager polygon av / envelope
Creator_4
    COORDS = $(MINX) $(MINY) $(MAXX) $(MINY) $(MAXX) $(MAXY)  $(MINX) $(MAXY)  $(MINX) $(MINY)
    GEOMTYPE = 2D Coordinate List
    COORDSYS = EPSG:25833
    NUM = 1
    CREATED -> Reprojector_4
Note: Projiserer envelopen til 25833
Reprojector_4
    INTERPOLATION_TYPE_NAME = Nearest Neighbor
    SOURCE = Read from feature
    RASTER_CELL_SIZE = Preserve Cells
    STROKE_ARCS = Yes
    DEST = EPSG:25833
    REPROJECTED -> Tiler_3
Note: Tiler opp envelopen i mindre / områder
Tiler_3
    XINC = 50000
    ROW_ATTR = _row
    YINC = 50000
    COL_ATTR = _column
    TILING_TYPE = Tile Size
    TILED -> BoundsExtractor_3
BoundsExtractor_3
    YMIN = _ymin
    YMAX = _ymax
    ZMIN = _zmin
    ZMAX = _zmax
    XMIN = _xmin
    XMAX = _xmax
    -> AttributeCreator_3
AttributeCreator_3
    ATTR_LIST = Query,http://gis3.nve.no/map/rest/services/Innsjodatabase/MapServer/1/query?where=1%3D1&text=&objectIds=&time=&geometry=@Value(_xmin),@Value(_ymin),@Value(_xmax),@Value(_ymax)&geometryType=esriGeometryEnvelope&inSR=&spatialRel=esriSpatialRelIntersects&relationParam=&outFields=&returnGeometry=true&maxAllowableOffset=&geometryPrecision=&outSR=&returnIdsOnly=false&returnCountOnly=false&orderByFields=&groupByFieldsForStatistics=&outStatistics=&returnZ=false&returnM=false&gdbVersion=&returnDistinctValues=false&returnTrueCurves=false&resultOffset=&resultRecordCount=&f=pjson
    -> FeatureReader_3
FeatureReader_3
    ESRIJSON_MAKE_PATHS = No
    ESRIJSON_CLIP_TO_ENVELOPE = NO
    ESRIJSON_DELETE_DOWNLOAD_FILE = Yes
    FEATURETYPES_RADIO = FEATURETYPES
    ESRIJSON_MAKE_DONUTS = No
    INTERACT = <No Spatial Filter>
    ESRIJSON_USE_BASENAME_AS_DEFAULT_FEATURE_TYPE = No
    ATTR_ACCUM_MODE = Only Use Result
    ESRIJSON_USE_SEARCH_ENVELOPE = NO
    DATASET = @Value(Query)
    ESRIJSON_SIMPLIFY_MULTIS = Yes
    OUTPUT_FEATURES_DISPLAY = Only Data Features
    FORMAT = ESRIJSON
    COMBINE_GEOM = Use Result
    <OTHER> -> Matcher_3
Matcher_3
    BLANK_AND_MISSING_DIFFER = No
    LENIENT_MATCH = No
    MATCH_STRATEGY = Match Selected Attributes
    CNT_ATTR = _match_id
    MATCH = 2D
    SINGLE_MATCHED -> Innsjo (writer SHAPE_1)
    NOT_MATCHED -> Innsjo (writer SHAPE_1)
Innsjo (writer SHAPE_1)
    attributes: _match_id char(200)

Bookmark: Kystverket
Note: Hoved - og biled
layer_37 (reader WFS_1)
    attributes: gml_parent_id xml_buffer, gml_parent_property xml_buffer, gml_id xml_buffer, msGeometry xml_geometry, navn xml_buffer, uuid xml_buffer, farlednummer xml_buffer, delstreknavn xml_buffer, farledpaabud xml_buffer, farledtype xml_buffer, farledstatus xml_buffer, kyv_region xml_buffer, lengde xml_buffer, datafangstdato xml_buffer, oppdateringsdato xml_buffer, gyldig_fra xml_buffer, gyldig_til xml_buffer, informasjon xml_buffer, maalemetode xml_buffer, noyaktighet xml_buffer, orginaldatavert xml_buffer, opphav xml_buffer, kopidato xml_buffer, id xml_buffer
    -> Deaggregator_2
Deaggregator_2
    SPLIT_COMPOSITES = No
    GEOM_NAME_FIELD = _geometry_name
    LIST_ATTR_MODE_LOOKUP = LEAN
    EXPLODE_INSTANCES = No
    MODE = Flatten All Levels
    DEAGGREGATED -> SpatialFilter_7 [input 1]
SpatialFilter_7
    USE_BOUNDING_BOX = No
    PREDICATE_VALUE = Intersects
    PREDATTR = _predicate
    BASE_TYPE = Multiple Filters
    PASS_CRITERIA = Pass Against One Filter
    CURVE_BOUNDARY_RULE_PARAM = Default Rule
    MERGE_ATTRS = Yes
    PASSED -> AttributeCreator_27
    FAILED -> AttributeCreator_28
AttributeCreator_27
    ATTR_LIST = kv_hovedbiled,1
    -> dekningsoversikt.dekningsoversikt (writer POSTGIS_2)
AttributeCreator_28
    ATTR_LIST = kv_hovedbiled,0
    -> dekningsoversikt.dekningsoversikt (writer POSTGIS_2)
Note: ISPS havneanlegg
layer_28 (reader WFS_1)
    attributes: gml_parent_id xml_buffer, gml_parent_property xml_buffer, gml_id xml_buffer, msGeometry xml_geometry, Cluster:FeatureCount xml_buffer, Cluster:Group xml_buffer
    -> SpatialFilter_8 [input 1]
SpatialFilter_8
    USE_BOUNDING_BOX = No
    PREDICATE_VALUE = Intersects
    PREDATTR = _predicate
    BASE_TYPE = Multiple Filters
    PASS_CRITERIA = Pass Against One Filter
    CURVE_BOUNDARY_RULE_PARAM = Default Rule
    MERGE_ATTRS = Yes
    PASSED -> AttributeCreator_29
    FAILED -> AttributeCreator_30
AttributeCreator_29
    ATTR_LIST = kv_ispshavneanlegg,1
    -> dekningsoversikt.dekningsoversikt (writer POSTGIS_2)
AttributeCreator_30
    ATTR_LIST = kv_ispshavneanlegg,0
    -> dekningsoversikt.dekningsoversikt (writer POSTGIS_2)
Note: Losbordingsfelt
layer_29 (reader WFS_1)
    attributes: gml_parent_id xml_buffer, gml_parent_property xml_buffer, gml_id xml_buffer, msGeometry xml_geometry, losbordingsfelt xml_buffer, nord xml_buffer, ost xml_buffer, kommune xml_buffer, merknad_begrensning xml_buffer, merknad2 xml_buffer, sjotrafikkomraade xml_buffer, uuid xml_buffer, datafangstdato xml_buffer, oppdateringsdato xml_buffer, gyldig_fra xml_buffer, gyldig_til xml_buffer, informasjon xml_buffer, maalemetode xml_buffer, noyaktighet xml_buffer, originaldatavert xml_buffer, opphav xml_buffer, kopidato xml_buffer, id xml_buffer
    -> SpatialFilter_9 [input 1]
SpatialFilter_9
    USE_BOUNDING_BOX = No
    PREDICATE_VALUE = Intersects
    PREDATTR = _predicate
    BASE_TYPE = Multiple Filters
    PASS_CRITERIA = Pass Against One Filter
    CURVE_BOUNDARY_RULE_PARAM = Default Rule
    MERGE_ATTRS = Yes
    PASSED -> AttributeCreator_31
    FAILED -> AttributeCreator_32
AttributeCreator_31
    ATTR_LIST = kv_losbordingsfelt,1
    -> dekningsoversikt.dekningsoversikt (writer POSTGIS_2)
AttributeCreator_32
    ATTR_LIST = kv_losbordingsfelt,0
    -> dekningsoversikt.dekningsoversikt (writer POSTGIS_2)
Note: Losstasjoner
layer_59 (reader WFS_1)
    attributes: gml_parent_id xml_buffer, gml_parent_property xml_buffer, gml_id xml_buffer, msGeometry xml_geometry, gid xml_buffer, navn xml_buffer, dato xml_buffer, funksjon xml_buffer, distrikt xml_buffer, los1 xml_buffer, los2 xml_buffer
    -> SpatialFilter_10 [input 1]
SpatialFilter_10
    USE_BOUNDING_BOX = No
    PREDICATE_VALUE = Intersects
    PREDATTR = _predicate
    BASE_TYPE = Multiple Filters
    PASS_CRITERIA = Pass Against One Filter
    CURVE_BOUNDARY_RULE_PARAM = Default Rule
    MERGE_ATTRS = Yes
    PASSED -> AttributeCreator_33
    FAILED -> AttributeCreator_34
AttributeCreator_33
    ATTR_LIST = kv_losstasjoner,1
    -> dekningsoversikt.dekningsoversikt (writer POSTGIS_2)
AttributeCreator_34
    ATTR_LIST = kv_losstasjoner,0
    -> dekningsoversikt.dekningsoversikt (writer POSTGIS_2)
