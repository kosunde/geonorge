FME workspace Dekningsanalyse_NVE_dataimport.fmw

Parameters:
- MINX = -75026   # Minimum X
- MINY = 6457862   # Minimum Y
- MAXX = 1099955   # Maximum X
- MAXY = 7939276   # Maximum Y
- SourceDataset_GEOJSON = http://gis3.nve.no/map/rest/services/Elvenett/MapServer/1/query?where=&text=&objectIds=&time=&geometry=&geometryType=esriGeometryEnvelope&inSR=&spatialRel=esriSpatialRelIntersects&relationParam=&outFields=&returnGeometry=true&maxAllowableOffset=&geometryPrecision=&outSR=&returnIdsOnly=false&returnCountOnly=false&orderByFields=&groupByFieldsForStatistics=&outStatistics=&returnZ=false&returnM=false&gdbVersion=&returnDistinctValues=false&returnTrueCurves=false&resultOffset=&resultRecordCount=&f=pjson   # Source GeoJSON File or URL
- DestDataset_SHAPE = $(FME_MF_DIR)Temp_data   # Destination Esri Shape Folder
- TILESIZE = 300000   # Tile Width (ground units)

Readers:
- GEOJSON_1: GEOJSON from $(SourceDataset_GEOJSON)

Writers:
- SHAPE_1: SHAPE to $(DestDataset_SHAPE)

Bookmark: Vannkraft
Note: Lager polygon av / envelope
Creator_11 [off]
    NUM = 1
    COORDS = $(MINX) $(MINY) $(MAXX) $(MINY) $(MAXX) $(MAXY)  $(MINX) $(MAXY)  $(MINX) $(MINY)
    GEOMTYPE = 2D Coordinate List
    COORDSYS = EPSG:25833
    CREATED -> Reprojector_11 [off]
Note: Projiserer envelopen til 25833
Reprojector_11 [off]
    DEST = EPSG:25833
    STROKE_ARCS = Yes
    SOURCE = Read from feature
    INTERPOLATION_TYPE_NAME = Nearest Neighbor
    RASTER_CELL_SIZE = Preserve Cells
    REPROJECTED -> Tiler_10 [off]
Note: Tiler opp envelopen i mindre / områder
Tiler_10 [off]
    TILING_TYPE = Tile Size
    XINC = 100000
    ROW_ATTR = _row
    YINC = 100000
    COL_ATTR = _column
    TILED -> BoundsExtractor_10 [off]
BoundsExtractor_10 [off]
    YMIN = _ymin
    YMAX = _ymax
    ZMIN = _zmin
    ZMAX = _zmax
    XMIN = _xmin
    XMAX = _xmax
    -> AttributeCreator_10 [off]
AttributeCreator_10 [off]
    ATTR_LIST = Query,http://gis3.nve.no/map/rest/services/Vannkraftverk/MapServer/2/query?where=1%3D1&text=&objectIds=&time=&geometry=@Value(_xmin),@Value(_ymin),@Value(_xmax),@Value(_ymax)&geometryType=esriGeometryEnvelope&inSR=&spatialRel=esriSpatialRelIntersects&relationParam=&outFields=&returnGeometry=true&maxAllowableOffset=&geometryPrecision=&outSR=&returnIdsOnly=false&returnCountOnly=false&orderByFields=&groupByFieldsForStatistics=&outStatistics=&returnZ=false&returnM=false&gdbVersion=&returnDistinctValues=false&returnTrueCurves=false&resultOffset=&resultRecordCount=&f=pjson
    -> FeatureReader_10 [off]
FeatureReader_10 [off]
    FORMAT = ESRIJSON
    OUTPUT_FEATURES_DISPLAY = Only Data Features
    ESRIJSON_CLIP_TO_ENVELOPE = NO
    COMBINE_GEOM = Use Result
    ESRIJSON_USE_BASENAME_AS_DEFAULT_FEATURE_TYPE = No
    ESRIJSON_USE_SEARCH_ENVELOPE = NO
    DATASET = @Value(Query)
    ATTR_ACCUM_MODE = Only Use Result
    ESRIJSON_DELETE_DOWNLOAD_FILE = Yes
    ESRIJSON_SIMPLIFY_MULTIS = Yes
    INTERACT = <No Spatial Filter>
    ESRIJSON_MAKE_PATHS = No
    FEATURETYPES_RADIO = FEATURETYPES
    ESRIJSON_MAKE_DONUTS = No
    <OTHER> -> Matcher_10 [off]
Matcher_10 [off]
    LENIENT_MATCH = No
    MATCH = 2D
    CNT_ATTR = _match_id
    MATCH_STRATEGY = Match Selected Attributes
    BLANK_AND_MISSING_DIFFER = No
    SINGLE_MATCHED -> vannkraftverk (writer SHAPE_1) [off]
    NOT_MATCHED -> vannkraftverk (writer SHAPE_1) [off]
vannkraftverk (writer SHAPE_1) [off]
    attributes: _match_id char(200)
Note: Lager polygon av / envelope
Creator_12 [off]
    NUM = 1
    COORDS = $(MINX) $(MINY) $(MAXX) $(MINY) $(MAXX) $(MAXY)  $(MINX) $(MAXY)  $(MINX) $(MINY)
    GEOMTYPE = 2D Coordinate List
    COORDSYS = EPSG:25833
    CREATED -> Reprojector_12 [off]
Note: Projiserer envelopen til 25833
Reprojector_12 [off]
    DEST = EPSG:25833
    STROKE_ARCS = Yes
    SOURCE = Read from feature
    INTERPOLATION_TYPE_NAME = Nearest Neighbor
    RASTER_CELL_SIZE = Preserve Cells
    REPROJECTED -> Tiler_11 [off]
Note: Tiler opp envelopen i mindre / områder
Tiler_11 [off]
    TILING_TYPE = Tile Size
    XINC = 100000
    ROW_ATTR = _row
    YINC = 100000
    COL_ATTR = _column
    TILED -> BoundsExtractor_11 [off]
BoundsExtractor_11 [off]
    YMIN = _ymin
    YMAX = _ymax
    ZMIN = _zmin
    ZMAX = _zmax
    XMIN = _xmin
    XMAX = _xmax
    -> AttributeCreator_11 [off]
AttributeCreator_11 [off]
    ATTR_LIST = Query,http://gis3.nve.no/map/rest/services/Vannkraftverk/MapServer/9/query?where=1%3D1&text=&objectIds=&time=&geometry=@Value(_xmin),@Value(_ymin),@Value(_xmax),@Value(_ymax)&geometryType=esriGeometryEnvelope&inSR=&spatialRel=esriSpatialRelIntersects&relationParam=&outFields=&returnGeometry=true&maxAllowableOffset=&geometryPrecision=&outSR=&returnIdsOnly=false&returnCountOnly=false&orderByFields=&groupByFieldsForStatistics=&outStatistics=&returnZ=false&returnM=false&gdbVersion=&returnDistinctValues=false&returnTrueCurves=false&resultOffset=&resultRecordCount=&f=pjson
    -> FeatureReader_11 [off]
FeatureReader_11 [off]
    FORMAT = ESRIJSON
    OUTPUT_FEATURES_DISPLAY = Only Data Features
    ESRIJSON_CLIP_TO_ENVELOPE = NO
    COMBINE_GEOM = Use Result
    ESRIJSON_USE_BASENAME_AS_DEFAULT_FEATURE_TYPE = No
    ESRIJSON_USE_SEARCH_ENVELOPE = NO
    DATASET = @Value(Query)
    ATTR_ACCUM_MODE = Only Use Result
    ESRIJSON_DELETE_DOWNLOAD_FILE = Yes
    ESRIJSON_SIMPLIFY_MULTIS = Yes
    INTERACT = <No Spatial Filter>
    ESRIJSON_MAKE_PATHS = No
    FEATURETYPES_RADIO = FEATURETYPES
    ESRIJSON_MAKE_DONUTS = No
    <OTHER> -> Matcher_11 [off]
Matcher_11 [off]
    LENIENT_MATCH = No
    MATCH = 2D
    CNT_ATTR = _match_id
    MATCH_STRATEGY = Match Selected Attributes
    BLANK_AND_MISSING_DIFFER = No
    SINGLE_MATCHED -> kraftverk_alle_konsesjonsstadier (writer SHAPE_1) [off]
    NOT_MATCHED -> kraftverk_alle_konsesjonsstadier (writer SHAPE_1) [off]
kraftverk_alle_konsesjonsstadier (writer SHAPE_1) [off]
    attributes: _match_id char(200)
Note: Lager polygon av / envelope
Creator_13 [off]
    NUM = 1
    COORDS = $(MINX) $(MINY) $(MAXX) $(MINY) $(MAXX) $(MAXY)  $(MINX) $(MAXY)  $(MINX) $(MINY)
    GEOMTYPE = 2D Coordinate List
    COORDSYS = EPSG:25833
    CREATED -> Reprojector_13 [off]
Note: Projiserer envelopen til 25833
Reprojector_13 [off]
    DEST = EPSG:25833
    STROKE_ARCS = Yes
    SOURCE = Read from feature
    INTERPOLATION_TYPE_NAME = Nearest Neighbor
    RASTER_CELL_SIZE = Preserve Cells
    REPROJECTED -> Tiler_12 [off]
Note: Tiler opp envelopen i mindre / områder
Tiler_12 [off]
    TILING_TYPE = Tile Size
    XINC = 100000
    ROW_ATTR = _row
    YINC = 100000
    COL_ATTR = _column
    TILED -> BoundsExtractor_12 [off]
BoundsExtractor_12 [off]
    YMIN = _ymin
    YMAX = _ymax
    ZMIN = _zmin
    ZMAX = _zmax
    XMIN = _xmin
    XMAX = _xmax
    -> AttributeCreator_12 [off]
AttributeCreator_12 [off]
    ATTR_LIST = Query,http://gis3.nve.no/map/rest/services/Vannkraftverk/MapServer/6/query?where=1%3D1&text=&objectIds=&time=&geometry=@Value(_xmin),@Value(_ymin),@Value(_xmax),@Value(_ymax)&geometryType=esriGeometryEnvelope&inSR=&spatialRel=esriSpatialRelIntersects&relationParam=&outFields=&returnGeometry=true&maxAllowableOffset=&geometryPrecision=&outSR=&returnIdsOnly=false&returnCountOnly=false&orderByFields=&groupByFieldsForStatistics=&outStatistics=&returnZ=false&returnM=false&gdbVersion=&returnDistinctValues=false&returnTrueCurves=false&resultOffset=&resultRecordCount=&f=pjson
    -> FeatureReader_12 [off]
FeatureReader_12 [off]
    FORMAT = ESRIJSON
    OUTPUT_FEATURES_DISPLAY = Only Data Features
    ESRIJSON_CLIP_TO_ENVELOPE = NO
    COMBINE_GEOM = Use Result
    ESRIJSON_USE_BASENAME_AS_DEFAULT_FEATURE_TYPE = No
    ESRIJSON_USE_SEARCH_ENVELOPE = NO
    DATASET = @Value(Query)
    ATTR_ACCUM_MODE = Only Use Result
    ESRIJSON_DELETE_DOWNLOAD_FILE = Yes
    ESRIJSON_SIMPLIFY_MULTIS = Yes
    INTERACT = <No Spatial Filter>
    ESRIJSON_MAKE_PATHS = No
    FEATURETYPES_RADIO = FEATURETYPES
    ESRIJSON_MAKE_DONUTS = No
    <OTHER> -> Matcher_12 [off]
Matcher_12 [off]
    LENIENT_MATCH = No
    MATCH = 2D
    CNT_ATTR = _match_id
    MATCH_STRATEGY = Match Selected Attributes
    BLANK_AND_MISSING_DIFFER = No
    SINGLE_MATCHED -> magasin (writer SHAPE_1) [off]
    NOT_MATCHED -> magasin (writer SHAPE_1) [off]
magasin (writer SHAPE_1) [off]
    attributes: _match_id char(200)
Note: Lager polygon av / envelope
Creator_14 [off]
    NUM = 1
    COORDS = $(MINX) $(MINY) $(MAXX) $(MINY) $(MAXX) $(MAXY)  $(MINX) $(MAXY)  $(MINX) $(MINY)
    GEOMTYPE = 2D Coordinate List
    COORDSYS = EPSG:25833
    CREATED -> Reprojector_14 [off]
Note: Projiserer envelopen til 25833
Reprojector_14 [off]
    DEST = EPSG:25833
    STROKE_ARCS = Yes
    SOURCE = Read from feature
    INTERPOLATION_TYPE_NAME = Nearest Neighbor
    RASTER_CELL_SIZE = Preserve Cells
    REPROJECTED -> Tiler_13 [off]
Note: Tiler opp envelopen i mindre / områder
Tiler_13 [off]
    TILING_TYPE = Tile Size
    XINC = 100000
    ROW_ATTR = _row
    YINC = 100000
    COL_ATTR = _column
    TILED -> BoundsExtractor_13 [off]
BoundsExtractor_13 [off]
    YMIN = _ymin
    YMAX = _ymax
    ZMIN = _zmin
    ZMAX = _zmax
    XMIN = _xmin
    XMAX = _xmax
    -> AttributeCreator_13 [off]
AttributeCreator_13 [off]
    ATTR_LIST = Query,http://gis3.nve.no/map/rest/services/Vannkraftverk/MapServer/0/query?where=1%3D1&text=&objectIds=&time=&geometry=@Value(_xmin),@Value(_ymin),@Value(_xmax),@Value(_ymax)&geometryType=esriGeometryEnvelope&inSR=&spatialRel=esriSpatialRelIntersects&relationParam=&outFields=&returnGeometry=true&maxAllowableOffset=&geometryPrecision=&outSR=&returnIdsOnly=false&returnCountOnly=false&orderByFields=&groupByFieldsForStatistics=&outStatistics=&returnZ=false&returnM=false&gdbVersion=&returnDistinctValues=false&returnTrueCurves=false&resultOffset=&resultRecordCount=&f=pjson
    -> FeatureReader_13 [off]
FeatureReader_13 [off]
    FORMAT = ESRIJSON
    OUTPUT_FEATURES_DISPLAY = Only Data Features
    ESRIJSON_CLIP_TO_ENVELOPE = NO
    COMBINE_GEOM = Use Result
    ESRIJSON_USE_BASENAME_AS_DEFAULT_FEATURE_TYPE = No
    ESRIJSON_USE_SEARCH_ENVELOPE = NO
    DATASET = @Value(Query)
    ATTR_ACCUM_MODE = Only Use Result
    ESRIJSON_DELETE_DOWNLOAD_FILE = Yes
    ESRIJSON_SIMPLIFY_MULTIS = Yes
    INTERACT = <No Spatial Filter>
    ESRIJSON_MAKE_PATHS = No
    FEATURETYPES_RADIO = FEATURETYPES
    ESRIJSON_MAKE_DONUTS = No
    <OTHER> -> Matcher_13 [off]
Matcher_13 [off]
    LENIENT_MATCH = No
    MATCH = 2D
    CNT_ATTR = _match_id
    MATCH_STRATEGY = Match Selected Attributes
    BLANK_AND_MISSING_DIFFER = No
    SINGLE_MATCHED -> dam (writer SHAPE_1) [off]
    NOT_MATCHED -> dam (writer SHAPE_1) [off]
dam (writer SHAPE_1) [off]
    attributes: _match_id char(200)
Note: Lager polygon av / envelope
Creator_15 [off]
    NUM = 1
    COORDS = $(MINX) $(MINY) $(MAXX) $(MINY) $(MAXX) $(MAXY)  $(MINX) $(MAXY)  $(MINX) $(MINY)
    GEOMTYPE = 2D Coordinate List
    COORDSYS = EPSG:25833
    CREATED -> Reprojector_15 [off]
Note: Projiserer envelopen til 25833
Reprojector_15 [off]
    DEST = EPSG:25833
    STROKE_ARCS = Yes
    SOURCE = Read from feature
    INTERPOLATION_TYPE_NAME = Nearest Neighbor
    RASTER_CELL_SIZE = Preserve Cells
    REPROJECTED -> Tiler_14 [off]
Note: Tiler opp envelopen i mindre / områder
Tiler_14 [off]
    TILING_TYPE = Tile Size
    XINC = 100000
    ROW_ATTR = _row
    YINC = 100000
    COL_ATTR = _column
    TILED -> BoundsExtractor_14 [off]
BoundsExtractor_14 [off]
    YMIN = _ymin
    YMAX = _ymax
    ZMIN = _zmin
    ZMAX = _zmax
    XMIN = _xmin
    XMAX = _xmax
    -> AttributeCreator_14 [off]
AttributeCreator_14 [off]
    ATTR_LIST = Query,http://gis3.nve.no/map/rest/services/Vannkraftverk/MapServer/4/query?where=1%3D1&text=&objectIds=&time=&geometry=@Value(_xmin),@Value(_ymin),@Value(_xmax),@Value(_ymax)&geometryType=esriGeometryEnvelope&inSR=&spatialRel=esriSpatialRelIntersects&relationParam=&outFields=&returnGeometry=true&maxAllowableOffset=&geometryPrecision=&outSR=&returnIdsOnly=false&returnCountOnly=false&orderByFields=&groupByFieldsForStatistics=&outStatistics=&returnZ=false&returnM=false&gdbVersion=&returnDistinctValues=false&returnTrueCurves=false&resultOffset=&resultRecordCount=&f=pjson
    -> FeatureReader_14 [off]
FeatureReader_14 [off]
    FORMAT = ESRIJSON
    OUTPUT_FEATURES_DISPLAY = Only Data Features
    ESRIJSON_CLIP_TO_ENVELOPE = NO
    COMBINE_GEOM = Use Result
    ESRIJSON_USE_BASENAME_AS_DEFAULT_FEATURE_TYPE = No
    ESRIJSON_USE_SEARCH_ENVELOPE = NO
    DATASET = @Value(Query)
    ATTR_ACCUM_MODE = Only Use Result
    ESRIJSON_DELETE_DOWNLOAD_FILE = Yes
    ESRIJSON_SIMPLIFY_MULTIS = Yes
    INTERACT = <No Spatial Filter>
    ESRIJSON_MAKE_PATHS = No
    FEATURETYPES_RADIO = FEATURETYPES
    ESRIJSON_MAKE_DONUTS = No
    <OTHER> -> Matcher_14 [off]
Matcher_14 [off]
    LENIENT_MATCH = No
    MATCH = 2D
    CNT_ATTR = _match_id
    MATCH_STRATEGY = Match Selected Attributes
    BLANK_AND_MISSING_DIFFER = No
    SINGLE_MATCHED -> vanninntak (writer SHAPE_1) [off]
    NOT_MATCHED -> vanninntak (writer SHAPE_1) [off]
vanninntak (writer SHAPE_1) [off]
    attributes: _match_id char(200)
Note: Lager polygon av / envelope
Creator_16 [off]
    NUM = 1
    COORDS = $(MINX) $(MINY) $(MAXX) $(MINY) $(MAXX) $(MAXY)  $(MINX) $(MAXY)  $(MINX) $(MINY)
    GEOMTYPE = 2D Coordinate List
    COORDSYS = EPSG:25833
    CREATED -> Reprojector_16 [off]
Note: Projiserer envelopen til 25833
Reprojector_16 [off]
    DEST = EPSG:25833
    STROKE_ARCS = Yes
    SOURCE = Read from feature
    INTERPOLATION_TYPE_NAME = Nearest Neighbor
    RASTER_CELL_SIZE = Preserve Cells
    REPROJECTED -> Tiler_15 [off]
Note: Tiler opp envelopen i mindre / områder
Tiler_15 [off]
    TILING_TYPE = Tile Size
    XINC = 100000
    ROW_ATTR = _row
    YINC = 100000
    COL_ATTR = _column
    TILED -> BoundsExtractor_15 [off]
BoundsExtractor_15 [off]
    YMIN = _ymin
    YMAX = _ymax
    ZMIN = _zmin
    ZMAX = _zmax
    XMIN = _xmin
    XMAX = _xmax
    -> AttributeCreator_15 [off]
AttributeCreator_15 [off]
    ATTR_LIST = Query,http://gis3.nve.no/map/rest/services/Vannkraftverk/MapServer/3/query?where=1%3D1&text=&objectIds=&time=&geometry=@Value(_xmin),@Value(_ymin),@Value(_xmax),@Value(_ymax)&geometryType=esriGeometryEnvelope&inSR=&spatialRel=esriSpatialRelIntersects&relationParam=&outFields=&returnGeometry=true&maxAllowableOffset=&geometryPrecision=&outSR=&returnIdsOnly=false&returnCountOnly=false&orderByFields=&groupByFieldsForStatistics=&outStatistics=&returnZ=false&returnM=false&gdbVersion=&returnDistinctValues=false&returnTrueCurves=false&resultOffset=&resultRecordCount=&f=pjson
    -> FeatureReader_15 [off]
FeatureReader_15 [off]
    FORMAT = ESRIJSON
    OUTPUT_FEATURES_DISPLAY = Only Data Features
    ESRIJSON_CLIP_TO_ENVELOPE = NO
    COMBINE_GEOM = Use Result
    ESRIJSON_USE_BASENAME_AS_DEFAULT_FEATURE_TYPE = No
    ESRIJSON_USE_SEARCH_ENVELOPE = NO
    DATASET = @Value(Query)
    ATTR_ACCUM_MODE = Only Use Result
    ESRIJSON_DELETE_DOWNLOAD_FILE = Yes
    ESRIJSON_SIMPLIFY_MULTIS = Yes
    INTERACT = <No Spatial Filter>
    ESRIJSON_MAKE_PATHS = No
    FEATURETYPES_RADIO = FEATURETYPES
    ESRIJSON_MAKE_DONUTS = No
    <OTHER> -> Matcher_15 [off]
Matcher_15 [off]
    LENIENT_MATCH = No
    MATCH = 2D
    CNT_ATTR = _match_id
    MATCH_STRATEGY = Match Selected Attributes
    BLANK_AND_MISSING_DIFFER = No
    SINGLE_MATCHED -> vannvei (writer SHAPE_1) [off]
    NOT_MATCHED -> vannvei (writer SHAPE_1) [off]
vannvei (writer SHAPE_1) [off]
    attributes: _match_id char(200)
Note: Lager polygon av / envelope
Creator_17 [off]
    NUM = 1
    COORDS = $(MINX) $(MINY) $(MAXX) $(MINY) $(MAXX) $(MAXY)  $(MINX) $(MAXY)  $(MINX) $(MINY)
    GEOMTYPE = 2D Coordinate List
    COORDSYS = EPSG:25833
    CREATED -> Reprojector_17 [off]
Note: Projiserer envelopen til 25833
Reprojector_17 [off]
    DEST = EPSG:25833
    STROKE_ARCS = Yes
    SOURCE = Read from feature
    INTERPOLATION_TYPE_NAME = Nearest Neighbor
    RASTER_CELL_SIZE = Preserve Cells
    REPROJECTED -> Tiler_16 [off]
Note: Tiler opp envelopen i mindre / områder
Tiler_16 [off]
    TILING_TYPE = Tile Size
    XINC = 100000
    ROW_ATTR = _row
    YINC = 100000
    COL_ATTR = _column
    TILED -> BoundsExtractor_16 [off]
BoundsExtractor_16 [off]
    YMIN = _ymin
    YMAX = _ymax
    ZMIN = _zmin
    ZMAX = _zmax
    XMIN = _xmin
    XMAX = _xmax
    -> AttributeCreator_16 [off]
AttributeCreator_16 [off]
    ATTR_LIST = Query,http://gis3.nve.no/map/rest/services/Vannkraftverk/MapServer/1/query?where=1%3D1&text=&objectIds=&time=&geometry=@Value(_xmin),@Value(_ymin),@Value(_xmax),@Value(_ymax)&geometryType=esriGeometryEnvelope&inSR=&spatialRel=esriSpatialRelIntersects&relationParam=&outFields=&returnGeometry=true&maxAllowableOffset=&geometryPrecision=&outSR=&returnIdsOnly=false&returnCountOnly=false&orderByFields=&groupByFieldsForStatistics=&outStatistics=&returnZ=false&returnM=false&gdbVersion=&returnDistinctValues=false&returnTrueCurves=false&resultOffset=&resultRecordCount=&f=pjson
    -> FeatureReader_16 [off]
FeatureReader_16 [off]
    FORMAT = ESRIJSON
    OUTPUT_FEATURES_DISPLAY = Only Data Features
    ESRIJSON_CLIP_TO_ENVELOPE = NO
    COMBINE_GEOM = Use Result
    ESRIJSON_USE_BASENAME_AS_DEFAULT_FEATURE_TYPE = No
    ESRIJSON_USE_SEARCH_ENVELOPE = NO
    DATASET = @Value(Query)
    ATTR_ACCUM_MODE = Only Use Result
    ESRIJSON_DELETE_DOWNLOAD_FILE = Yes
    ESRIJSON_SIMPLIFY_MULTIS = Yes
    INTERACT = <No Spatial Filter>
    ESRIJSON_MAKE_PATHS = No
    FEATURETYPES_RADIO = FEATURETYPES
    ESRIJSON_MAKE_DONUTS = No
    <OTHER> -> Matcher_16 [off]
Matcher_16 [off]
    LENIENT_MATCH = No
    MATCH = 2D
    CNT_ATTR = _match_id
    MATCH_STRATEGY = Match Selected Attributes
    BLANK_AND_MISSING_DIFFER = No
    SINGLE_MATCHED -> delfelt_vannkraft (writer SHAPE_1) [off]
    NOT_MATCHED -> delfelt_vannkraft (writer SHAPE_1) [off]
delfelt_vannkraft (writer SHAPE_1) [off]
    attributes: _match_id char(200)

Bookmark: Hydrologi
Note: Lager polygon av / envelope
Creator_2 [off]
    NUM = 1
    COORDS = $(MINX) $(MINY) $(MAXX) $(MINY) $(MAXX) $(MAXY)  $(MINX) $(MAXY)  $(MINX) $(MINY)
    GEOMTYPE = 2D Coordinate List
    COORDSYS = EPSG:25833
    CREATED -> Reprojector_2 [off]
Note: Projiserer envelopen til 25833
Reprojector_2 [off]
    DEST = EPSG:25833
    STROKE_ARCS = Yes
    SOURCE = Read from feature
    INTERPOLATION_TYPE_NAME = Nearest Neighbor
    RASTER_CELL_SIZE = Preserve Cells
    REPROJECTED -> Tiler [off]
Note: Tiler opp envelopen i mindre / områder
Tiler [off]
    TILING_TYPE = Tile Size
    XINC = $(TILESIZE)
    ROW_ATTR = _row
    YINC = $(TILESIZE)
    COL_ATTR = _column
    TILED -> BoundsExtractor [off]
BoundsExtractor [off]
    YMIN = _ymin
    YMAX = _ymax
    ZMIN = _zmin
    ZMAX = _zmax
    XMIN = _xmin
    XMAX = _xmax
    -> AttributeCreator [off]
AttributeCreator [off]
    ATTR_LIST = Query,http://gis3.nve.no/map/rest/services/Elvenett/MapServer/1/query?where=1%3D1&text=&objectIds=&time=&geometry=@Value(_xmin),@Value(_ymin),@Value(_xmax),@Value(_ymax)&geometryType=esriGeometryEnvelope&inSR=&spatialRel=esriSpatialRelIntersects&relationParam=&outFields=&returnGeometry=true&maxAllowableOffset=&geometryPrecision=&outSR=&returnIdsOnly=false&returnCountOnly=false&orderByFields=&groupByFieldsForStatistics=&outStatistics=&returnZ=false&returnM=false&gdbVersion=&returnDistinctValues=false&returnTrueCurves=false&resultOffset=&resultRecordCount=&f=pjson
    -> FeatureReader [off]
FeatureReader [off]
    FORMAT = ESRIJSON
    OUTPUT_FEATURES_DISPLAY = Only Data Features
    ESRIJSON_CLIP_TO_ENVELOPE = NO
    COMBINE_GEOM = Use Result
    ESRIJSON_USE_BASENAME_AS_DEFAULT_FEATURE_TYPE = No
    ESRIJSON_USE_SEARCH_ENVELOPE = NO
    DATASET = @Value(Query)
    ATTR_ACCUM_MODE = Only Use Result
    ESRIJSON_DELETE_DOWNLOAD_FILE = Yes
    ESRIJSON_SIMPLIFY_MULTIS = Yes
    INTERACT = <No Spatial Filter>
    ESRIJSON_MAKE_PATHS = No
    FEATURETYPES_RADIO = FEATURETYPES
    ESRIJSON_MAKE_DONUTS = No
    <OTHER> -> Matcher [off]
Matcher [off]
    LENIENT_MATCH = No
    MATCH = 2D
    CNT_ATTR = _match_id
    MATCH_STRATEGY = Match Selected Attributes
    BLANK_AND_MISSING_DIFFER = No
    SINGLE_MATCHED -> Elvis_hovedneett (writer SHAPE_1) [off]
    NOT_MATCHED -> Elvis_hovedneett (writer SHAPE_1) [off]
Elvis_hovedneett (writer SHAPE_1) [off]
    attributes: _match_id char(200)
Note: Lager polygon av / envelope
Creator_3 [off]
    NUM = 1
    COORDS = $(MINX) $(MINY) $(MAXX) $(MINY) $(MAXX) $(MAXY)  $(MINX) $(MAXY)  $(MINX) $(MINY)
    GEOMTYPE = 2D Coordinate List
    COORDSYS = EPSG:25833
    CREATED -> Reprojector_3 [off]
Note: Projiserer envelopen til 25833
Reprojector_3 [off]
    DEST = EPSG:25833
    STROKE_ARCS = Yes
    SOURCE = Read from feature
    INTERPOLATION_TYPE_NAME = Nearest Neighbor
    RASTER_CELL_SIZE = Preserve Cells
    REPROJECTED -> Tiler_2 [off]
Note: Tiler opp envelopen i mindre / områder
Tiler_2 [off]
    TILING_TYPE = Tile Size
    XINC = 25000
    ROW_ATTR = _row
    YINC = 25000
    COL_ATTR = _column
    TILED -> BoundsExtractor_2 [off]
BoundsExtractor_2 [off]
    YMIN = _ymin
    YMAX = _ymax
    ZMIN = _zmin
    ZMAX = _zmax
    XMIN = _xmin
    XMAX = _xmax
    -> AttributeCreator_2 [off]
AttributeCreator_2 [off]
    ATTR_LIST = Query2,http://gis3.nve.no/map/rest/services/Elvenett/MapServer/2/query?where=1%3D1&text=&objectIds=&time=&geometry=@Value(_xmin),@Value(_ymin),@Value(_xmax),@Value(_ymax)&geometryType=esriGeometryEnvelope&inSR=&spatialRel=esriSpatialRelIntersects&relationParam=&outFields=&returnGeometry=true&maxAllowableOffset=&geometryPrecision=&outSR=&returnIdsOnly=false&returnCountOnly=false&orderByFields=&groupByFieldsForStatistics=&outStatistics=&returnZ=false&returnM=false&gdbVersion=&returnDistinctValues=false&returnTrueCurves=false&resultOffset=&resultRecordCount=&f=pjson
    -> FeatureReader_2 [off]
FeatureReader_2 [off]
    FORMAT = ESRIJSON
    OUTPUT_FEATURES_DISPLAY = Only Data Features
    ESRIJSON_CLIP_TO_ENVELOPE = NO
    COMBINE_GEOM = Use Result
    ESRIJSON_USE_BASENAME_AS_DEFAULT_FEATURE_TYPE = No
    ESRIJSON_USE_SEARCH_ENVELOPE = NO
    DATASET = @Value(Query2)
    ATTR_ACCUM_MODE = Only Use Result
    ESRIJSON_DELETE_DOWNLOAD_FILE = Yes
    ESRIJSON_SIMPLIFY_MULTIS = Yes
    INTERACT = <No Spatial Filter>
    ESRIJSON_MAKE_PATHS = No
    FEATURETYPES_RADIO = FEATURETYPES
    ESRIJSON_MAKE_DONUTS = No
    <OTHER> -> Matcher_2 [off]
Matcher_2 [off]
    LENIENT_MATCH = No
    MATCH = 2D
    CNT_ATTR = _match_id
    MATCH_STRATEGY = Match Selected Attributes
    BLANK_AND_MISSING_DIFFER = No
    SINGLE_MATCHED -> Elvis_elvenett (writer SHAPE_1) [off]
    NOT_MATCHED -> Elvis_elvenett (writer SHAPE_1) [off]
Elvis_elvenett (writer SHAPE_1) [off]
    attributes: _match_id char(200)
Note: Lager polygon av / envelope
Creator_4 [off]
    NUM = 1
    COORDS = $(MINX) $(MINY) $(MAXX) $(MINY) $(MAXX) $(MAXY)  $(MINX) $(MAXY)  $(MINX) $(MINY)
    GEOMTYPE = 2D Coordinate List
    COORDSYS = EPSG:25833
    CREATED -> Reprojector_4 [off]
Note: Projiserer envelopen til 25833
Reprojector_4 [off]
    DEST = EPSG:25833
    STROKE_ARCS = Yes
    SOURCE = Read from feature
    INTERPOLATION_TYPE_NAME = Nearest Neighbor
    RASTER_CELL_SIZE = Preserve Cells
    REPROJECTED -> Tiler_3 [off]
Note: Tiler opp envelopen i mindre / områder
Tiler_3 [off]
    TILING_TYPE = Tile Size
    XINC = 25000
    ROW_ATTR = _row
    YINC = 25000
    COL_ATTR = _column
    TILED -> BoundsExtractor_3 [off]
BoundsExtractor_3 [off]
    YMIN = _ymin
    YMAX = _ymax
    ZMIN = _zmin
    ZMAX = _zmax
    XMIN = _xmin
    XMAX = _xmax
    -> AttributeCreator_3 [off]
AttributeCreator_3 [off]
    ATTR_LIST = Query,http://gis3.nve.no/map/rest/services/Innsjodatabase/MapServer/1/query?where=1%3D1&text=&objectIds=&time=&geometry=@Value(_xmin),@Value(_ymin),@Value(_xmax),@Value(_ymax)&geometryType=esriGeometryEnvelope&inSR=&spatialRel=esriSpatialRelIntersects&relationParam=&outFields=&returnGeometry=true&maxAllowableOffset=&geometryPrecision=&outSR=&returnIdsOnly=false&returnCountOnly=false&orderByFields=&groupByFieldsForStatistics=&outStatistics=&returnZ=false&returnM=false&gdbVersion=&returnDistinctValues=false&returnTrueCurves=false&resultOffset=&resultRecordCount=&f=pjson
    -> FeatureReader_3 [off]
FeatureReader_3 [off]
    FORMAT = ESRIJSON
    OUTPUT_FEATURES_DISPLAY = Only Data Features
    ESRIJSON_CLIP_TO_ENVELOPE = NO
    COMBINE_GEOM = Use Result
    ESRIJSON_USE_BASENAME_AS_DEFAULT_FEATURE_TYPE = No
    ESRIJSON_USE_SEARCH_ENVELOPE = NO
    DATASET = @Value(Query)
    ATTR_ACCUM_MODE = Only Use Result
    ESRIJSON_DELETE_DOWNLOAD_FILE = Yes
    ESRIJSON_SIMPLIFY_MULTIS = Yes
    INTERACT = <No Spatial Filter>
    ESRIJSON_MAKE_PATHS = No
    FEATURETYPES_RADIO = FEATURETYPES
    ESRIJSON_MAKE_DONUTS = No
    <OTHER> -> Matcher_3 [off]
Matcher_3 [off]
    LENIENT_MATCH = No
    MATCH = 2D
    CNT_ATTR = _match_id
    MATCH_STRATEGY = Match Selected Attributes
    BLANK_AND_MISSING_DIFFER = No
    SINGLE_MATCHED -> Innsjo (writer SHAPE_1) [off]
    NOT_MATCHED -> Innsjo (writer SHAPE_1) [off]
Innsjo (writer SHAPE_1) [off]
    attributes: _match_id char(200)
Note: Lager polygon av / envelope
Creator_5 [off]
    NUM = 1
    COORDS = $(MINX) $(MINY) $(MAXX) $(MINY) $(MAXX) $(MAXY)  $(MINX) $(MAXY)  $(MINX) $(MINY)
    GEOMTYPE = 2D Coordinate List
    COORDSYS = EPSG:25833
    CREATED -> Reprojector_5 [off]
Note: Projiserer envelopen til 25833
Reprojector_5 [off]
    DEST = EPSG:25833
    STROKE_ARCS = Yes
    SOURCE = Read from feature
    INTERPOLATION_TYPE_NAME = Nearest Neighbor
    RASTER_CELL_SIZE = Preserve Cells
    REPROJECTED -> Tiler_4 [off]
Note: Tiler opp envelopen i mindre / områder
Tiler_4 [off]
    TILING_TYPE = Tile Size
    XINC = 100000
    ROW_ATTR = _row
    YINC = 100000
    COL_ATTR = _column
    TILED -> BoundsExtractor_4 [off]
BoundsExtractor_4 [off]
    YMIN = _ymin
    YMAX = _ymax
    ZMIN = _zmin
    ZMAX = _zmax
    XMIN = _xmin
    XMAX = _xmax
    -> AttributeCreator_4 [off]
AttributeCreator_4 [off]
    ATTR_LIST = Query,http://gis3.nve.no/map/rest/services/Innsjodatabase/MapServer/0/query?where=1%3D1&text=&objectIds=&time=&geometry=@Value(_xmin),@Value(_ymin),@Value(_xmax),@Value(_ymax)&geometryType=esriGeometryEnvelope&inSR=&spatialRel=esriSpatialRelIntersects&relationParam=&outFields=&returnGeometry=true&maxAllowableOffset=&geometryPrecision=&outSR=&returnIdsOnly=false&returnCountOnly=false&orderByFields=&groupByFieldsForStatistics=&outStatistics=&returnZ=false&returnM=false&gdbVersion=&returnDistinctValues=false&returnTrueCurves=false&resultOffset=&resultRecordCount=&f=pjson
    -> FeatureReader_4 [off]
FeatureReader_4 [off]
    FORMAT = ESRIJSON
    OUTPUT_FEATURES_DISPLAY = Only Data Features
    ESRIJSON_CLIP_TO_ENVELOPE = NO
    COMBINE_GEOM = Use Result
    ESRIJSON_USE_BASENAME_AS_DEFAULT_FEATURE_TYPE = No
    ESRIJSON_USE_SEARCH_ENVELOPE = NO
    DATASET = @Value(Query)
    ATTR_ACCUM_MODE = Only Use Result
    ESRIJSON_DELETE_DOWNLOAD_FILE = Yes
    ESRIJSON_SIMPLIFY_MULTIS = Yes
    INTERACT = <No Spatial Filter>
    ESRIJSON_MAKE_PATHS = No
    FEATURETYPES_RADIO = FEATURETYPES
    ESRIJSON_MAKE_DONUTS = No
    <OTHER> -> Matcher_4 [off]
Matcher_4 [off]
    LENIENT_MATCH = No
    MATCH = 2D
    CNT_ATTR = _match_id
    MATCH_STRATEGY = Match Selected Attributes
    BLANK_AND_MISSING_DIFFER = No
    SINGLE_MATCHED -> Dybdekart (writer SHAPE_1) [off]
    NOT_MATCHED -> Dybdekart (writer SHAPE_1) [off]
Dybdekart (writer SHAPE_1) [off]
    attributes: _match_id char(200)
Note: Lager polygon av / envelope
Creator_7 [off]
    NUM = 1
    COORDS = $(MINX) $(MINY) $(MAXX) $(MINY) $(MAXX) $(MAXY)  $(MINX) $(MAXY)  $(MINX) $(MINY)
    GEOMTYPE = 2D Coordinate List
    COORDSYS = EPSG:25833
    CREATED -> Reprojector_7 [off]
Note: Projiserer envelopen til 25833
Reprojector_7 [off]
    DEST = EPSG:25833
    STROKE_ARCS = Yes
    SOURCE = Read from feature
    INTERPOLATION_TYPE_NAME = Nearest Neighbor
    RASTER_CELL_SIZE = Preserve Cells
    REPROJECTED -> Tiler_6 [off]
Note: Tiler opp envelopen i mindre / områder
Tiler_6 [off]
    TILING_TYPE = Tile Size
    XINC = 100000
    ROW_ATTR = _row
    YINC = 100000
    COL_ATTR = _column
    TILED -> BoundsExtractor_6 [off]
BoundsExtractor_6 [off]
    YMIN = _ymin
    YMAX = _ymax
    ZMIN = _zmin
    ZMAX = _zmax
    XMIN = _xmin
    XMAX = _xmax
    -> AttributeCreator_6 [off]
AttributeCreator_6 [off]
    ATTR_LIST = Query,http://gis3.nve.no/map/rest/services/Nedborfelt/MapServer/1/query?where=1%3D1&text=&objectIds=&time=&geometry=@Value(_xmin),@Value(_ymin),@Value(_xmax),@Value(_ymax)&geometryType=esriGeometryEnvelope&inSR=&spatialRel=esriSpatialRelIntersects&relationParam=&outFields=&returnGeometry=true&maxAllowableOffset=&geometryPrecision=&outSR=&returnIdsOnly=false&returnCountOnly=false&orderByFields=&groupByFieldsForStatistics=&outStatistics=&returnZ=false&returnM=false&gdbVersion=&returnDistinctValues=false&returnTrueCurves=false&resultOffset=&resultRecordCount=&f=pjson
    -> FeatureReader_6 [off]
FeatureReader_6 [off]
    FORMAT = ESRIJSON
    OUTPUT_FEATURES_DISPLAY = Only Data Features
    ESRIJSON_CLIP_TO_ENVELOPE = NO
    COMBINE_GEOM = Use Result
    ESRIJSON_USE_BASENAME_AS_DEFAULT_FEATURE_TYPE = No
    ESRIJSON_USE_SEARCH_ENVELOPE = NO
    DATASET = @Value(Query)
    ATTR_ACCUM_MODE = Only Use Result
    ESRIJSON_DELETE_DOWNLOAD_FILE = Yes
    ESRIJSON_SIMPLIFY_MULTIS = Yes
    INTERACT = <No Spatial Filter>
    ESRIJSON_MAKE_PATHS = No
    FEATURETYPES_RADIO = FEATURETYPES
    ESRIJSON_MAKE_DONUTS = No
    <OTHER> -> Matcher_6 [off]
Matcher_6 [off]
    LENIENT_MATCH = No
    MATCH = 2D
    CNT_ATTR = _match_id
    MATCH_STRATEGY = Match Selected Attributes
    BLANK_AND_MISSING_DIFFER = No
    SINGLE_MATCHED -> nedborfelttilhav (writer SHAPE_1) [off]
    NOT_MATCHED -> nedborfelttilhav (writer SHAPE_1) [off]
nedborfelttilhav (writer SHAPE_1) [off]
    attributes: _match_id char(200)
Note: Lager polygon av / envelope
Creator_8 [off]
    NUM = 1
    COORDS = $(MINX) $(MINY) $(MAXX) $(MINY) $(MAXX) $(MAXY)  $(MINX) $(MAXY)  $(MINX) $(MINY)
    GEOMTYPE = 2D Coordinate List
    COORDSYS = EPSG:25833
    CREATED -> Reprojector_8 [off]
Note: Projiserer envelopen til 25833
Reprojector_8 [off]
    DEST = EPSG:25833
    STROKE_ARCS = Yes
    SOURCE = Read from feature
    INTERPOLATION_TYPE_NAME = Nearest Neighbor
    RASTER_CELL_SIZE = Preserve Cells
    REPROJECTED -> Tiler_7 [off]
Note: Tiler opp envelopen i mindre / områder
Tiler_7 [off]
    TILING_TYPE = Tile Size
    XINC = 100000
    ROW_ATTR = _row
    YINC = 100000
    COL_ATTR = _column
    TILED -> BoundsExtractor_7 [off]
BoundsExtractor_7 [off]
    YMIN = _ymin
    YMAX = _ymax
    ZMIN = _zmin
    ZMAX = _zmax
    XMIN = _xmin
    XMAX = _xmax
    -> AttributeCreator_7 [off]
AttributeCreator_7 [off]
    ATTR_LIST = Query,http://gis3.nve.no/map/rest/services/Nedborfelt/MapServer/2/query?where=1%3D1&text=&objectIds=&time=&geometry=@Value(_xmin),@Value(_ymin),@Value(_xmax),@Value(_ymax)&geometryType=esriGeometryEnvelope&inSR=&spatialRel=esriSpatialRelIntersects&relationParam=&outFields=&returnGeometry=true&maxAllowableOffset=&geometryPrecision=&outSR=&returnIdsOnly=false&returnCountOnly=false&orderByFields=&groupByFieldsForStatistics=&outStatistics=&returnZ=false&returnM=false&gdbVersion=&returnDistinctValues=false&returnTrueCurves=false&resultOffset=&resultRecordCount=&f=pjson
    -> FeatureReader_7 [off]
FeatureReader_7 [off]
    FORMAT = ESRIJSON
    OUTPUT_FEATURES_DISPLAY = Only Data Features
    ESRIJSON_CLIP_TO_ENVELOPE = NO
    COMBINE_GEOM = Use Result
    ESRIJSON_USE_BASENAME_AS_DEFAULT_FEATURE_TYPE = No
    ESRIJSON_USE_SEARCH_ENVELOPE = NO
    DATASET = @Value(Query)
    ATTR_ACCUM_MODE = Only Use Result
    ESRIJSON_DELETE_DOWNLOAD_FILE = Yes
    ESRIJSON_SIMPLIFY_MULTIS = Yes
    INTERACT = <No Spatial Filter>
    ESRIJSON_MAKE_PATHS = No
    FEATURETYPES_RADIO = FEATURETYPES
    ESRIJSON_MAKE_DONUTS = No
    <OTHER> -> Matcher_7 [off]
Matcher_7 [off]
    LENIENT_MATCH = No
    MATCH = 2D
    CNT_ATTR = _match_id
    MATCH_STRATEGY = Match Selected Attributes
    BLANK_AND_MISSING_DIFFER = No
    SINGLE_MATCHED -> sidenedborfelt (writer SHAPE_1) [off]
    NOT_MATCHED -> sidenedborfelt (writer SHAPE_1) [off]
sidenedborfelt (writer SHAPE_1) [off]
    attributes: _match_id char(200)
Note: Lager polygon av / envelope
Creator_9 [off]
    NUM = 1
    COORDS = $(MINX) $(MINY) $(MAXX) $(MINY) $(MAXX) $(MAXY)  $(MINX) $(MAXY)  $(MINX) $(MINY)
    GEOMTYPE = 2D Coordinate List
    COORDSYS = EPSG:25833
    CREATED -> Reprojector_9 [off]
Note: Projiserer envelopen til 25833
Reprojector_9 [off]
    DEST = EPSG:25833
    STROKE_ARCS = Yes
    SOURCE = Read from feature
    INTERPOLATION_TYPE_NAME = Nearest Neighbor
    RASTER_CELL_SIZE = Preserve Cells
    REPROJECTED -> Tiler_8 [off]
Note: Tiler opp envelopen i mindre / områder
Tiler_8 [off]
    TILING_TYPE = Tile Size
    XINC = 100000
    ROW_ATTR = _row
    YINC = 100000
    COL_ATTR = _column
    TILED -> BoundsExtractor_8 [off]
BoundsExtractor_8 [off]
    YMIN = _ymin
    YMAX = _ymax
    ZMIN = _zmin
    ZMAX = _zmax
    XMIN = _xmin
    XMAX = _xmax
    -> AttributeCreator_8 [off]
AttributeCreator_8 [off]
    ATTR_LIST = Query,http://gis3.nve.no/map/rest/services/HydrologiskeData/MapServer/1/query?where=1%3D1&text=&objectIds=&time=&geometry=@Value(_xmin),@Value(_ymin),@Value(_xmax),@Value(_ymax)&geometryType=esriGeometryEnvelope&inSR=&spatialRel=esriSpatialRelIntersects&relationParam=&outFields=&returnGeometry=true&maxAllowableOffset=&geometryPrecision=&outSR=&returnIdsOnly=false&returnCountOnly=false&orderByFields=&groupByFieldsForStatistics=&outStatistics=&returnZ=false&returnM=false&gdbVersion=&returnDistinctValues=false&returnTrueCurves=false&resultOffset=&resultRecordCount=&f=pjson
    -> FeatureReader_8 [off]
FeatureReader_8 [off]
    FORMAT = ESRIJSON
    OUTPUT_FEATURES_DISPLAY = Only Data Features
    ESRIJSON_CLIP_TO_ENVELOPE = NO
    COMBINE_GEOM = Use Result
    ESRIJSON_USE_BASENAME_AS_DEFAULT_FEATURE_TYPE = No
    ESRIJSON_USE_SEARCH_ENVELOPE = NO
    DATASET = @Value(Query)
    ATTR_ACCUM_MODE = Only Use Result
    ESRIJSON_DELETE_DOWNLOAD_FILE = Yes
    ESRIJSON_SIMPLIFY_MULTIS = Yes
    INTERACT = <No Spatial Filter>
    ESRIJSON_MAKE_PATHS = No
    FEATURETYPES_RADIO = FEATURETYPES
    ESRIJSON_MAKE_DONUTS = No
    <OTHER> -> Matcher_8 [off]
Matcher_8 [off]
    LENIENT_MATCH = No
    MATCH = 2D
    CNT_ATTR = _match_id
    MATCH_STRATEGY = Match Selected Attributes
    BLANK_AND_MISSING_DIFFER = No
    SINGLE_MATCHED -> maaleserie (writer SHAPE_1) [off]
    NOT_MATCHED -> maaleserie (writer SHAPE_1) [off]
maaleserie (writer SHAPE_1) [off]
    attributes: _match_id char(200)
Note: Lager polygon av / envelope
Creator_10 [off]
    NUM = 1
    COORDS = $(MINX) $(MINY) $(MAXX) $(MINY) $(MAXX) $(MAXY)  $(MINX) $(MAXY)  $(MINX) $(MINY)
    GEOMTYPE = 2D Coordinate List
    COORDSYS = EPSG:25833
    CREATED -> Reprojector_10 [off]
Note: Projiserer envelopen til 25833
Reprojector_10 [off]
    DEST = EPSG:25833
    STROKE_ARCS = Yes
    SOURCE = Read from feature
    INTERPOLATION_TYPE_NAME = Nearest Neighbor
    RASTER_CELL_SIZE = Preserve Cells
    REPROJECTED -> Tiler_9 [off]
Note: Tiler opp envelopen i mindre / områder
Tiler_9 [off]
    TILING_TYPE = Tile Size
    XINC = 100000
    ROW_ATTR = _row
    YINC = 100000
    COL_ATTR = _column
    TILED -> BoundsExtractor_9 [off]
BoundsExtractor_9 [off]
    YMIN = _ymin
    YMAX = _ymax
    ZMIN = _zmin
    ZMAX = _zmax
    XMIN = _xmin
    XMAX = _xmax
    -> AttributeCreator_9 [off]
AttributeCreator_9 [off]
    ATTR_LIST = Query,http://gis3.nve.no/map/rest/services/HydrologiskeData/MapServer/2/query?where=1%3D1&text=&objectIds=&time=&geometry=@Value(_xmin),@Value(_ymin),@Value(_xmax),@Value(_ymax)&geometryType=esriGeometryEnvelope&inSR=&spatialRel=esriSpatialRelIntersects&relationParam=&outFields=&returnGeometry=true&maxAllowableOffset=&geometryPrecision=&outSR=&returnIdsOnly=false&returnCountOnly=false&orderByFields=&groupByFieldsForStatistics=&outStatistics=&returnZ=false&returnM=false&gdbVersion=&returnDistinctValues=false&returnTrueCurves=false&resultOffset=&resultRecordCount=&f=pjson
    -> FeatureReader_9 [off]
FeatureReader_9 [off]
    FORMAT = ESRIJSON
    OUTPUT_FEATURES_DISPLAY = Only Data Features
    ESRIJSON_CLIP_TO_ENVELOPE = NO
    COMBINE_GEOM = Use Result
    ESRIJSON_USE_BASENAME_AS_DEFAULT_FEATURE_TYPE = No
    ESRIJSON_USE_SEARCH_ENVELOPE = NO
    DATASET = @Value(Query)
    ATTR_ACCUM_MODE = Only Use Result
    ESRIJSON_DELETE_DOWNLOAD_FILE = Yes
    ESRIJSON_SIMPLIFY_MULTIS = Yes
    INTERACT = <No Spatial Filter>
    ESRIJSON_MAKE_PATHS = No
    FEATURETYPES_RADIO = FEATURETYPES
    ESRIJSON_MAKE_DONUTS = No
    <OTHER> -> Matcher_9 [off]
Matcher_9 [off]
    LENIENT_MATCH = No
    MATCH = 2D
    CNT_ATTR = _match_id
    MATCH_STRATEGY = Match Selected Attributes
    BLANK_AND_MISSING_DIFFER = No
    SINGLE_MATCHED -> totalnedborfelt_til_maalestasjon (writer SHAPE_1) [off]
    NOT_MATCHED -> totalnedborfelt_til_maalestasjon (writer SHAPE_1) [off]
totalnedborfelt_til_maalestasjon (writer SHAPE_1) [off]
    attributes: _match_id char(200)
Note: Lager polygon av / envelope
Creator_48 [off]
    NUM = 1
    COORDS = $(MINX) $(MINY) $(MAXX) $(MINY) $(MAXX) $(MAXY)  $(MINX) $(MAXY)  $(MINX) $(MINY)
    GEOMTYPE = 2D Coordinate List
    COORDSYS = EPSG:25833
    CREATED -> Reprojector_44 [off]
Note: Projiserer envelopen til 25833
Reprojector_44 [off]
    DEST = EPSG:25833
    STROKE_ARCS = Yes
    SOURCE = Read from feature
    INTERPOLATION_TYPE_NAME = Nearest Neighbor
    RASTER_CELL_SIZE = Preserve Cells
    REPROJECTED -> Tiler_43 [off]
Note: Tiler opp envelopen i mindre / områder
Tiler_43 [off]
    TILING_TYPE = Tile Size
    XINC = 100000
    ROW_ATTR = _row
    YINC = 100000
    COL_ATTR = _column
    TILED -> BoundsExtractor_43 [off]
BoundsExtractor_43 [off]
    YMIN = _ymin
    YMAX = _ymax
    ZMIN = _zmin
    ZMAX = _zmax
    XMIN = _xmin
    XMAX = _xmax
    -> AttributeCreator_27 [off]
AttributeCreator_27 [off]
    ATTR_LIST = Query,http://gis3.nve.no/map/rest/services/Nedborfelt/MapServer/3/query?where=1%3D1&text=&objectIds=&time=&geometry=@Value(_xmin),@Value(_ymin),@Value(_xmax),@Value(_ymax)&geometryType=esriGeometryEnvelope&inSR=&spatialRel=esriSpatialRelIntersects&relationParam=&outFields=&returnGeometry=true&maxAllowableOffset=&geometryPrecision=&outSR=&returnIdsOnly=false&returnCountOnly=false&orderByFields=&groupByFieldsForStatistics=&outStatistics=&returnZ=false&returnM=false&gdbVersion=&returnDistinctValues=false&returnTrueCurves=false&resultOffset=&resultRecordCount=&f=pjson
    -> FeatureReader_47 [off]
FeatureReader_47 [off]
    FORMAT = ESRIJSON
    OUTPUT_FEATURES_DISPLAY = Only Data Features
    ESRIJSON_CLIP_TO_ENVELOPE = NO
    COMBINE_GEOM = Use Result
    ESRIJSON_USE_BASENAME_AS_DEFAULT_FEATURE_TYPE = No
    ESRIJSON_USE_SEARCH_ENVELOPE = NO
    DATASET = @Value(Query)
    ATTR_ACCUM_MODE = Only Use Result
    ESRIJSON_DELETE_DOWNLOAD_FILE = Yes
    ESRIJSON_SIMPLIFY_MULTIS = Yes
    INTERACT = <No Spatial Filter>
    ESRIJSON_MAKE_PATHS = No
    FEATURETYPES_RADIO = FEATURETYPES
    ESRIJSON_MAKE_DONUTS = No
    <OTHER> -> Matcher_46 [off]
Matcher_46 [off]
    LENIENT_MATCH = No
    MATCH = 2D
    CNT_ATTR = _match_id
    MATCH_STRATEGY = Match Selected Attributes
    BLANK_AND_MISSING_DIFFER = No
    SINGLE_MATCHED -> Regine_enhet (writer SHAPE_1) [off]
    NOT_MATCHED -> Regine_enhet (writer SHAPE_1) [off]
Regine_enhet (writer SHAPE_1) [off]
    attributes: _match_id char(200)
Note: Lager polygon av / envelope
Creator_6 [off]
    NUM = 1
    COORDS = $(MINX) $(MINY) $(MAXX) $(MINY) $(MAXX) $(MAXY)  $(MINX) $(MAXY)  $(MINX) $(MINY)
    GEOMTYPE = 2D Coordinate List
    COORDSYS = EPSG:25833
    CREATED -> Reprojector_6 [off]
Note: Projiserer envelopen til 25833
Reprojector_6 [off]
    DEST = EPSG:25833
    STROKE_ARCS = Yes
    SOURCE = Read from feature
    INTERPOLATION_TYPE_NAME = Nearest Neighbor
    RASTER_CELL_SIZE = Preserve Cells
    REPROJECTED -> Tiler_5 [off]
Note: Tiler opp envelopen i mindre / områder
Tiler_5 [off]
    TILING_TYPE = Tile Size
    XINC = 100000
    ROW_ATTR = _row
    YINC = 100000
    COL_ATTR = _column
    TILED -> BoundsExtractor_5 [off]
BoundsExtractor_5 [off]
    YMIN = _ymin
    YMAX = _ymax
    ZMIN = _zmin
    ZMAX = _zmax
    XMIN = _xmin
    XMAX = _xmax
    -> AttributeCreator_5 [off]
AttributeCreator_5 [off]
    ATTR_LIST = Query,http://gis3.nve.no/map/rest/services/Nedborfelt/MapServer/0/query?where=1%3D1&text=&objectIds=&time=&geometry=@Value(_xmin),@Value(_ymin),@Value(_xmax),@Value(_ymax)&geometryType=esriGeometryEnvelope&inSR=&spatialRel=esriSpatialRelIntersects&relationParam=&outFields=&returnGeometry=true&maxAllowableOffset=&geometryPrecision=&outSR=&returnIdsOnly=false&returnCountOnly=false&orderByFields=&groupByFieldsForStatistics=&outStatistics=&returnZ=false&returnM=false&gdbVersion=&returnDistinctValues=false&returnTrueCurves=false&resultOffset=&resultRecordCount=&f=pjson
    -> FeatureReader_5 [off]
FeatureReader_5 [off]
    FORMAT = ESRIJSON
    OUTPUT_FEATURES_DISPLAY = Only Data Features
    ESRIJSON_CLIP_TO_ENVELOPE = NO
    COMBINE_GEOM = Use Result
    ESRIJSON_USE_BASENAME_AS_DEFAULT_FEATURE_TYPE = No
    ESRIJSON_USE_SEARCH_ENVELOPE = NO
    DATASET = @Value(Query)
    ATTR_ACCUM_MODE = Only Use Result
    ESRIJSON_DELETE_DOWNLOAD_FILE = Yes
    ESRIJSON_SIMPLIFY_MULTIS = Yes
    INTERACT = <No Spatial Filter>
    ESRIJSON_MAKE_PATHS = No
    FEATURETYPES_RADIO = FEATURETYPES
    ESRIJSON_MAKE_DONUTS = No
    <OTHER> -> Matcher_5 [off]
Matcher_5 [off]
    LENIENT_MATCH = No
    MATCH = 2D
    CNT_ATTR = _match_id
    MATCH_STRATEGY = Match Selected Attributes
    BLANK_AND_MISSING_DIFFER = No
    SINGLE_MATCHED -> Vassdragsomr (writer SHAPE_1) [off]
    NOT_MATCHED -> Vassdragsomr (writer SHAPE_1) [off]
Vassdragsomr (writer SHAPE_1) [off]
    attributes: _match_id char(200)

Bookmark: Vindkraft
Note: Lager polygon av / envelope
Creator_18 [off]
    NUM = 1
    COORDS = $(MINX) $(MINY) $(MAXX) $(MINY) $(MAXX) $(MAXY)  $(MINX) $(MAXY)  $(MINX) $(MINY)
    GEOMTYPE = 2D Coordinate List
    COORDSYS = EPSG:25833
    CREATED -> Reprojector_18 [off]
Note: Projiserer envelopen til 25833
Reprojector_18 [off]
    DEST = EPSG:25833
    STROKE_ARCS = Yes
    SOURCE = Read from feature
    INTERPOLATION_TYPE_NAME = Nearest Neighbor
    RASTER_CELL_SIZE = Preserve Cells
    REPROJECTED -> Tiler_17 [off]
Note: Tiler opp envelopen i mindre / områder
Tiler_17 [off]
    TILING_TYPE = Tile Size
    XINC = 100000
    ROW_ATTR = _row
    YINC = 100000
    COL_ATTR = _column
    TILED -> BoundsExtractor_17 [off]
BoundsExtractor_17 [off]
    YMIN = _ymin
    YMAX = _ymax
    ZMIN = _zmin
    ZMAX = _zmax
    XMIN = _xmin
    XMAX = _xmax
    -> AttributeCreator_17 [off]
AttributeCreator_17 [off]
    ATTR_LIST = Query,http://gis3.nve.no/map/rest/services/Vindkraftverk/MapServer/0/query?where=1%3D1&text=&objectIds=&time=&geometry=@Value(_xmin),@Value(_ymin),@Value(_xmax),@Value(_ymax)&geometryType=esriGeometryEnvelope&inSR=&spatialRel=esriSpatialRelIntersects&relationParam=&outFields=&returnGeometry=true&maxAllowableOffset=&geometryPrecision=&outSR=&returnIdsOnly=false&returnCountOnly=false&orderByFields=&groupByFieldsForStatistics=&outStatistics=&returnZ=false&returnM=false&gdbVersion=&returnDistinctValues=false&returnTrueCurves=false&resultOffset=&resultRecordCount=&f=pjson
    -> FeatureReader_17 [off]
FeatureReader_17 [off]
    FORMAT = ESRIJSON
    OUTPUT_FEATURES_DISPLAY = Only Data Features
    ESRIJSON_CLIP_TO_ENVELOPE = NO
    COMBINE_GEOM = Use Result
    ESRIJSON_USE_BASENAME_AS_DEFAULT_FEATURE_TYPE = No
    ESRIJSON_USE_SEARCH_ENVELOPE = NO
    DATASET = @Value(Query)
    ATTR_ACCUM_MODE = Only Use Result
    ESRIJSON_DELETE_DOWNLOAD_FILE = Yes
    ESRIJSON_SIMPLIFY_MULTIS = Yes
    INTERACT = <No Spatial Filter>
    ESRIJSON_MAKE_PATHS = No
    FEATURETYPES_RADIO = FEATURETYPES
    ESRIJSON_MAKE_DONUTS = No
    <OTHER> -> Matcher_17 [off]
Matcher_17 [off]
    LENIENT_MATCH = No
    MATCH = 2D
    CNT_ATTR = _match_id
    MATCH_STRATEGY = Match Selected Attributes
    BLANK_AND_MISSING_DIFFER = No
    SINGLE_MATCHED -> vindkraftverk_utbygd (writer SHAPE_1) [off]
    NOT_MATCHED -> vindkraftverk_utbygd (writer SHAPE_1) [off]
vindkraftverk_utbygd (writer SHAPE_1) [off]
    attributes: _match_id char(200)
Note: Lager polygon av / envelope
Creator_19 [off]
    NUM = 1
    COORDS = $(MINX) $(MINY) $(MAXX) $(MINY) $(MAXX) $(MAXY)  $(MINX) $(MAXY)  $(MINX) $(MINY)
    GEOMTYPE = 2D Coordinate List
    COORDSYS = EPSG:25833
    CREATED -> Reprojector_19 [off]
Note: Projiserer envelopen til 25833
Reprojector_19 [off]
    DEST = EPSG:25833
    STROKE_ARCS = Yes
    SOURCE = Read from feature
    INTERPOLATION_TYPE_NAME = Nearest Neighbor
    RASTER_CELL_SIZE = Preserve Cells
    REPROJECTED -> Tiler_18 [off]
Note: Tiler opp envelopen i mindre / områder
Tiler_18 [off]
    TILING_TYPE = Tile Size
    XINC = 100000
    ROW_ATTR = _row
    YINC = 100000
    COL_ATTR = _column
    TILED -> BoundsExtractor_18 [off]
BoundsExtractor_18 [off]
    YMIN = _ymin
    YMAX = _ymax
    ZMIN = _zmin
    ZMAX = _zmax
    XMIN = _xmin
    XMAX = _xmax
    -> AttributeCreator_18 [off]
AttributeCreator_18 [off]
    ATTR_LIST = Query,http://gis3.nve.no/map/rest/services/Vindkraftverk/MapServer/8/query?where=1%3D1&text=&objectIds=&time=&geometry=@Value(_xmin),@Value(_ymin),@Value(_xmax),@Value(_ymax)&geometryType=esriGeometryEnvelope&inSR=&spatialRel=esriSpatialRelIntersects&relationParam=&outFields=&returnGeometry=true&maxAllowableOffset=&geometryPrecision=&outSR=&returnIdsOnly=false&returnCountOnly=false&orderByFields=&groupByFieldsForStatistics=&outStatistics=&returnZ=false&returnM=false&gdbVersion=&returnDistinctValues=false&returnTrueCurves=false&resultOffset=&resultRecordCount=&f=pjson
    -> FeatureReader_18 [off]
FeatureReader_18 [off]
    FORMAT = ESRIJSON
    OUTPUT_FEATURES_DISPLAY = Only Data Features
    ESRIJSON_CLIP_TO_ENVELOPE = NO
    COMBINE_GEOM = Use Result
    ESRIJSON_USE_BASENAME_AS_DEFAULT_FEATURE_TYPE = No
    ESRIJSON_USE_SEARCH_ENVELOPE = NO
    DATASET = @Value(Query)
    ATTR_ACCUM_MODE = Only Use Result
    ESRIJSON_DELETE_DOWNLOAD_FILE = Yes
    ESRIJSON_SIMPLIFY_MULTIS = Yes
    INTERACT = <No Spatial Filter>
    ESRIJSON_MAKE_PATHS = No
    FEATURETYPES_RADIO = FEATURETYPES
    ESRIJSON_MAKE_DONUTS = No
    <OTHER> -> Matcher_18 [off]
Matcher_18 [off]
    LENIENT_MATCH = No
    MATCH = 2D
    CNT_ATTR = _match_id
    MATCH_STRATEGY = Match Selected Attributes
    BLANK_AND_MISSING_DIFFER = No
    SINGLE_MATCHED -> vindparkomraade_utbygd (writer SHAPE_1) [off]
    NOT_MATCHED -> vindparkomraade_utbygd (writer SHAPE_1) [off]
vindparkomraade_utbygd (writer SHAPE_1) [off]
    attributes: _match_id char(200)
Note: Lager polygon av / envelope
Creator_20 [off]
    NUM = 1
    COORDS = $(MINX) $(MINY) $(MAXX) $(MINY) $(MAXX) $(MAXY)  $(MINX) $(MAXY)  $(MINX) $(MINY)
    GEOMTYPE = 2D Coordinate List
    COORDSYS = EPSG:25833
    CREATED -> Reprojector_20 [off]
Note: Projiserer envelopen til 25833
Reprojector_20 [off]
    DEST = EPSG:25833
    STROKE_ARCS = Yes
    SOURCE = Read from feature
    INTERPOLATION_TYPE_NAME = Nearest Neighbor
    RASTER_CELL_SIZE = Preserve Cells
    REPROJECTED -> Tiler_19 [off]
Note: Tiler opp envelopen i mindre / områder
Tiler_19 [off]
    TILING_TYPE = Tile Size
    XINC = 100000
    ROW_ATTR = _row
    YINC = 100000
    COL_ATTR = _column
    TILED -> BoundsExtractor_19 [off]
BoundsExtractor_19 [off]
    YMIN = _ymin
    YMAX = _ymax
    ZMIN = _zmin
    ZMAX = _zmax
    XMIN = _xmin
    XMAX = _xmax
    -> AttributeCreator_19 [off]
AttributeCreator_19 [off]
    ATTR_LIST = Query,http://gis3.nve.no/map/rest/services/Vindkraftverk/MapServer/7/query?where=1%3D1&text=&objectIds=&time=&geometry=@Value(_xmin),@Value(_ymin),@Value(_xmax),@Value(_ymax)&geometryType=esriGeometryEnvelope&inSR=&spatialRel=esriSpatialRelIntersects&relationParam=&outFields=&returnGeometry=true&maxAllowableOffset=&geometryPrecision=&outSR=&returnIdsOnly=false&returnCountOnly=false&orderByFields=&groupByFieldsForStatistics=&outStatistics=&returnZ=false&returnM=false&gdbVersion=&returnDistinctValues=false&returnTrueCurves=false&resultOffset=&resultRecordCount=&f=pjson
    -> FeatureReader_19 [off]
FeatureReader_19 [off]
    FORMAT = ESRIJSON
    OUTPUT_FEATURES_DISPLAY = Only Data Features
    ESRIJSON_CLIP_TO_ENVELOPE = NO
    COMBINE_GEOM = Use Result
    ESRIJSON_USE_BASENAME_AS_DEFAULT_FEATURE_TYPE = No
    ESRIJSON_USE_SEARCH_ENVELOPE = NO
    DATASET = @Value(Query)
    ATTR_ACCUM_MODE = Only Use Result
    ESRIJSON_DELETE_DOWNLOAD_FILE = Yes
    ESRIJSON_SIMPLIFY_MULTIS = Yes
    INTERACT = <No Spatial Filter>
    ESRIJSON_MAKE_PATHS = No
    FEATURETYPES_RADIO = FEATURETYPES
    ESRIJSON_MAKE_DONUTS = No
    <OTHER> -> Matcher_19 [off]
Matcher_19 [off]
    LENIENT_MATCH = No
    MATCH = 2D
    CNT_ATTR = _match_id
    MATCH_STRATEGY = Match Selected Attributes
    BLANK_AND_MISSING_DIFFER = No
    SINGLE_MATCHED -> vindturbin_utbygd (writer SHAPE_1) [off]
    NOT_MATCHED -> vindturbin_utbygd (writer SHAPE_1) [off]
vindturbin_utbygd (writer SHAPE_1) [off]
    attributes: _match_id char(200)
Note: Lager polygon av / envelope
Creator_49
    NUM = 1
    COORDS = $(MINX) $(MINY) $(MAXX) $(MINY) $(MAXX) $(MAXY)  $(MINX) $(MAXY)  $(MINX) $(MINY)
    GEOMTYPE = 2D Coordinate List
    COORDSYS = EPSG:25833
    CREATED -> Reprojector_45
Note: Projiserer envelopen til 25833
Reprojector_45
    DEST = EPSG:25833
    STROKE_ARCS = Yes
    SOURCE = Read from feature
    INTERPOLATION_TYPE_NAME = Nearest Neighbor
    RASTER_CELL_SIZE = Preserve Cells
    REPROJECTED -> Tiler_44
Note: Tiler opp envelopen i mindre / områder
Tiler_44
    TILING_TYPE = Tile Size
    XINC = 100000
    ROW_ATTR = _row
    YINC = 100000
    COL_ATTR = _column
    TILED -> BoundsExtractor_44
BoundsExtractor_44
    YMIN = _ymin
    YMAX = _ymax
    ZMIN = _zmin
    ZMAX = _zmax
    XMIN = _xmin
    XMAX = _xmax
    -> AttributeCreator_28
AttributeCreator_28
    ATTR_LIST = Query,http://gis3.nve.no/map/rest/services/Vindkraftverk/MapServer/9/query?where=1%3D1&text=&objectIds=&time=&geometry=@Value(_xmin),@Value(_ymin),@Value(_xmax),@Value(_ymax)&geometryType=esriGeometryEnvelope&inSR=&spatialRel=esriSpatialRelIntersects&relationParam=&outFields=&returnGeometry=true&maxAllowableOffset=&geometryPrecision=&outSR=&returnIdsOnly=false&returnCountOnly=false&orderByFields=&groupByFieldsForStatistics=&outStatistics=&returnZ=false&returnM=false&gdbVersion=&returnDistinctValues=false&returnTrueCurves=false&resultOffset=&resultRecordCount=&f=pjson
    -> FeatureReader_48
FeatureReader_48
    FORMAT = ESRIJSON
    OUTPUT_FEATURES_DISPLAY = Only Data Features
    ESRIJSON_CLIP_TO_ENVELOPE = NO
    COMBINE_GEOM = Use Result
    ESRIJSON_USE_BASENAME_AS_DEFAULT_FEATURE_TYPE = No
    ESRIJSON_USE_SEARCH_ENVELOPE = NO
    DATASET = @Value(Query)
    ATTR_ACCUM_MODE = Only Use Result
    ESRIJSON_DELETE_DOWNLOAD_FILE = Yes
    ESRIJSON_SIMPLIFY_MULTIS = Yes
    INTERACT = <No Spatial Filter>
    ESRIJSON_MAKE_PATHS = No
    FEATURETYPES_RADIO = FEATURETYPES
    ESRIJSON_MAKE_DONUTS = No
    <OTHER> -> Matcher_47
Matcher_47
    LENIENT_MATCH = No
    MATCH = 2D
    CNT_ATTR = _match_id
    MATCH_STRATEGY = Match Selected Attributes
    BLANK_AND_MISSING_DIFFER = No
    SINGLE_MATCHED -> vindparkomraade_konsesjon (writer SHAPE_1)
    NOT_MATCHED -> vindparkomraade_konsesjon (writer SHAPE_1)
    SINGLE_MATCHED -> Matcher_47_SingleMatched
    NOT_MATCHED -> Matcher_47_NotMatched
Matcher_47_SingleMatched: Inspector
vindparkomraade_konsesjon (writer SHAPE_1) [off]
    attributes: _match_id char(200)
Matcher_47_NotMatched: Inspector
Note: Lager polygon av / envelope
Creator_21 [off]
    NUM = 1
    COORDS = $(MINX) $(MINY) $(MAXX) $(MINY) $(MAXX) $(MAXY)  $(MINX) $(MAXY)  $(MINX) $(MINY)
    GEOMTYPE = 2D Coordinate List
    COORDSYS = EPSG:25833
    CREATED -> Reprojector_21 [off]
Note: Projiserer envelopen til 25833
Reprojector_21 [off]
    DEST = EPSG:25833
    STROKE_ARCS = Yes
    SOURCE = Read from feature
    INTERPOLATION_TYPE_NAME = Nearest Neighbor
    RASTER_CELL_SIZE = Preserve Cells
    REPROJECTED -> Tiler_20 [off]
Note: Tiler opp envelopen i mindre / områder
Tiler_20 [off]
    TILING_TYPE = Tile Size
    XINC = 100000
    ROW_ATTR = _row
    YINC = 100000
    COL_ATTR = _column
    TILED -> BoundsExtractor_20 [off]
BoundsExtractor_20 [off]
    YMIN = _ymin
    YMAX = _ymax
    ZMIN = _zmin
    ZMAX = _zmax
    XMIN = _xmin
    XMAX = _xmax
    -> AttributeCreator_20 [off]
AttributeCreator_20 [off]
    ATTR_LIST = Query,http://gis3.nve.no/map/rest/services/Vindkraftverk/MapServer/2/query?where=1%3D1&text=&objectIds=&time=&geometry=@Value(_xmin),@Value(_ymin),@Value(_xmax),@Value(_ymax)&geometryType=esriGeometryEnvelope&inSR=&spatialRel=esriSpatialRelIntersects&relationParam=&outFields=&returnGeometry=true&maxAllowableOffset=&geometryPrecision=&outSR=&returnIdsOnly=false&returnCountOnly=false&orderByFields=&groupByFieldsForStatistics=&outStatistics=&returnZ=false&returnM=false&gdbVersion=&returnDistinctValues=false&returnTrueCurves=false&resultOffset=&resultRecordCount=&f=pjson
    -> FeatureReader_20 [off]
FeatureReader_20 [off]
    FORMAT = ESRIJSON
    OUTPUT_FEATURES_DISPLAY = Only Data Features
    ESRIJSON_CLIP_TO_ENVELOPE = NO
    COMBINE_GEOM = Use Result
    ESRIJSON_USE_BASENAME_AS_DEFAULT_FEATURE_TYPE = No
    ESRIJSON_USE_SEARCH_ENVELOPE = NO
    DATASET = @Value(Query)
    ATTR_ACCUM_MODE = Only Use Result
    ESRIJSON_DELETE_DOWNLOAD_FILE = Yes
    ESRIJSON_SIMPLIFY_MULTIS = Yes
    INTERACT = <No Spatial Filter>
    ESRIJSON_MAKE_PATHS = No
    FEATURETYPES_RADIO = FEATURETYPES
    ESRIJSON_MAKE_DONUTS = No
    <OTHER> -> Matcher_20 [off]
Matcher_20 [off]
    LENIENT_MATCH = No
    MATCH = 2D
    CNT_ATTR = _match_id
    MATCH_STRATEGY = Match Selected Attributes
    BLANK_AND_MISSING_DIFFER = No
    SINGLE_MATCHED -> vindkraftverk_konsesjon_soekt (writer SHAPE_1) [off]
    NOT_MATCHED -> vindkraftverk_konsesjon_soekt (writer SHAPE_1) [off]
vindkraftverk_konsesjon_soekt (writer SHAPE_1) [off]
    attributes: _match_id char(200)

Bookmark: Sikringstiltak
Note: Lager polygon av / envelope
Creator_27 [off]
    NUM = 1
    COORDS = $(MINX) $(MINY) $(MAXX) $(MINY) $(MAXX) $(MAXY)  $(MINX) $(MAXY)  $(MINX) $(MINY)
    GEOMTYPE = 2D Coordinate List
    COORDSYS = EPSG:25833
    CREATED -> Reprojector_25 [off]
Note: Projiserer envelopen til 25833
Reprojector_25 [off]
    DEST = EPSG:25833
    STROKE_ARCS = Yes
    SOURCE = Read from feature
    INTERPOLATION_TYPE_NAME = Nearest Neighbor
    RASTER_CELL_SIZE = Preserve Cells
    REPROJECTED -> Tiler_24 [off]
Note: Tiler opp envelopen i mindre / områder
Tiler_24 [off]
    TILING_TYPE = Tile Size
    XINC = 100000
    ROW_ATTR = _row
    YINC = 100000
    COL_ATTR = _column
    TILED -> BoundsExtractor_24 [off]
BoundsExtractor_24 [off]
    YMIN = _ymin
    YMAX = _ymax
    ZMIN = _zmin
    ZMAX = _zmax
    XMIN = _xmin
    XMAX = _xmax
    -> AttributeCreator_26 [off]
AttributeCreator_26 [off]
    ATTR_LIST = Query,http://gis3.nve.no/map/rest/services/Sikringstiltak/MapServer/0/query?where=1%3D1&text=&objectIds=&time=&geometry=@Value(_xmin),@Value(_ymin),@Value(_xmax),@Value(_ymax)&geometryType=esriGeometryEnvelope&inSR=&spatialRel=esriSpatialRelIntersects&relationParam=&outFields=&returnGeometry=true&maxAllowableOffset=&geometryPrecision=&outSR=&returnIdsOnly=false&returnCountOnly=false&orderByFields=&groupByFieldsForStatistics=&outStatistics=&returnZ=false&returnM=false&gdbVersion=&returnDistinctValues=false&returnTrueCurves=false&resultOffset=&resultRecordCount=&f=pjson
    -> FeatureReader_26 [off]
FeatureReader_26 [off]
    FORMAT = ESRIJSON
    OUTPUT_FEATURES_DISPLAY = Only Data Features
    ESRIJSON_CLIP_TO_ENVELOPE = NO
    COMBINE_GEOM = Use Result
    ESRIJSON_USE_BASENAME_AS_DEFAULT_FEATURE_TYPE = No
    ESRIJSON_USE_SEARCH_ENVELOPE = NO
    DATASET = @Value(Query)
    ATTR_ACCUM_MODE = Only Use Result
    ESRIJSON_DELETE_DOWNLOAD_FILE = Yes
    ESRIJSON_SIMPLIFY_MULTIS = Yes
    INTERACT = <No Spatial Filter>
    ESRIJSON_MAKE_PATHS = No
    FEATURETYPES_RADIO = FEATURETYPES
    ESRIJSON_MAKE_DONUTS = No
    <OTHER> -> Matcher_25 [off]
Matcher_25 [off]
    LENIENT_MATCH = No
    MATCH = 2D
    CNT_ATTR = _match_id
    MATCH_STRATEGY = Match Selected Attributes
    BLANK_AND_MISSING_DIFFER = No
    SINGLE_MATCHED -> Sikringstiltak (writer SHAPE_1) [off]
    NOT_MATCHED -> Sikringstiltak (writer SHAPE_1) [off]
Sikringstiltak (writer SHAPE_1) [off]
    attributes: _match_id char(200)

Bookmark: Verneplan vassdrag
Note: Lager polygon av / envelope
Creator_28 [off]
    NUM = 1
    COORDS = $(MINX) $(MINY) $(MAXX) $(MINY) $(MAXX) $(MAXY)  $(MINX) $(MAXY)  $(MINX) $(MINY)
    GEOMTYPE = 2D Coordinate List
    COORDSYS = EPSG:25833
    CREATED -> AttributeCreator_35 [off]
AttributeCreator_35 [off]
    ATTR_LIST = Query,http://gis3.nve.no/map/rest/services/VerneplanforVassdrag1/MapServer/0/query?where=1%3D1&text=&objectIds=&time=&geometry=&geometryType=esriGeometryEnvelope&inSR=&spatialRel=esriSpatialRelIntersects&relationParam=&outFields=&returnGeometry=true&maxAllowableOffset=&geometryPrecision=&outSR=&returnIdsOnly=false&returnCountOnly=false&orderByFields=&groupByFieldsForStatistics=&outStatistics=&returnZ=false&returnM=false&gdbVersion=&returnDistinctValues=false&returnTrueCurves=false&resultOffset=&resultRecordCount=&f=pjson
    -> FeatureReader_27 [off]
FeatureReader_27 [off]
    FORMAT = ESRIJSON
    OUTPUT_FEATURES_DISPLAY = Only Data Features
    ESRIJSON_CLIP_TO_ENVELOPE = NO
    COMBINE_GEOM = Use Result
    ESRIJSON_USE_BASENAME_AS_DEFAULT_FEATURE_TYPE = No
    ESRIJSON_USE_SEARCH_ENVELOPE = NO
    DATASET = @Value(Query)
    ATTR_ACCUM_MODE = Only Use Result
    ESRIJSON_DELETE_DOWNLOAD_FILE = Yes
    ESRIJSON_SIMPLIFY_MULTIS = Yes
    INTERACT = <No Spatial Filter>
    ESRIJSON_MAKE_PATHS = No
    FEATURETYPES_RADIO = FEATURETYPES
    ESRIJSON_MAKE_DONUTS = No
    <OTHER> -> Matcher_26 [off]
Matcher_26 [off]
    LENIENT_MATCH = No
    MATCH = 2D
    CNT_ATTR = _match_id
    MATCH_STRATEGY = Match Selected Attributes
    BLANK_AND_MISSING_DIFFER = No
    SINGLE_MATCHED -> VerneplanForVassdrag (writer SHAPE_1) [off]
    NOT_MATCHED -> VerneplanForVassdrag (writer SHAPE_1) [off]
VerneplanForVassdrag (writer SHAPE_1) [off]
    attributes: _match_id char(200)

Bookmark: SkredKvikkleire
Note: Lager polygon av / envelope
Creator_29 [off]
    NUM = 1
    COORDS = $(MINX) $(MINY) $(MAXX) $(MINY) $(MAXX) $(MAXY)  $(MINX) $(MAXY)  $(MINX) $(MINY)
    GEOMTYPE = 2D Coordinate List
    COORDSYS = EPSG:25833
    CREATED -> Reprojector_26 [off]
Note: Projiserer envelopen til 25833
Reprojector_26 [off]
    DEST = EPSG:25833
    STROKE_ARCS = Yes
    SOURCE = Read from feature
    INTERPOLATION_TYPE_NAME = Nearest Neighbor
    RASTER_CELL_SIZE = Preserve Cells
    REPROJECTED -> Tiler_25 [off]
Note: Tiler opp envelopen i mindre / områder
Tiler_25 [off]
    TILING_TYPE = Tile Size
    XINC = 100000
    ROW_ATTR = _row
    YINC = 100000
    COL_ATTR = _column
    TILED -> BoundsExtractor_25 [off]
BoundsExtractor_25 [off]
    YMIN = _ymin
    YMAX = _ymax
    ZMIN = _zmin
    ZMAX = _zmax
    XMIN = _xmin
    XMAX = _xmax
    -> AttributeCreator_36 [off]
AttributeCreator_36 [off]
    ATTR_LIST = Query,http://gis3.nve.no/map/rest/services/SkredKvikkleire/MapServer/1/query?where=1%3D1&text=&objectIds=&time=&geometry=@Value(_xmin),@Value(_ymin),@Value(_xmax),@Value(_ymax)&geometryType=esriGeometryEnvelope&inSR=&spatialRel=esriSpatialRelIntersects&relationParam=&outFields=&returnGeometry=true&maxAllowableOffset=&geometryPrecision=&outSR=&returnIdsOnly=false&returnCountOnly=false&orderByFields=&groupByFieldsForStatistics=&outStatistics=&returnZ=false&returnM=false&gdbVersion=&returnDistinctValues=false&returnTrueCurves=false&resultOffset=&resultRecordCount=&f=pjson
    -> FeatureReader_28 [off]
FeatureReader_28 [off]
    FORMAT = ESRIJSON
    OUTPUT_FEATURES_DISPLAY = Only Data Features
    ESRIJSON_CLIP_TO_ENVELOPE = NO
    COMBINE_GEOM = Use Result
    ESRIJSON_USE_BASENAME_AS_DEFAULT_FEATURE_TYPE = No
    ESRIJSON_USE_SEARCH_ENVELOPE = NO
    DATASET = @Value(Query)
    ATTR_ACCUM_MODE = Only Use Result
    ESRIJSON_DELETE_DOWNLOAD_FILE = Yes
    ESRIJSON_SIMPLIFY_MULTIS = Yes
    INTERACT = <No Spatial Filter>
    ESRIJSON_MAKE_PATHS = No
    FEATURETYPES_RADIO = FEATURETYPES
    ESRIJSON_MAKE_DONUTS = No
    <OTHER> -> Matcher_27 [off]
Matcher_27 [off]
    LENIENT_MATCH = No
    MATCH = 2D
    CNT_ATTR = _match_id
    MATCH_STRATEGY = Match Selected Attributes
    BLANK_AND_MISSING_DIFFER = No
    SINGLE_MATCHED -> SkredKvikkleire (writer SHAPE_1) [off]
    NOT_MATCHED -> SkredKvikkleire (writer SHAPE_1) [off]
SkredKvikkleire (writer SHAPE_1) [off]
    attributes: _match_id char(200)

Bookmark: Regionalnett
Note: Lager polygon av / envelope
Creator_22 [off]
    NUM = 1
    COORDS = $(MINX) $(MINY) $(MAXX) $(MINY) $(MAXX) $(MAXY)  $(MINX) $(MAXY)  $(MINX) $(MINY)
    GEOMTYPE = 2D Coordinate List
    COORDSYS = EPSG:25833
    CREATED -> Reprojector_22 [off]
Note: Projiserer envelopen til 25833
Reprojector_22 [off]
    DEST = EPSG:25833
    STROKE_ARCS = Yes
    SOURCE = Read from feature
    INTERPOLATION_TYPE_NAME = Nearest Neighbor
    RASTER_CELL_SIZE = Preserve Cells
    REPROJECTED -> Tiler_21 [off]
Note: Tiler opp envelopen i mindre / områder
Tiler_21 [off]
    TILING_TYPE = Tile Size
    XINC = 100000
    ROW_ATTR = _row
    YINC = 100000
    COL_ATTR = _column
    TILED -> BoundsExtractor_21 [off]
BoundsExtractor_21 [off]
    YMIN = _ymin
    YMAX = _ymax
    ZMIN = _zmin
    ZMAX = _zmax
    XMIN = _xmin
    XMAX = _xmax
    -> AttributeCreator_21 [off]
AttributeCreator_21 [off]
    ATTR_LIST = Query,http://gis3.nve.no/map/rest/services/Nettanlegg/MapServer/1/query?where=1%3D1&text=&objectIds=&time=&geometry=@Value(_xmin),@Value(_ymin),@Value(_xmax),@Value(_ymax)&geometryType=esriGeometryEnvelope&inSR=&spatialRel=esriSpatialRelIntersects&relationParam=&outFields=&returnGeometry=true&maxAllowableOffset=&geometryPrecision=&outSR=&returnIdsOnly=false&returnCountOnly=false&orderByFields=&groupByFieldsForStatistics=&outStatistics=&returnZ=false&returnM=false&gdbVersion=&returnDistinctValues=false&returnTrueCurves=false&resultOffset=&resultRecordCount=&f=pjson
    -> FeatureReader_21 [off]
FeatureReader_21 [off]
    FORMAT = ESRIJSON
    OUTPUT_FEATURES_DISPLAY = Only Data Features
    ESRIJSON_CLIP_TO_ENVELOPE = NO
    COMBINE_GEOM = Use Result
    ESRIJSON_USE_BASENAME_AS_DEFAULT_FEATURE_TYPE = No
    ESRIJSON_USE_SEARCH_ENVELOPE = NO
    DATASET = @Value(Query)
    ATTR_ACCUM_MODE = Only Use Result
    ESRIJSON_DELETE_DOWNLOAD_FILE = Yes
    ESRIJSON_SIMPLIFY_MULTIS = Yes
    INTERACT = <No Spatial Filter>
    ESRIJSON_MAKE_PATHS = No
    FEATURETYPES_RADIO = FEATURETYPES
    ESRIJSON_MAKE_DONUTS = No
    <OTHER> -> Matcher_21 [off]
Matcher_21 [off]
    LENIENT_MATCH = No
    MATCH = 2D
    CNT_ATTR = _match_id
    MATCH_STRATEGY = Match Selected Attributes
    BLANK_AND_MISSING_DIFFER = No
    SINGLE_MATCHED -> Kraftlinjer (writer SHAPE_1) [off]
    NOT_MATCHED -> Kraftlinjer (writer SHAPE_1) [off]

Bookmark: Sjøkabler
Note: Lager polygon av / envelope
Creator_24 [off]
    NUM = 1
    COORDS = $(MINX) $(MINY) $(MAXX) $(MINY) $(MAXX) $(MAXY)  $(MINX) $(MAXY)  $(MINX) $(MINY)
    GEOMTYPE = 2D Coordinate List
    COORDSYS = EPSG:25833
    CREATED -> Reprojector_23 [off]
Note: Projiserer envelopen til 25833
Reprojector_23 [off]
    DEST = EPSG:25833
    STROKE_ARCS = Yes
    SOURCE = Read from feature
    INTERPOLATION_TYPE_NAME = Nearest Neighbor
    RASTER_CELL_SIZE = Preserve Cells
    REPROJECTED -> Tiler_22 [off]
Note: Tiler opp envelopen i mindre / områder
Tiler_22 [off]
    TILING_TYPE = Tile Size
    XINC = 100000
    ROW_ATTR = _row
    YINC = 100000
    COL_ATTR = _column
    TILED -> BoundsExtractor_22 [off]
BoundsExtractor_22 [off]
    YMIN = _ymin
    YMAX = _ymax
    ZMIN = _zmin
    ZMAX = _zmax
    XMIN = _xmin
    XMAX = _xmax
    -> AttributeCreator_23 [off]
AttributeCreator_23 [off]
    ATTR_LIST = Query,http://gis3.nve.no/map/rest/services/Nettanlegg/MapServer/2/query?where=1%3D1&text=&objectIds=&time=&geometry=@Value(_xmin),@Value(_ymin),@Value(_xmax),@Value(_ymax)&geometryType=esriGeometryEnvelope&inSR=&spatialRel=esriSpatialRelIntersects&relationParam=&outFields=&returnGeometry=true&maxAllowableOffset=&geometryPrecision=&outSR=&returnIdsOnly=false&returnCountOnly=false&orderByFields=&groupByFieldsForStatistics=&outStatistics=&returnZ=false&returnM=false&gdbVersion=&returnDistinctValues=false&returnTrueCurves=false&resultOffset=&resultRecordCount=&f=pjson
    -> FeatureReader_23 [off]
FeatureReader_23 [off]
    FORMAT = ESRIJSON
    OUTPUT_FEATURES_DISPLAY = Only Data Features
    ESRIJSON_CLIP_TO_ENVELOPE = NO
    COMBINE_GEOM = Use Result
    ESRIJSON_USE_BASENAME_AS_DEFAULT_FEATURE_TYPE = No
    ESRIJSON_USE_SEARCH_ENVELOPE = NO
    DATASET = @Value(Query)
    ATTR_ACCUM_MODE = Only Use Result
    ESRIJSON_DELETE_DOWNLOAD_FILE = Yes
    ESRIJSON_SIMPLIFY_MULTIS = Yes
    INTERACT = <No Spatial Filter>
    ESRIJSON_MAKE_PATHS = No
    FEATURETYPES_RADIO = FEATURETYPES
    ESRIJSON_MAKE_DONUTS = No
    <OTHER> -> Matcher_22 [off]
Matcher_22 [off]
    LENIENT_MATCH = No
    MATCH = 2D
    CNT_ATTR = _match_id
    MATCH_STRATEGY = Match Selected Attributes
    BLANK_AND_MISSING_DIFFER = No
    SINGLE_MATCHED -> Sjoekabler (writer SHAPE_1) [off]
    NOT_MATCHED -> Sjoekabler (writer SHAPE_1) [off]
Sjoekabler (writer SHAPE_1) [off]
    attributes: _match_id char(200)

Bookmark: Transformatorstasjoner
Note: Lager polygon av / envelope
Creator_25 [off]
    NUM = 1
    COORDS = $(MINX) $(MINY) $(MAXX) $(MINY) $(MAXX) $(MAXY)  $(MINX) $(MAXY)  $(MINX) $(MINY)
    GEOMTYPE = 2D Coordinate List
    COORDSYS = EPSG:25833
    CREATED -> Reprojector_24 [off]
Note: Projiserer envelopen til 25833
Reprojector_24 [off]
    DEST = EPSG:25833
    STROKE_ARCS = Yes
    SOURCE = Read from feature
    INTERPOLATION_TYPE_NAME = Nearest Neighbor
    RASTER_CELL_SIZE = Preserve Cells
    REPROJECTED -> Tiler_23 [off]
Note: Tiler opp envelopen i mindre / områder
Tiler_23 [off]
    TILING_TYPE = Tile Size
    XINC = 100000
    ROW_ATTR = _row
    YINC = 100000
    COL_ATTR = _column
    TILED -> BoundsExtractor_23 [off]
BoundsExtractor_23 [off]
    YMIN = _ymin
    YMAX = _ymax
    ZMIN = _zmin
    ZMAX = _zmax
    XMIN = _xmin
    XMAX = _xmax
    -> AttributeCreator_24 [off]
AttributeCreator_24 [off]
    ATTR_LIST = Query,http://gis3.nve.no/map/rest/services/Nettanlegg/MapServer/4/query?where=1%3D1&text=&objectIds=&time=&geometry=@Value(_xmin),@Value(_ymin),@Value(_xmax),@Value(_ymax)&geometryType=esriGeometryEnvelope&inSR=&spatialRel=esriSpatialRelIntersects&relationParam=&outFields=&returnGeometry=true&maxAllowableOffset=&geometryPrecision=&outSR=&returnIdsOnly=false&returnCountOnly=false&orderByFields=&groupByFieldsForStatistics=&outStatistics=&returnZ=false&returnM=false&gdbVersion=&returnDistinctValues=false&returnTrueCurves=false&resultOffset=&resultRecordCount=&f=pjson
    -> FeatureReader_24 [off]
FeatureReader_24 [off]
    FORMAT = ESRIJSON
    OUTPUT_FEATURES_DISPLAY = Only Data Features
    ESRIJSON_CLIP_TO_ENVELOPE = NO
    COMBINE_GEOM = Use Result
    ESRIJSON_USE_BASENAME_AS_DEFAULT_FEATURE_TYPE = No
    ESRIJSON_USE_SEARCH_ENVELOPE = NO
    DATASET = @Value(Query)
    ATTR_ACCUM_MODE = Only Use Result
    ESRIJSON_DELETE_DOWNLOAD_FILE = Yes
    ESRIJSON_SIMPLIFY_MULTIS = Yes
    INTERACT = <No Spatial Filter>
    ESRIJSON_MAKE_PATHS = No
    FEATURETYPES_RADIO = FEATURETYPES
    ESRIJSON_MAKE_DONUTS = No
    <OTHER> -> Matcher_23 [off]
Matcher_23 [off]
    LENIENT_MATCH = No
    MATCH = 2D
    CNT_ATTR = _match_id
    MATCH_STRATEGY = Match Selected Attributes
    BLANK_AND_MISSING_DIFFER = No
    SINGLE_MATCHED -> Transformatorstasjoner (writer SHAPE_1) [off]
    NOT_MATCHED -> Transformatorstasjoner (writer SHAPE_1) [off]
Transformatorstasjoner (writer SHAPE_1) [off]
    attributes: _match_id char(200)

Bookmark: områdekonsesjoner
Note: Lager polygon av / envelope
Creator_26 [off]
    NUM = 1
    COORDS = $(MINX) $(MINY) $(MAXX) $(MINY) $(MAXX) $(MAXY)  $(MINX) $(MAXY)  $(MINX) $(MINY)
    GEOMTYPE = 2D Coordinate List
    COORDSYS = EPSG:25833
    CREATED -> AttributeCreator_25 [off]
AttributeCreator_25 [off]
    ATTR_LIST = Query,http://gis3.nve.no/map/rest/services/Nettanlegg/MapServer/5/query?where=1%3D1&text=&objectIds=&time=&geometry=&geometryType=esriGeometryEnvelope&inSR=&spatialRel=esriSpatialRelIntersects&relationParam=&outFields=&returnGeometry=true&maxAllowableOffset=&geometryPrecision=&outSR=&returnIdsOnly=false&returnCountOnly=false&orderByFields=&groupByFieldsForStatistics=&outStatistics=&returnZ=false&returnM=false&gdbVersion=&returnDistinctValues=false&returnTrueCurves=false&resultOffset=&resultRecordCount=&f=pjson
    -> FeatureReader_25 [off]
FeatureReader_25 [off]
    FORMAT = ESRIJSON
    OUTPUT_FEATURES_DISPLAY = Only Data Features
    ESRIJSON_CLIP_TO_ENVELOPE = NO
    COMBINE_GEOM = Use Result
    ESRIJSON_USE_BASENAME_AS_DEFAULT_FEATURE_TYPE = No
    ESRIJSON_USE_SEARCH_ENVELOPE = NO
    DATASET = @Value(Query)
    ATTR_ACCUM_MODE = Only Use Result
    ESRIJSON_DELETE_DOWNLOAD_FILE = Yes
    ESRIJSON_SIMPLIFY_MULTIS = Yes
    INTERACT = <No Spatial Filter>
    ESRIJSON_MAKE_PATHS = No
    FEATURETYPES_RADIO = FEATURETYPES
    ESRIJSON_MAKE_DONUTS = No
    <OTHER> -> Matcher_24 [off]
Matcher_24 [off]
    LENIENT_MATCH = No
    MATCH = 2D
    CNT_ATTR = _match_id
    MATCH_STRATEGY = Match Selected Attributes
    BLANK_AND_MISSING_DIFFER = No
    SINGLE_MATCHED -> Omraadekonsesjoner (writer SHAPE_1) [off]
    NOT_MATCHED -> Omraadekonsesjoner (writer SHAPE_1) [off]
Omraadekonsesjoner (writer SHAPE_1) [off]
    attributes: _match_id char(200)

Bookmark: Sentralnett
Creator_23 [off]
    NUM = 1
    COORDS = $(MINX) $(MINY) $(MAXX) $(MINY) $(MAXX) $(MAXY)  $(MINX) $(MAXY)  $(MINX) $(MINY)
    GEOMTYPE = 2D Coordinate List
    COORDSYS = EPSG:25833
    CREATED -> AttributeCreator_22 [off]
AttributeCreator_22 [off]
    ATTR_LIST = Query,http://gis3.nve.no/map/rest/services/Nettanlegg/MapServer/0/query?where=1%3D1&text=&objectIds=&time=&geometry=&geometryType=esriGeometryEnvelope&inSR=&spatialRel=esriSpatialRelIntersects&relationParam=&outFields=&returnGeometry=true&maxAllowableOffset=&geometryPrecision=&outSR=&returnIdsOnly=false&returnCountOnly=false&orderByFields=&groupByFieldsForStatistics=&outStatistics=&returnZ=false&returnM=false&gdbVersion=&returnDistinctValues=false&returnTrueCurves=false&resultOffset=&resultRecordCount=&f=pjson
    -> FeatureReader_22 [off]
FeatureReader_22 [off]
    FORMAT = ESRIJSON
    OUTPUT_FEATURES_DISPLAY = Only Data Features
    ESRIJSON_CLIP_TO_ENVELOPE = NO
    COMBINE_GEOM = Use Result
    ESRIJSON_USE_BASENAME_AS_DEFAULT_FEATURE_TYPE = No
    ESRIJSON_USE_SEARCH_ENVELOPE = NO
    DATASET = @Value(Query)
    ATTR_ACCUM_MODE = Only Use Result
    ESRIJSON_DELETE_DOWNLOAD_FILE = Yes
    ESRIJSON_SIMPLIFY_MULTIS = Yes
    INTERACT = <No Spatial Filter>
    ESRIJSON_MAKE_PATHS = No
    FEATURETYPES_RADIO = FEATURETYPES
    ESRIJSON_MAKE_DONUTS = No
    <OTHER> -> Kraftlinjer (writer SHAPE_1) [off]

Bookmark: Kraftlinjer
Kraftlinjer (writer SHAPE_1) [off]
    attributes: _match_id char(200)

Bookmark: Flomsonekartplan
Note: Lager polygon av / envelope
Creator_30 [off]
    NUM = 1
    COORDS = $(MINX) $(MINY) $(MAXX) $(MINY) $(MAXX) $(MAXY)  $(MINX) $(MAXY)  $(MINX) $(MINY)
    GEOMTYPE = 2D Coordinate List
    COORDSYS = EPSG:25833
    CREATED -> Reprojector_27 [off]
Note: Projiserer envelopen til 25833
Reprojector_27 [off]
    DEST = EPSG:25833
    STROKE_ARCS = Yes
    SOURCE = Read from feature
    INTERPOLATION_TYPE_NAME = Nearest Neighbor
    RASTER_CELL_SIZE = Preserve Cells
    REPROJECTED -> Tiler_26 [off]
Note: Tiler opp envelopen i mindre / områder
Tiler_26 [off]
    TILING_TYPE = Tile Size
    XINC = 100000
    ROW_ATTR = _row
    YINC = 100000
    COL_ATTR = _column
    TILED -> BoundsExtractor_26 [off]
BoundsExtractor_26 [off]
    YMIN = _ymin
    YMAX = _ymax
    ZMIN = _zmin
    ZMAX = _zmax
    XMIN = _xmin
    XMAX = _xmax
    -> AttributeCreator_37 [off]
AttributeCreator_37 [off]
    ATTR_LIST = Query,http://gis3.nve.no/map/rest/services/Flomsoner/MapServer/0/query?where=1%3D1&text=&objectIds=&time=&geometry=@Value(_xmin),@Value(_ymin),@Value(_xmax),@Value(_ymax)&geometryType=esriGeometryEnvelope&inSR=&spatialRel=esriSpatialRelIntersects&relationParam=&outFields=&returnGeometry=true&maxAllowableOffset=&geometryPrecision=&outSR=&returnIdsOnly=false&returnCountOnly=false&orderByFields=&groupByFieldsForStatistics=&outStatistics=&returnZ=false&returnM=false&gdbVersion=&returnDistinctValues=false&returnTrueCurves=false&resultOffset=&resultRecordCount=&f=pjson
    -> FeatureReader_29 [off]
FeatureReader_29 [off]
    FORMAT = ESRIJSON
    OUTPUT_FEATURES_DISPLAY = Only Data Features
    ESRIJSON_CLIP_TO_ENVELOPE = NO
    COMBINE_GEOM = Use Result
    ESRIJSON_USE_BASENAME_AS_DEFAULT_FEATURE_TYPE = No
    ESRIJSON_USE_SEARCH_ENVELOPE = NO
    DATASET = @Value(Query)
    ATTR_ACCUM_MODE = Only Use Result
    ESRIJSON_DELETE_DOWNLOAD_FILE = Yes
    ESRIJSON_SIMPLIFY_MULTIS = Yes
    INTERACT = <No Spatial Filter>
    ESRIJSON_MAKE_PATHS = No
    FEATURETYPES_RADIO = FEATURETYPES
    ESRIJSON_MAKE_DONUTS = No
    <OTHER> -> Matcher_28 [off]
Matcher_28 [off]
    LENIENT_MATCH = No
    MATCH = 2D
    CNT_ATTR = _match_id
    MATCH_STRATEGY = Match Selected Attributes
    BLANK_AND_MISSING_DIFFER = No
    SINGLE_MATCHED -> Flomsonekartplan (writer SHAPE_1) [off]
    NOT_MATCHED -> Flomsonekartplan (writer SHAPE_1) [off]
Flomsonekartplan (writer SHAPE_1) [off]
    attributes: _match_id char(200)

Bookmark: Flomsoner10
Note: Lager polygon av / envelope
Creator_31 [off]
    NUM = 1
    COORDS = $(MINX) $(MINY) $(MAXX) $(MINY) $(MAXX) $(MAXY)  $(MINX) $(MAXY)  $(MINX) $(MINY)
    GEOMTYPE = 2D Coordinate List
    COORDSYS = EPSG:25833
    CREATED -> Reprojector_28 [off]
Note: Projiserer envelopen til 25833
Reprojector_28 [off]
    DEST = EPSG:25833
    STROKE_ARCS = Yes
    SOURCE = Read from feature
    INTERPOLATION_TYPE_NAME = Nearest Neighbor
    RASTER_CELL_SIZE = Preserve Cells
    REPROJECTED -> Tiler_27 [off]
Note: Tiler opp envelopen i mindre / områder
Tiler_27 [off]
    TILING_TYPE = Tile Size
    XINC = 100000
    ROW_ATTR = _row
    YINC = 100000
    COL_ATTR = _column
    TILED -> BoundsExtractor_27 [off]
BoundsExtractor_27 [off]
    YMIN = _ymin
    YMAX = _ymax
    ZMIN = _zmin
    ZMAX = _zmax
    XMIN = _xmin
    XMAX = _xmax
    -> AttributeCreator_38 [off]
AttributeCreator_38 [off]
    ATTR_LIST = Query,http://gis3.nve.no/map/rest/services/Flomsoner/MapServer/2/query?where=1%3D1&text=&objectIds=&time=&geometry=@Value(_xmin),@Value(_ymin),@Value(_xmax),@Value(_ymax)&geometryType=esriGeometryEnvelope&inSR=&spatialRel=esriSpatialRelIntersects&relationParam=&outFields=&returnGeometry=true&maxAllowableOffset=&geometryPrecision=&outSR=&returnIdsOnly=false&returnCountOnly=false&orderByFields=&groupByFieldsForStatistics=&outStatistics=&returnZ=false&returnM=false&gdbVersion=&returnDistinctValues=false&returnTrueCurves=false&resultOffset=&resultRecordCount=&f=pjson
    -> FeatureReader_30 [off]
FeatureReader_30 [off]
    FORMAT = ESRIJSON
    OUTPUT_FEATURES_DISPLAY = Only Data Features
    ESRIJSON_CLIP_TO_ENVELOPE = NO
    COMBINE_GEOM = Use Result
    ESRIJSON_USE_BASENAME_AS_DEFAULT_FEATURE_TYPE = No
    ESRIJSON_USE_SEARCH_ENVELOPE = NO
    DATASET = @Value(Query)
    ATTR_ACCUM_MODE = Only Use Result
    ESRIJSON_DELETE_DOWNLOAD_FILE = Yes
    ESRIJSON_SIMPLIFY_MULTIS = Yes
    INTERACT = <No Spatial Filter>
    ESRIJSON_MAKE_PATHS = No
    FEATURETYPES_RADIO = FEATURETYPES
    ESRIJSON_MAKE_DONUTS = No
    <OTHER> -> Matcher_29 [off]
Matcher_29 [off]
    LENIENT_MATCH = No
    MATCH = 2D
    CNT_ATTR = _match_id
    MATCH_STRATEGY = Match Selected Attributes
    BLANK_AND_MISSING_DIFFER = No
    SINGLE_MATCHED -> Flomsoner10 (writer SHAPE_1) [off]
    NOT_MATCHED -> Flomsoner10 (writer SHAPE_1) [off]
Flomsoner10 (writer SHAPE_1) [off]
    attributes: _match_id char(200)

Bookmark: Flomsoner20
Note: Lager polygon av / envelope
Creator_32 [off]
    NUM = 1
    COORDS = $(MINX) $(MINY) $(MAXX) $(MINY) $(MAXX) $(MAXY)  $(MINX) $(MAXY)  $(MINX) $(MINY)
    GEOMTYPE = 2D Coordinate List
    COORDSYS = EPSG:25833
    CREATED -> Reprojector_29 [off]
Note: Projiserer envelopen til 25833
Reprojector_29 [off]
    DEST = EPSG:25833
    STROKE_ARCS = Yes
    SOURCE = Read from feature
    INTERPOLATION_TYPE_NAME = Nearest Neighbor
    RASTER_CELL_SIZE = Preserve Cells
    REPROJECTED -> Tiler_28 [off]
Note: Tiler opp envelopen i mindre / områder
Tiler_28 [off]
    TILING_TYPE = Tile Size
    XINC = 100000
    ROW_ATTR = _row
    YINC = 100000
    COL_ATTR = _column
    TILED -> BoundsExtractor_28 [off]
BoundsExtractor_28 [off]
    YMIN = _ymin
    YMAX = _ymax
    ZMIN = _zmin
    ZMAX = _zmax
    XMIN = _xmin
    XMAX = _xmax
    -> AttributeCreator_39 [off]
AttributeCreator_39 [off]
    ATTR_LIST = Query,http://gis3.nve.no/map/rest/services/Flomsoner/MapServer/3/query?where=1%3D1&text=&objectIds=&time=&geometry=@Value(_xmin),@Value(_ymin),@Value(_xmax),@Value(_ymax)&geometryType=esriGeometryEnvelope&inSR=&spatialRel=esriSpatialRelIntersects&relationParam=&outFields=&returnGeometry=true&maxAllowableOffset=&geometryPrecision=&outSR=&returnIdsOnly=false&returnCountOnly=false&orderByFields=&groupByFieldsForStatistics=&outStatistics=&returnZ=false&returnM=false&gdbVersion=&returnDistinctValues=false&returnTrueCurves=false&resultOffset=&resultRecordCount=&f=pjson
    -> FeatureReader_31 [off]
FeatureReader_31 [off]
    FORMAT = ESRIJSON
    OUTPUT_FEATURES_DISPLAY = Only Data Features
    ESRIJSON_CLIP_TO_ENVELOPE = NO
    COMBINE_GEOM = Use Result
    ESRIJSON_USE_BASENAME_AS_DEFAULT_FEATURE_TYPE = No
    ESRIJSON_USE_SEARCH_ENVELOPE = NO
    DATASET = @Value(Query)
    ATTR_ACCUM_MODE = Only Use Result
    ESRIJSON_DELETE_DOWNLOAD_FILE = Yes
    ESRIJSON_SIMPLIFY_MULTIS = Yes
    INTERACT = <No Spatial Filter>
    ESRIJSON_MAKE_PATHS = No
    FEATURETYPES_RADIO = FEATURETYPES
    ESRIJSON_MAKE_DONUTS = No
    <OTHER> -> Matcher_30 [off]
Matcher_30 [off]
    LENIENT_MATCH = No
    MATCH = 2D
    CNT_ATTR = _match_id
    MATCH_STRATEGY = Match Selected Attributes
    BLANK_AND_MISSING_DIFFER = No
    SINGLE_MATCHED -> Flomsoner20 (writer SHAPE_1) [off]
    NOT_MATCHED -> Flomsoner20 (writer SHAPE_1) [off]
Flomsoner20 (writer SHAPE_1) [off]
    attributes: _match_id char(200)

Bookmark: Flomsoner50
Note: Lager polygon av / envelope
Creator_33 [off]
    NUM = 1
    COORDS = $(MINX) $(MINY) $(MAXX) $(MINY) $(MAXX) $(MAXY)  $(MINX) $(MAXY)  $(MINX) $(MINY)
    GEOMTYPE = 2D Coordinate List
    COORDSYS = EPSG:25833
    CREATED -> Reprojector_30 [off]
Note: Projiserer envelopen til 25833
Reprojector_30 [off]
    DEST = EPSG:25833
    STROKE_ARCS = Yes
    SOURCE = Read from feature
    INTERPOLATION_TYPE_NAME = Nearest Neighbor
    RASTER_CELL_SIZE = Preserve Cells
    REPROJECTED -> Tiler_29 [off]
Note: Tiler opp envelopen i mindre / områder
Tiler_29 [off]
    TILING_TYPE = Tile Size
    XINC = 100000
    ROW_ATTR = _row
    YINC = 100000
    COL_ATTR = _column
    TILED -> BoundsExtractor_29 [off]
BoundsExtractor_29 [off]
    YMIN = _ymin
    YMAX = _ymax
    ZMIN = _zmin
    ZMAX = _zmax
    XMIN = _xmin
    XMAX = _xmax
    -> AttributeCreator_40 [off]
AttributeCreator_40 [off]
    ATTR_LIST = Query,http://gis3.nve.no/map/rest/services/Flomsoner/MapServer/4/query?where=1%3D1&text=&objectIds=&time=&geometry=@Value(_xmin),@Value(_ymin),@Value(_xmax),@Value(_ymax)&geometryType=esriGeometryEnvelope&inSR=&spatialRel=esriSpatialRelIntersects&relationParam=&outFields=&returnGeometry=true&maxAllowableOffset=&geometryPrecision=&outSR=&returnIdsOnly=false&returnCountOnly=false&orderByFields=&groupByFieldsForStatistics=&outStatistics=&returnZ=false&returnM=false&gdbVersion=&returnDistinctValues=false&returnTrueCurves=false&resultOffset=&resultRecordCount=&f=pjson
    -> FeatureReader_32 [off]
FeatureReader_32 [off]
    FORMAT = ESRIJSON
    OUTPUT_FEATURES_DISPLAY = Only Data Features
    ESRIJSON_CLIP_TO_ENVELOPE = NO
    COMBINE_GEOM = Use Result
    ESRIJSON_USE_BASENAME_AS_DEFAULT_FEATURE_TYPE = No
    ESRIJSON_USE_SEARCH_ENVELOPE = NO
    DATASET = @Value(Query)
    ATTR_ACCUM_MODE = Only Use Result
    ESRIJSON_DELETE_DOWNLOAD_FILE = Yes
    ESRIJSON_SIMPLIFY_MULTIS = Yes
    INTERACT = <No Spatial Filter>
    ESRIJSON_MAKE_PATHS = No
    FEATURETYPES_RADIO = FEATURETYPES
    ESRIJSON_MAKE_DONUTS = No
    <OTHER> -> Matcher_31 [off]
Matcher_31 [off]
    LENIENT_MATCH = No
    MATCH = 2D
    CNT_ATTR = _match_id
    MATCH_STRATEGY = Match Selected Attributes
    BLANK_AND_MISSING_DIFFER = No
    SINGLE_MATCHED -> Flomsoner50 (writer SHAPE_1) [off]
    NOT_MATCHED -> Flomsoner50 (writer SHAPE_1) [off]
Flomsoner50 (writer SHAPE_1) [off]
    attributes: _match_id char(200)

Bookmark: Flomsoner100
Note: Lager polygon av / envelope
Creator_34 [off]
    NUM = 1
    COORDS = $(MINX) $(MINY) $(MAXX) $(MINY) $(MAXX) $(MAXY)  $(MINX) $(MAXY)  $(MINX) $(MINY)
    GEOMTYPE = 2D Coordinate List
    COORDSYS = EPSG:25833
    CREATED -> Reprojector_31 [off]
Note: Projiserer envelopen til 25833
Reprojector_31 [off]
    DEST = EPSG:25833
    STROKE_ARCS = Yes
    SOURCE = Read from feature
    INTERPOLATION_TYPE_NAME = Nearest Neighbor
    RASTER_CELL_SIZE = Preserve Cells
    REPROJECTED -> Tiler_30 [off]
Note: Tiler opp envelopen i mindre / områder
Tiler_30 [off]
    TILING_TYPE = Tile Size
    XINC = 100000
    ROW_ATTR = _row
    YINC = 100000
    COL_ATTR = _column
    TILED -> BoundsExtractor_30 [off]
BoundsExtractor_30 [off]
    YMIN = _ymin
    YMAX = _ymax
    ZMIN = _zmin
    ZMAX = _zmax
    XMIN = _xmin
    XMAX = _xmax
    -> AttributeCreator_41 [off]
AttributeCreator_41 [off]
    ATTR_LIST = Query,http://gis3.nve.no/map/rest/services/Flomsoner/MapServer/5/query?where=1%3D1&text=&objectIds=&time=&geometry=@Value(_xmin),@Value(_ymin),@Value(_xmax),@Value(_ymax)&geometryType=esriGeometryEnvelope&inSR=&spatialRel=esriSpatialRelIntersects&relationParam=&outFields=&returnGeometry=true&maxAllowableOffset=&geometryPrecision=&outSR=&returnIdsOnly=false&returnCountOnly=false&orderByFields=&groupByFieldsForStatistics=&outStatistics=&returnZ=false&returnM=false&gdbVersion=&returnDistinctValues=false&returnTrueCurves=false&resultOffset=&resultRecordCount=&f=pjson
    -> FeatureReader_33 [off]
FeatureReader_33 [off]
    FORMAT = ESRIJSON
    OUTPUT_FEATURES_DISPLAY = Only Data Features
    ESRIJSON_CLIP_TO_ENVELOPE = NO
    COMBINE_GEOM = Use Result
    ESRIJSON_USE_BASENAME_AS_DEFAULT_FEATURE_TYPE = No
    ESRIJSON_USE_SEARCH_ENVELOPE = NO
    DATASET = @Value(Query)
    ATTR_ACCUM_MODE = Only Use Result
    ESRIJSON_DELETE_DOWNLOAD_FILE = Yes
    ESRIJSON_SIMPLIFY_MULTIS = Yes
    INTERACT = <No Spatial Filter>
    ESRIJSON_MAKE_PATHS = No
    FEATURETYPES_RADIO = FEATURETYPES
    ESRIJSON_MAKE_DONUTS = No
    <OTHER> -> Matcher_32 [off]
Matcher_32 [off]
    LENIENT_MATCH = No
    MATCH = 2D
    CNT_ATTR = _match_id
    MATCH_STRATEGY = Match Selected Attributes
    BLANK_AND_MISSING_DIFFER = No
    SINGLE_MATCHED -> Flomsoner100 (writer SHAPE_1) [off]
    NOT_MATCHED -> Flomsoner100 (writer SHAPE_1) [off]
Flomsoner100 (writer SHAPE_1) [off]
    attributes: _match_id char(200)

Bookmark: Flomsoner200
Note: Lager polygon av / envelope
Creator_35 [off]
    NUM = 1
    COORDS = $(MINX) $(MINY) $(MAXX) $(MINY) $(MAXX) $(MAXY)  $(MINX) $(MAXY)  $(MINX) $(MINY)
    GEOMTYPE = 2D Coordinate List
    COORDSYS = EPSG:25833
    CREATED -> Reprojector_32 [off]
Note: Projiserer envelopen til 25833
Reprojector_32 [off]
    DEST = EPSG:25833
    STROKE_ARCS = Yes
    SOURCE = Read from feature
    INTERPOLATION_TYPE_NAME = Nearest Neighbor
    RASTER_CELL_SIZE = Preserve Cells
    REPROJECTED -> Tiler_31 [off]
Note: Tiler opp envelopen i mindre / områder
Tiler_31 [off]
    TILING_TYPE = Tile Size
    XINC = 100000
    ROW_ATTR = _row
    YINC = 100000
    COL_ATTR = _column
    TILED -> BoundsExtractor_31 [off]
BoundsExtractor_31 [off]
    YMIN = _ymin
    YMAX = _ymax
    ZMIN = _zmin
    ZMAX = _zmax
    XMIN = _xmin
    XMAX = _xmax
    -> AttributeCreator_42 [off]
AttributeCreator_42 [off]
    ATTR_LIST = Query,http://gis3.nve.no/map/rest/services/Flomsoner/MapServer/6/query?where=1%3D1&text=&objectIds=&time=&geometry=@Value(_xmin),@Value(_ymin),@Value(_xmax),@Value(_ymax)&geometryType=esriGeometryEnvelope&inSR=&spatialRel=esriSpatialRelIntersects&relationParam=&outFields=&returnGeometry=true&maxAllowableOffset=&geometryPrecision=&outSR=&returnIdsOnly=false&returnCountOnly=false&orderByFields=&groupByFieldsForStatistics=&outStatistics=&returnZ=false&returnM=false&gdbVersion=&returnDistinctValues=false&returnTrueCurves=false&resultOffset=&resultRecordCount=&f=pjson
    -> FeatureReader_34 [off]
FeatureReader_34 [off]
    FORMAT = ESRIJSON
    OUTPUT_FEATURES_DISPLAY = Only Data Features
    ESRIJSON_CLIP_TO_ENVELOPE = NO
    COMBINE_GEOM = Use Result
    ESRIJSON_USE_BASENAME_AS_DEFAULT_FEATURE_TYPE = No
    ESRIJSON_USE_SEARCH_ENVELOPE = NO
    DATASET = @Value(Query)
    ATTR_ACCUM_MODE = Only Use Result
    ESRIJSON_DELETE_DOWNLOAD_FILE = Yes
    ESRIJSON_SIMPLIFY_MULTIS = Yes
    INTERACT = <No Spatial Filter>
    ESRIJSON_MAKE_PATHS = No
    FEATURETYPES_RADIO = FEATURETYPES
    ESRIJSON_MAKE_DONUTS = No
    <OTHER> -> Matcher_33 [off]
Matcher_33 [off]
    LENIENT_MATCH = No
    MATCH = 2D
    CNT_ATTR = _match_id
    MATCH_STRATEGY = Match Selected Attributes
    BLANK_AND_MISSING_DIFFER = No
    SINGLE_MATCHED -> Flomsoner200 (writer SHAPE_1) [off]
    NOT_MATCHED -> Flomsoner200 (writer SHAPE_1) [off]
Flomsoner200 (writer SHAPE_1) [off]
    attributes: _match_id char(200)

Bookmark: Flomsoner500
Note: Lager polygon av / envelope
Creator_36 [off]
    NUM = 1
    COORDS = $(MINX) $(MINY) $(MAXX) $(MINY) $(MAXX) $(MAXY)  $(MINX) $(MAXY)  $(MINX) $(MINY)
    GEOMTYPE = 2D Coordinate List
    COORDSYS = EPSG:25833
    CREATED -> Reprojector_33 [off]
Note: Projiserer envelopen til 25833
Reprojector_33 [off]
    DEST = EPSG:25833
    STROKE_ARCS = Yes
    SOURCE = Read from feature
    INTERPOLATION_TYPE_NAME = Nearest Neighbor
    RASTER_CELL_SIZE = Preserve Cells
    REPROJECTED -> Tiler_32 [off]
Note: Tiler opp envelopen i mindre / områder
Tiler_32 [off]
    TILING_TYPE = Tile Size
    XINC = 100000
    ROW_ATTR = _row
    YINC = 100000
    COL_ATTR = _column
    TILED -> BoundsExtractor_32 [off]
BoundsExtractor_32 [off]
    YMIN = _ymin
    YMAX = _ymax
    ZMIN = _zmin
    ZMAX = _zmax
    XMIN = _xmin
    XMAX = _xmax
    -> AttributeCreator_43 [off]
AttributeCreator_43 [off]
    ATTR_LIST = Query,http://gis3.nve.no/map/rest/services/Flomsoner/MapServer/7/query?where=1%3D1&text=&objectIds=&time=&geometry=@Value(_xmin),@Value(_ymin),@Value(_xmax),@Value(_ymax)&geometryType=esriGeometryEnvelope&inSR=&spatialRel=esriSpatialRelIntersects&relationParam=&outFields=&returnGeometry=true&maxAllowableOffset=&geometryPrecision=&outSR=&returnIdsOnly=false&returnCountOnly=false&orderByFields=&groupByFieldsForStatistics=&outStatistics=&returnZ=false&returnM=false&gdbVersion=&returnDistinctValues=false&returnTrueCurves=false&resultOffset=&resultRecordCount=&f=pjson
    -> FeatureReader_35 [off]
FeatureReader_35 [off]
    FORMAT = ESRIJSON
    OUTPUT_FEATURES_DISPLAY = Only Data Features
    ESRIJSON_CLIP_TO_ENVELOPE = NO
    COMBINE_GEOM = Use Result
    ESRIJSON_USE_BASENAME_AS_DEFAULT_FEATURE_TYPE = No
    ESRIJSON_USE_SEARCH_ENVELOPE = NO
    DATASET = @Value(Query)
    ATTR_ACCUM_MODE = Only Use Result
    ESRIJSON_DELETE_DOWNLOAD_FILE = Yes
    ESRIJSON_SIMPLIFY_MULTIS = Yes
    INTERACT = <No Spatial Filter>
    ESRIJSON_MAKE_PATHS = No
    FEATURETYPES_RADIO = FEATURETYPES
    ESRIJSON_MAKE_DONUTS = No
    <OTHER> -> Matcher_34 [off]
Matcher_34 [off]
    LENIENT_MATCH = No
    MATCH = 2D
    CNT_ATTR = _match_id
    MATCH_STRATEGY = Match Selected Attributes
    BLANK_AND_MISSING_DIFFER = No
    SINGLE_MATCHED -> Flomsoner500 (writer SHAPE_1) [off]
    NOT_MATCHED -> Flomsoner500 (writer SHAPE_1) [off]
Flomsoner500 (writer SHAPE_1) [off]
    attributes: _match_id char(200)

Bookmark: Flomsoner1000
Note: Lager polygon av / envelope
Creator_37 [off]
    NUM = 1
    COORDS = $(MINX) $(MINY) $(MAXX) $(MINY) $(MAXX) $(MAXY)  $(MINX) $(MAXY)  $(MINX) $(MINY)
    GEOMTYPE = 2D Coordinate List
    COORDSYS = EPSG:25833
    CREATED -> Reprojector_34 [off]
Note: Projiserer envelopen til 25833
Reprojector_34 [off]
    DEST = EPSG:25833
    STROKE_ARCS = Yes
    SOURCE = Read from feature
    INTERPOLATION_TYPE_NAME = Nearest Neighbor
    RASTER_CELL_SIZE = Preserve Cells
    REPROJECTED -> Tiler_33 [off]
Note: Tiler opp envelopen i mindre / områder
Tiler_33 [off]
    TILING_TYPE = Tile Size
    XINC = 100000
    ROW_ATTR = _row
    YINC = 100000
    COL_ATTR = _column
    TILED -> BoundsExtractor_33 [off]
BoundsExtractor_33 [off]
    YMIN = _ymin
    YMAX = _ymax
    ZMIN = _zmin
    ZMAX = _zmax
    XMIN = _xmin
    XMAX = _xmax
    -> AttributeCreator_44 [off]
AttributeCreator_44 [off]
    ATTR_LIST = Query,http://gis3.nve.no/map/rest/services/Flomsoner/MapServer/8/query?where=1%3D1&text=&objectIds=&time=&geometry=@Value(_xmin),@Value(_ymin),@Value(_xmax),@Value(_ymax)&geometryType=esriGeometryEnvelope&inSR=&spatialRel=esriSpatialRelIntersects&relationParam=&outFields=&returnGeometry=true&maxAllowableOffset=&geometryPrecision=&outSR=&returnIdsOnly=false&returnCountOnly=false&orderByFields=&groupByFieldsForStatistics=&outStatistics=&returnZ=false&returnM=false&gdbVersion=&returnDistinctValues=false&returnTrueCurves=false&resultOffset=&resultRecordCount=&f=pjson
    -> FeatureReader_36 [off]
FeatureReader_36 [off]
    FORMAT = ESRIJSON
    OUTPUT_FEATURES_DISPLAY = Only Data Features
    ESRIJSON_CLIP_TO_ENVELOPE = NO
    COMBINE_GEOM = Use Result
    ESRIJSON_USE_BASENAME_AS_DEFAULT_FEATURE_TYPE = No
    ESRIJSON_USE_SEARCH_ENVELOPE = NO
    DATASET = @Value(Query)
    ATTR_ACCUM_MODE = Only Use Result
    ESRIJSON_DELETE_DOWNLOAD_FILE = Yes
    ESRIJSON_SIMPLIFY_MULTIS = Yes
    INTERACT = <No Spatial Filter>
    ESRIJSON_MAKE_PATHS = No
    FEATURETYPES_RADIO = FEATURETYPES
    ESRIJSON_MAKE_DONUTS = No
    <OTHER> -> Matcher_35 [off]
Matcher_35 [off]
    LENIENT_MATCH = No
    MATCH = 2D
    CNT_ATTR = _match_id
    MATCH_STRATEGY = Match Selected Attributes
    BLANK_AND_MISSING_DIFFER = No
    SINGLE_MATCHED -> Flomsoner1000 (writer SHAPE_1) [off]
    NOT_MATCHED -> Flomsoner1000 (writer SHAPE_1) [off]
Flomsoner1000 (writer SHAPE_1) [off]
    attributes: _match_id char(200)

Bookmark: Flomsoner 200 i år 2100
Note: Lager polygon av / envelope
Creator_38 [off]
    NUM = 1
    COORDS = $(MINX) $(MINY) $(MAXX) $(MINY) $(MAXX) $(MAXY)  $(MINX) $(MAXY)  $(MINX) $(MINY)
    GEOMTYPE = 2D Coordinate List
    COORDSYS = EPSG:25833
    CREATED -> Reprojector_35 [off]
Note: Projiserer envelopen til 25833
Reprojector_35 [off]
    DEST = EPSG:25833
    STROKE_ARCS = Yes
    SOURCE = Read from feature
    INTERPOLATION_TYPE_NAME = Nearest Neighbor
    RASTER_CELL_SIZE = Preserve Cells
    REPROJECTED -> Tiler_34 [off]
Note: Tiler opp envelopen i mindre / områder
Tiler_34 [off]
    TILING_TYPE = Tile Size
    XINC = 100000
    ROW_ATTR = _row
    YINC = 100000
    COL_ATTR = _column
    TILED -> BoundsExtractor_34 [off]
BoundsExtractor_34 [off]
    YMIN = _ymin
    YMAX = _ymax
    ZMIN = _zmin
    ZMAX = _zmax
    XMIN = _xmin
    XMAX = _xmax
    -> AttributeCreator_45 [off]
AttributeCreator_45 [off]
    ATTR_LIST = Query,http://gis3.nve.no/map/rest/services/Flomsoner/MapServer/9/query?where=1%3D1&text=&objectIds=&time=&geometry=@Value(_xmin),@Value(_ymin),@Value(_xmax),@Value(_ymax)&geometryType=esriGeometryEnvelope&inSR=&spatialRel=esriSpatialRelIntersects&relationParam=&outFields=&returnGeometry=true&maxAllowableOffset=&geometryPrecision=&outSR=&returnIdsOnly=false&returnCountOnly=false&orderByFields=&groupByFieldsForStatistics=&outStatistics=&returnZ=false&returnM=false&gdbVersion=&returnDistinctValues=false&returnTrueCurves=false&resultOffset=&resultRecordCount=&f=pjson
    -> FeatureReader_37 [off]
FeatureReader_37 [off]
    FORMAT = ESRIJSON
    OUTPUT_FEATURES_DISPLAY = Only Data Features
    ESRIJSON_CLIP_TO_ENVELOPE = NO
    COMBINE_GEOM = Use Result
    ESRIJSON_USE_BASENAME_AS_DEFAULT_FEATURE_TYPE = No
    ESRIJSON_USE_SEARCH_ENVELOPE = NO
    DATASET = @Value(Query)
    ATTR_ACCUM_MODE = Only Use Result
    ESRIJSON_DELETE_DOWNLOAD_FILE = Yes
    ESRIJSON_SIMPLIFY_MULTIS = Yes
    INTERACT = <No Spatial Filter>
    ESRIJSON_MAKE_PATHS = No
    FEATURETYPES_RADIO = FEATURETYPES
    ESRIJSON_MAKE_DONUTS = No
    <OTHER> -> Matcher_36 [off]
Matcher_36 [off]
    LENIENT_MATCH = No
    MATCH = 2D
    CNT_ATTR = _match_id
    MATCH_STRATEGY = Match Selected Attributes
    BLANK_AND_MISSING_DIFFER = No
    SINGLE_MATCHED -> Flomsoner200_i_aar_2100 (writer SHAPE_1) [off]
    NOT_MATCHED -> Flomsoner200_i_aar_2100 (writer SHAPE_1) [off]
Flomsoner200_i_aar_2100 (writer SHAPE_1) [off]
    attributes: _match_id char(200)

Bookmark: Snøskred_aktsomhetsområde
Note: Lager polygon av / envelope
Creator_39 [off]
    NUM = 1
    COORDS = $(MINX) $(MINY) $(MAXX) $(MINY) $(MAXX) $(MAXY)  $(MINX) $(MAXY)  $(MINX) $(MINY)
    GEOMTYPE = 2D Coordinate List
    COORDSYS = EPSG:25833
    CREATED -> Reprojector_36 [off]
Note: Projiserer envelopen til 25833
Reprojector_36 [off]
    DEST = EPSG:25833
    STROKE_ARCS = Yes
    SOURCE = Read from feature
    INTERPOLATION_TYPE_NAME = Nearest Neighbor
    RASTER_CELL_SIZE = Preserve Cells
    REPROJECTED -> Tiler_35 [off]
Note: Tiler opp envelopen i mindre / områder
Tiler_35 [off]
    TILING_TYPE = Tile Size
    XINC = 100000
    ROW_ATTR = _row
    YINC = 100000
    COL_ATTR = _column
    TILED -> BoundsExtractor_35 [off]
BoundsExtractor_35 [off]
    YMIN = _ymin
    YMAX = _ymax
    ZMIN = _zmin
    ZMAX = _zmax
    XMIN = _xmin
    XMAX = _xmax
    -> AttributeCreator_46 [off]
AttributeCreator_46 [off]
    ATTR_LIST = Query,http://gis3.nve.no/map/rest/services/SkredSnoAktR/MapServer/1/query?where=1%3D1&text=&objectIds=&time=&geometry=@Value(_xmin),@Value(_ymin),@Value(_xmax),@Value(_ymax)&geometryType=esriGeometryEnvelope&inSR=&spatialRel=esriSpatialRelIntersects&relationParam=&outFields=&returnGeometry=true&maxAllowableOffset=&geometryPrecision=&outSR=&returnIdsOnly=false&returnCountOnly=false&orderByFields=&groupByFieldsForStatistics=&outStatistics=&returnZ=false&returnM=false&gdbVersion=&returnDistinctValues=false&returnTrueCurves=false&resultOffset=&resultRecordCount=&f=pjson
    -> FeatureReader_38 [off]
FeatureReader_38 [off]
    FORMAT = ESRIJSON
    OUTPUT_FEATURES_DISPLAY = Only Data Features
    ESRIJSON_CLIP_TO_ENVELOPE = NO
    COMBINE_GEOM = Use Result
    ESRIJSON_USE_BASENAME_AS_DEFAULT_FEATURE_TYPE = No
    ESRIJSON_USE_SEARCH_ENVELOPE = NO
    DATASET = @Value(Query)
    ATTR_ACCUM_MODE = Only Use Result
    ESRIJSON_DELETE_DOWNLOAD_FILE = Yes
    ESRIJSON_SIMPLIFY_MULTIS = Yes
    INTERACT = <No Spatial Filter>
    ESRIJSON_MAKE_PATHS = No
    FEATURETYPES_RADIO = FEATURETYPES
    ESRIJSON_MAKE_DONUTS = No
    <OTHER> -> Matcher_37 [off]
Matcher_37 [off]
    LENIENT_MATCH = No
    MATCH = 2D
    CNT_ATTR = _match_id
    MATCH_STRATEGY = Match Selected Attributes
    BLANK_AND_MISSING_DIFFER = No
    SINGLE_MATCHED -> Snoeskred_aktsomhet (writer SHAPE_1) [off]
    NOT_MATCHED -> Snoeskred_aktsomhet (writer SHAPE_1) [off]
Note: Lager polygon av / envelope
Creator_40 [off]
    NUM = 1
    COORDS = $(MINX) $(MINY) $(MAXX) $(MINY) $(MAXX) $(MAXY)  $(MINX) $(MAXY)  $(MINX) $(MINY)
    GEOMTYPE = 2D Coordinate List
    COORDSYS = EPSG:25833
    CREATED -> Reprojector_37 [off]
Note: Projiserer envelopen til 25833
Reprojector_37 [off]
    DEST = EPSG:25833
    STROKE_ARCS = Yes
    SOURCE = Read from feature
    INTERPOLATION_TYPE_NAME = Nearest Neighbor
    RASTER_CELL_SIZE = Preserve Cells
    REPROJECTED -> Tiler_36 [off]
Note: Tiler opp envelopen i mindre / områder
Tiler_36 [off]
    TILING_TYPE = Tile Size
    XINC = 50000
    ROW_ATTR = _row
    YINC = 50000
    COL_ATTR = _column
    TILED -> BoundsExtractor_36 [off]
BoundsExtractor_36 [off]
    YMIN = _ymin
    YMAX = _ymax
    ZMIN = _zmin
    ZMAX = _zmax
    XMIN = _xmin
    XMAX = _xmax
    -> AttributeCreator_47 [off]
AttributeCreator_47 [off]
    ATTR_LIST = Query,http://gis3.nve.no/map/rest/services/SkredSnoAktR/MapServer/2/query?where=1%3D1&text=&objectIds=&time=&geometry=@Value(_xmin),@Value(_ymin),@Value(_xmax),@Value(_ymax)&geometryType=esriGeometryEnvelope&inSR=&spatialRel=esriSpatialRelIntersects&relationParam=&outFields=&returnGeometry=true&maxAllowableOffset=&geometryPrecision=&outSR=&returnIdsOnly=false&returnCountOnly=false&orderByFields=&groupByFieldsForStatistics=&outStatistics=&returnZ=false&returnM=false&gdbVersion=&returnDistinctValues=false&returnTrueCurves=false&resultOffset=&resultRecordCount=&f=pjson
    -> FeatureReader_39 [off]
FeatureReader_39 [off]
    FORMAT = ESRIJSON
    OUTPUT_FEATURES_DISPLAY = Only Data Features
    ESRIJSON_CLIP_TO_ENVELOPE = NO
    COMBINE_GEOM = Use Result
    ESRIJSON_USE_BASENAME_AS_DEFAULT_FEATURE_TYPE = No
    ESRIJSON_USE_SEARCH_ENVELOPE = NO
    DATASET = @Value(Query)
    ATTR_ACCUM_MODE = Only Use Result
    ESRIJSON_DELETE_DOWNLOAD_FILE = Yes
    ESRIJSON_SIMPLIFY_MULTIS = Yes
    INTERACT = <No Spatial Filter>
    ESRIJSON_MAKE_PATHS = No
    FEATURETYPES_RADIO = FEATURETYPES
    ESRIJSON_MAKE_DONUTS = No
    <OTHER> -> Matcher_38 [off]
Matcher_38 [off]
    LENIENT_MATCH = No
    MATCH = 2D
    CNT_ATTR = _match_id
    MATCH_STRATEGY = Match Selected Attributes
    BLANK_AND_MISSING_DIFFER = No
    SINGLE_MATCHED -> Snoeskred_aktsomhet (writer SHAPE_1) [off]
    NOT_MATCHED -> Snoeskred_aktsomhet (writer SHAPE_1) [off]
Snoeskred_aktsomhet (writer SHAPE_1) [off]
    attributes: _match_id char(200)

Bookmark: Steinsprang_aktsomhetsområde
Note: Lager polygon av / envelope
Creator_41 [off]
    NUM = 1
    COORDS = $(MINX) $(MINY) $(MAXX) $(MINY) $(MAXX) $(MAXY)  $(MINX) $(MAXY)  $(MINX) $(MINY)
    GEOMTYPE = 2D Coordinate List
    COORDSYS = EPSG:25833
    CREATED -> Reprojector_38 [off]
Note: Projiserer envelopen til 25833
Reprojector_38 [off]
    DEST = EPSG:25833
    STROKE_ARCS = Yes
    SOURCE = Read from feature
    INTERPOLATION_TYPE_NAME = Nearest Neighbor
    RASTER_CELL_SIZE = Preserve Cells
    REPROJECTED -> Tiler_37 [off]
Note: Tiler opp envelopen i mindre / områder
Tiler_37 [off]
    TILING_TYPE = Tile Size
    XINC = 100000
    ROW_ATTR = _row
    YINC = 100000
    COL_ATTR = _column
    TILED -> BoundsExtractor_37 [off]
BoundsExtractor_37 [off]
    YMIN = _ymin
    YMAX = _ymax
    ZMIN = _zmin
    ZMAX = _zmax
    XMIN = _xmin
    XMAX = _xmax
    -> AttributeCreator_48 [off]
AttributeCreator_48 [off]
    ATTR_LIST = Query,http://gis3.nve.no/map/rest/services/SkredSteinAktR/MapServer/1/query?where=1%3D1&text=&objectIds=&time=&geometry=@Value(_xmin),@Value(_ymin),@Value(_xmax),@Value(_ymax)&geometryType=esriGeometryEnvelope&inSR=&spatialRel=esriSpatialRelIntersects&relationParam=&outFields=&returnGeometry=true&maxAllowableOffset=&geometryPrecision=&outSR=&returnIdsOnly=false&returnCountOnly=false&orderByFields=&groupByFieldsForStatistics=&outStatistics=&returnZ=false&returnM=false&gdbVersion=&returnDistinctValues=false&returnTrueCurves=false&resultOffset=&resultRecordCount=&f=pjson
    -> FeatureReader_40 [off]
FeatureReader_40 [off]
    FORMAT = ESRIJSON
    OUTPUT_FEATURES_DISPLAY = Only Data Features
    ESRIJSON_CLIP_TO_ENVELOPE = NO
    COMBINE_GEOM = Use Result
    ESRIJSON_USE_BASENAME_AS_DEFAULT_FEATURE_TYPE = No
    ESRIJSON_USE_SEARCH_ENVELOPE = NO
    DATASET = @Value(Query)
    ATTR_ACCUM_MODE = Only Use Result
    ESRIJSON_DELETE_DOWNLOAD_FILE = Yes
    ESRIJSON_SIMPLIFY_MULTIS = Yes
    INTERACT = <No Spatial Filter>
    ESRIJSON_MAKE_PATHS = No
    FEATURETYPES_RADIO = FEATURETYPES
    ESRIJSON_MAKE_DONUTS = No
    <OTHER> -> Matcher_39 [off]
Matcher_39 [off]
    LENIENT_MATCH = No
    MATCH = 2D
    CNT_ATTR = _match_id
    MATCH_STRATEGY = Match Selected Attributes
    BLANK_AND_MISSING_DIFFER = No
    SINGLE_MATCHED -> Steinsprang_aktsomhet (writer SHAPE_1) [off]
    NOT_MATCHED -> Steinsprang_aktsomhet (writer SHAPE_1) [off]
Note: Lager polygon av / envelope
Creator_42 [off]
    NUM = 1
    COORDS = $(MINX) $(MINY) $(MAXX) $(MINY) $(MAXX) $(MAXY)  $(MINX) $(MAXY)  $(MINX) $(MINY)
    GEOMTYPE = 2D Coordinate List
    COORDSYS = EPSG:25833
    CREATED -> Reprojector_39 [off]
Note: Projiserer envelopen til 25833
Reprojector_39 [off]
    DEST = EPSG:25833
    STROKE_ARCS = Yes
    SOURCE = Read from feature
    INTERPOLATION_TYPE_NAME = Nearest Neighbor
    RASTER_CELL_SIZE = Preserve Cells
    REPROJECTED -> Tiler_38 [off]
Note: Tiler opp envelopen i mindre / områder
Tiler_38 [off]
    TILING_TYPE = Tile Size
    XINC = 50000
    ROW_ATTR = _row
    YINC = 50000
    COL_ATTR = _column
    TILED -> BoundsExtractor_38 [off]
BoundsExtractor_38 [off]
    YMIN = _ymin
    YMAX = _ymax
    ZMIN = _zmin
    ZMAX = _zmax
    XMIN = _xmin
    XMAX = _xmax
    -> AttributeCreator_49 [off]
AttributeCreator_49 [off]
    ATTR_LIST = Query,http://gis3.nve.no/map/rest/services/SkredSteinAktR/MapServer/2/query?where=1%3D1&text=&objectIds=&time=&geometry=@Value(_xmin),@Value(_ymin),@Value(_xmax),@Value(_ymax)&geometryType=esriGeometryEnvelope&inSR=&spatialRel=esriSpatialRelIntersects&relationParam=&outFields=&returnGeometry=true&maxAllowableOffset=&geometryPrecision=&outSR=&returnIdsOnly=false&returnCountOnly=false&orderByFields=&groupByFieldsForStatistics=&outStatistics=&returnZ=false&returnM=false&gdbVersion=&returnDistinctValues=false&returnTrueCurves=false&resultOffset=&resultRecordCount=&f=pjson
    -> FeatureReader_41 [off]
FeatureReader_41 [off]
    FORMAT = ESRIJSON
    OUTPUT_FEATURES_DISPLAY = Only Data Features
    ESRIJSON_CLIP_TO_ENVELOPE = NO
    COMBINE_GEOM = Use Result
    ESRIJSON_USE_BASENAME_AS_DEFAULT_FEATURE_TYPE = No
    ESRIJSON_USE_SEARCH_ENVELOPE = NO
    DATASET = @Value(Query)
    ATTR_ACCUM_MODE = Only Use Result
    ESRIJSON_DELETE_DOWNLOAD_FILE = Yes
    ESRIJSON_SIMPLIFY_MULTIS = Yes
    INTERACT = <No Spatial Filter>
    ESRIJSON_MAKE_PATHS = No
    FEATURETYPES_RADIO = FEATURETYPES
    ESRIJSON_MAKE_DONUTS = No
    <OTHER> -> Matcher_40 [off]
Matcher_40 [off]
    LENIENT_MATCH = No
    MATCH = 2D
    CNT_ATTR = _match_id
    MATCH_STRATEGY = Match Selected Attributes
    BLANK_AND_MISSING_DIFFER = No
    SINGLE_MATCHED -> Steinsprang_aktsomhet (writer SHAPE_1) [off]
    NOT_MATCHED -> Steinsprang_aktsomhet (writer SHAPE_1) [off]
Steinsprang_aktsomhet (writer SHAPE_1) [off]
    attributes: _match_id char(200)

Bookmark: Snøskred_Steinsprang_aktsomhetsområde
Note: Lager polygon av / envelope
Creator_43 [off]
    NUM = 1
    COORDS = $(MINX) $(MINY) $(MAXX) $(MINY) $(MAXX) $(MAXY)  $(MINX) $(MAXY)  $(MINX) $(MINY)
    GEOMTYPE = 2D Coordinate List
    COORDSYS = EPSG:25833
    CREATED -> Reprojector_40 [off]
Note: Projiserer envelopen til 25833
Reprojector_40 [off]
    DEST = EPSG:25833
    STROKE_ARCS = Yes
    SOURCE = Read from feature
    INTERPOLATION_TYPE_NAME = Nearest Neighbor
    RASTER_CELL_SIZE = Preserve Cells
    REPROJECTED -> Tiler_39 [off]
Note: Tiler opp envelopen i mindre / områder
Tiler_39 [off]
    TILING_TYPE = Tile Size
    XINC = 100000
    ROW_ATTR = _row
    YINC = 100000
    COL_ATTR = _column
    TILED -> BoundsExtractor_39 [off]
BoundsExtractor_39 [off]
    YMIN = _ymin
    YMAX = _ymax
    ZMIN = _zmin
    ZMAX = _zmax
    XMIN = _xmin
    XMAX = _xmax
    -> AttributeCreator_50 [off]
AttributeCreator_50 [off]
    ATTR_LIST = Query,http://gis3.nve.no/map/rest/services/SkredSnoSteinAkt/MapServer/1/query?where=1%3D1&text=&objectIds=&time=&geometry=@Value(_xmin),@Value(_ymin),@Value(_xmax),@Value(_ymax)&geometryType=esriGeometryEnvelope&inSR=&spatialRel=esriSpatialRelIntersects&relationParam=&outFields=&returnGeometry=true&maxAllowableOffset=&geometryPrecision=&outSR=&returnIdsOnly=false&returnCountOnly=false&orderByFields=&groupByFieldsForStatistics=&outStatistics=&returnZ=false&returnM=false&gdbVersion=&returnDistinctValues=false&returnTrueCurves=false&resultOffset=&resultRecordCount=&f=pjson
    -> FeatureReader_42 [off]
FeatureReader_42 [off]
    FORMAT = ESRIJSON
    OUTPUT_FEATURES_DISPLAY = Only Data Features
    ESRIJSON_CLIP_TO_ENVELOPE = NO
    COMBINE_GEOM = Use Result
    ESRIJSON_USE_BASENAME_AS_DEFAULT_FEATURE_TYPE = No
    ESRIJSON_USE_SEARCH_ENVELOPE = NO
    DATASET = @Value(Query)
    ATTR_ACCUM_MODE = Only Use Result
    ESRIJSON_DELETE_DOWNLOAD_FILE = Yes
    ESRIJSON_SIMPLIFY_MULTIS = Yes
    INTERACT = <No Spatial Filter>
    ESRIJSON_MAKE_PATHS = No
    FEATURETYPES_RADIO = FEATURETYPES
    ESRIJSON_MAKE_DONUTS = No
    <OTHER> -> Matcher_41 [off]
Matcher_41 [off]
    LENIENT_MATCH = No
    MATCH = 2D
    CNT_ATTR = _match_id
    MATCH_STRATEGY = Match Selected Attributes
    BLANK_AND_MISSING_DIFFER = No
    SINGLE_MATCHED -> Snoeskred_Steinsprang_aktsomhet (writer SHAPE_1) [off]
    NOT_MATCHED -> Snoeskred_Steinsprang_aktsomhet (writer SHAPE_1) [off]
Note: Lager polygon av / envelope
Creator_44 [off]
    NUM = 1
    COORDS = $(MINX) $(MINY) $(MAXX) $(MINY) $(MAXX) $(MAXY)  $(MINX) $(MAXY)  $(MINX) $(MINY)
    GEOMTYPE = 2D Coordinate List
    COORDSYS = EPSG:25833
    CREATED -> Reprojector_41 [off]
Note: Projiserer envelopen til 25833
Reprojector_41 [off]
    DEST = EPSG:25833
    STROKE_ARCS = Yes
    SOURCE = Read from feature
    INTERPOLATION_TYPE_NAME = Nearest Neighbor
    RASTER_CELL_SIZE = Preserve Cells
    REPROJECTED -> Tiler_40 [off]
Note: Tiler opp envelopen i mindre / områder
Tiler_40 [off]
    TILING_TYPE = Tile Size
    XINC = 100000
    ROW_ATTR = _row
    YINC = 100000
    COL_ATTR = _column
    TILED -> BoundsExtractor_40 [off]
BoundsExtractor_40 [off]
    YMIN = _ymin
    YMAX = _ymax
    ZMIN = _zmin
    ZMAX = _zmax
    XMIN = _xmin
    XMAX = _xmax
    -> AttributeCreator_51 [off]
AttributeCreator_51 [off]
    ATTR_LIST = Query,http://gis3.nve.no/map/rest/services/SkredSnoSteinAkt/MapServer/2/query?where=1%3D1&text=&objectIds=&time=&geometry=@Value(_xmin),@Value(_ymin),@Value(_xmax),@Value(_ymax)&geometryType=esriGeometryEnvelope&inSR=&spatialRel=esriSpatialRelIntersects&relationParam=&outFields=&returnGeometry=true&maxAllowableOffset=&geometryPrecision=&outSR=&returnIdsOnly=false&returnCountOnly=false&orderByFields=&groupByFieldsForStatistics=&outStatistics=&returnZ=false&returnM=false&gdbVersion=&returnDistinctValues=false&returnTrueCurves=false&resultOffset=&resultRecordCount=&f=pjson
    -> FeatureReader_43 [off]
FeatureReader_43 [off]
    FORMAT = ESRIJSON
    OUTPUT_FEATURES_DISPLAY = Only Data Features
    ESRIJSON_CLIP_TO_ENVELOPE = NO
    COMBINE_GEOM = Use Result
    ESRIJSON_USE_BASENAME_AS_DEFAULT_FEATURE_TYPE = No
    ESRIJSON_USE_SEARCH_ENVELOPE = NO
    DATASET = @Value(Query)
    ATTR_ACCUM_MODE = Only Use Result
    ESRIJSON_DELETE_DOWNLOAD_FILE = Yes
    ESRIJSON_SIMPLIFY_MULTIS = Yes
    INTERACT = <No Spatial Filter>
    ESRIJSON_MAKE_PATHS = No
    FEATURETYPES_RADIO = FEATURETYPES
    ESRIJSON_MAKE_DONUTS = No
    <OTHER> -> Matcher_42 [off]
Matcher_42 [off]
    LENIENT_MATCH = No
    MATCH = 2D
    CNT_ATTR = _match_id
    MATCH_STRATEGY = Match Selected Attributes
    BLANK_AND_MISSING_DIFFER = No
    SINGLE_MATCHED -> Snoeskred_Steinsprang_aktsomhet (writer SHAPE_1) [off]
    NOT_MATCHED -> Snoeskred_Steinsprang_aktsomhet (writer SHAPE_1) [off]
Snoeskred_Steinsprang_aktsomhet (writer SHAPE_1) [off]
    attributes: _match_id char(200)

Bookmark: Jord og Flomskred
Note: Lager polygon av / envelope
Creator_45 [off]
    NUM = 1
    COORDS = $(MINX) $(MINY) $(MAXX) $(MINY) $(MAXX) $(MAXY)  $(MINX) $(MAXY)  $(MINX) $(MINY)
    GEOMTYPE = 2D Coordinate List
    COORDSYS = EPSG:25833
    CREATED -> Reprojector_42 [off]
Note: Projiserer envelopen til 25833
Reprojector_42 [off]
    DEST = EPSG:25833
    STROKE_ARCS = Yes
    SOURCE = Read from feature
    INTERPOLATION_TYPE_NAME = Nearest Neighbor
    RASTER_CELL_SIZE = Preserve Cells
    REPROJECTED -> Tiler_41 [off]
Note: Tiler opp envelopen i mindre / områder
Tiler_41 [off]
    TILING_TYPE = Tile Size
    XINC = 50000
    ROW_ATTR = _row
    YINC = 50000
    COL_ATTR = _column
    TILED -> BoundsExtractor_41 [off]
BoundsExtractor_41 [off]
    YMIN = _ymin
    YMAX = _ymax
    ZMIN = _zmin
    ZMAX = _zmax
    XMIN = _xmin
    XMAX = _xmax
    -> AttributeCreator_52 [off]
AttributeCreator_52 [off]
    ATTR_LIST = Query,http://gis3.nve.no/map/rest/services/SkredJordFlomAktR1/MapServer/1/query?where=1%3D1&text=&objectIds=&time=&geometry=@Value(_xmin),@Value(_ymin),@Value(_xmax),@Value(_ymax)&geometryType=esriGeometryEnvelope&inSR=&spatialRel=esriSpatialRelIntersects&relationParam=&outFields=&returnGeometry=true&maxAllowableOffset=&geometryPrecision=&outSR=&returnIdsOnly=false&returnCountOnly=false&orderByFields=&groupByFieldsForStatistics=&outStatistics=&returnZ=false&returnM=false&gdbVersion=&returnDistinctValues=false&returnTrueCurves=false&resultOffset=&resultRecordCount=&f=pjson
    -> FeatureReader_44 [off]
FeatureReader_44 [off]
    FORMAT = ESRIJSON
    OUTPUT_FEATURES_DISPLAY = Only Data Features
    ESRIJSON_CLIP_TO_ENVELOPE = NO
    COMBINE_GEOM = Use Result
    ESRIJSON_USE_BASENAME_AS_DEFAULT_FEATURE_TYPE = No
    ESRIJSON_USE_SEARCH_ENVELOPE = NO
    DATASET = @Value(Query)
    ATTR_ACCUM_MODE = Only Use Result
    ESRIJSON_DELETE_DOWNLOAD_FILE = Yes
    ESRIJSON_SIMPLIFY_MULTIS = Yes
    INTERACT = <No Spatial Filter>
    ESRIJSON_MAKE_PATHS = No
    FEATURETYPES_RADIO = FEATURETYPES
    ESRIJSON_MAKE_DONUTS = No
    <OTHER> -> Matcher_43 [off]
Matcher_43 [off]
    LENIENT_MATCH = No
    MATCH = 2D
    CNT_ATTR = _match_id
    MATCH_STRATEGY = Match Selected Attributes
    BLANK_AND_MISSING_DIFFER = No
    SINGLE_MATCHED -> Jord_og_flomskred_aktsomhet (writer SHAPE_1) [off]
    NOT_MATCHED -> Jord_og_flomskred_aktsomhet (writer SHAPE_1) [off]
Jord_og_flomskred_aktsomhet (writer SHAPE_1) [off]
    attributes: _match_id char(200)

Bookmark: Skredhendelser
Note: Lager polygon av / envelope
Creator_47 [off]
    NUM = 1
    COORDS = $(MINX) $(MINY) $(MAXX) $(MINY) $(MAXX) $(MAXY)  $(MINX) $(MAXY)  $(MINX) $(MINY)
    GEOMTYPE = 2D Coordinate List
    COORDSYS = EPSG:25833
    CREATED -> Reprojector_43 [off]
Note: Projiserer envelopen til 25833
Reprojector_43 [off]
    DEST = EPSG:25833
    STROKE_ARCS = Yes
    SOURCE = Read from feature
    INTERPOLATION_TYPE_NAME = Nearest Neighbor
    RASTER_CELL_SIZE = Preserve Cells
    REPROJECTED -> Tiler_42 [off]
Note: Tiler opp envelopen i mindre / områder
Tiler_42 [off]
    TILING_TYPE = Tile Size
    XINC = 100000
    ROW_ATTR = _row
    YINC = 100000
    COL_ATTR = _column
    TILED -> BoundsExtractor_42 [off]
BoundsExtractor_42 [off]
    YMIN = _ymin
    YMAX = _ymax
    ZMIN = _zmin
    ZMAX = _zmax
    XMIN = _xmin
    XMAX = _xmax
    -> AttributeCreator_54 [off]
AttributeCreator_54 [off]
    ATTR_LIST = Query,http://gis3.nve.no/map/rest/services/SkredHendelser/MapServer/0/query?where=1%3D1&text=&objectIds=&time=&geometry=@Value(_xmin),@Value(_ymin),@Value(_xmax),@Value(_ymax)&geometryType=esriGeometryEnvelope&inSR=&spatialRel=esriSpatialRelIntersects&relationParam=&outFields=&returnGeometry=true&maxAllowableOffset=&geometryPrecision=&outSR=&returnIdsOnly=false&returnCountOnly=false&orderByFields=&groupByFieldsForStatistics=&outStatistics=&returnZ=false&returnM=false&gdbVersion=&returnDistinctValues=false&returnTrueCurves=false&resultOffset=&resultRecordCount=&f=pjson
    -> FeatureReader_46 [off]
FeatureReader_46 [off]
    FORMAT = ESRIJSON
    OUTPUT_FEATURES_DISPLAY = Only Data Features
    ESRIJSON_CLIP_TO_ENVELOPE = NO
    COMBINE_GEOM = Use Result
    ESRIJSON_USE_BASENAME_AS_DEFAULT_FEATURE_TYPE = No
    ESRIJSON_USE_SEARCH_ENVELOPE = NO
    DATASET = @Value(Query)
    ATTR_ACCUM_MODE = Only Use Result
    ESRIJSON_DELETE_DOWNLOAD_FILE = Yes
    ESRIJSON_SIMPLIFY_MULTIS = Yes
    INTERACT = <No Spatial Filter>
    ESRIJSON_MAKE_PATHS = No
    FEATURETYPES_RADIO = FEATURETYPES
    ESRIJSON_MAKE_DONUTS = No
    <OTHER> -> Matcher_45 [off]
Matcher_45 [off]
    LENIENT_MATCH = No
    MATCH = 2D
    CNT_ATTR = _match_id
    MATCH_STRATEGY = Match Selected Attributes
    BLANK_AND_MISSING_DIFFER = No
    SINGLE_MATCHED -> Skredhendelser (writer SHAPE_1) [off]
    NOT_MATCHED -> Skredhendelser (writer SHAPE_1) [off]
Skredhendelser (writer SHAPE_1) [off]
    attributes: _match_id char(200)

Bookmark: Skredfaresoner
Note: Lager polygon av / envelope
Creator_46 [off]
    NUM = 1
    COORDS = $(MINX) $(MINY) $(MAXX) $(MINY) $(MAXX) $(MAXY)  $(MINX) $(MAXY)  $(MINX) $(MINY)
    GEOMTYPE = 2D Coordinate List
    COORDSYS = EPSG:25833
    CREATED -> AttributeCreator_53 [off]
AttributeCreator_53 [off]
    ATTR_LIST = Query,http://gis3.nve.no/map/rest/services/Skredfaresoner1/MapServer/0/query?where=1%3D1&text=&objectIds=&time=&geometry=&geometryType=esriGeometryEnvelope&inSR=&spatialRel=esriSpatialRelIntersects&relationParam=&outFields=&returnGeometry=true&maxAllowableOffset=&geometryPrecision=&outSR=&returnIdsOnly=false&returnCountOnly=false&orderByFields=&groupByFieldsForStatistics=&outStatistics=&returnZ=false&returnM=false&gdbVersion=&returnDistinctValues=false&returnTrueCurves=false&resultOffset=&resultRecordCount=&f=pjson
    -> FeatureReader_45 [off]
FeatureReader_45 [off]
    FORMAT = ESRIJSON
    OUTPUT_FEATURES_DISPLAY = Only Data Features
    ESRIJSON_CLIP_TO_ENVELOPE = NO
    COMBINE_GEOM = Use Result
    ESRIJSON_USE_BASENAME_AS_DEFAULT_FEATURE_TYPE = No
    ESRIJSON_USE_SEARCH_ENVELOPE = NO
    DATASET = @Value(Query)
    ATTR_ACCUM_MODE = Only Use Result
    ESRIJSON_DELETE_DOWNLOAD_FILE = Yes
    ESRIJSON_SIMPLIFY_MULTIS = Yes
    INTERACT = <No Spatial Filter>
    ESRIJSON_MAKE_PATHS = No
    FEATURETYPES_RADIO = FEATURETYPES
    ESRIJSON_MAKE_DONUTS = No
    <OTHER> -> Matcher_44 [off]
Matcher_44 [off]
    LENIENT_MATCH = No
    MATCH = 2D
    CNT_ATTR = _match_id
    MATCH_STRATEGY = Match Selected Attributes
    BLANK_AND_MISSING_DIFFER = No
    SINGLE_MATCHED -> Skredfaresoner (writer SHAPE_1) [off]
    NOT_MATCHED -> Skredfaresoner (writer SHAPE_1) [off]
Skredfaresoner (writer SHAPE_1) [off]
    attributes: _match_id char(200)
