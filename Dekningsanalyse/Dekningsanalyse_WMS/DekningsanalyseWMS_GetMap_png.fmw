FME workspace DekningsanalyseWMS_GetMap_png.fmw
Title: INSPIRE_WMS.fmw
Description: This WMS workspace reads from an INSPIRE staging PostGIS database and uses WFS to publish GML via the data streaming service, based on the query parameters provided by the WFS client. The Loader workspaces (INSPIRE_WFS_A1.CadastralParcels.Loader.fmw, INSPIRE_WFS_A1.GeoNames.Loader.fmw) handle data loading, reprojection and schema mapping to the databases 'INSPIRE like' data model. 
INSPIRE_WFS.fmw is a WFS 'service broker' workspace. This just needs to be published to the data streaming service and will accept WFS GET or POST requests (GetCapabilities, DescribeFeature and GetFeatrue) and generate the appropriate responses as XML or GML data streams (GetCapabilities, Describe feature XML docs or GML features). Supports XMLfilters which is something our built in WFS did not do. 
Also, configured to support FME Data Inspector as a WFS client. Note that 
this requires FME Server 2014 or later to function. This is required 
to support the new GML writer.
Requirements: FME 2014 14229+
History: 1/8/2014,Dean,Created / published

Parameters:
- SERVICE = WMS   # Service
- REQUEST = GetMap   # Request
- VERSION = 1.1.1   # Version
- LAYERS = Akvakultur   # Layer
- _WorkspaceURL = $(FME_SERVER_WEB_URL)/fmedatastreaming/INSPIRE/INSPIRE_WMS.fmw   # Workspace URL
- bboxWest =   # Bounding box - minimum X coordinate
- bboxSouth =   # Bounding box - minimum Y coordinate
- bboxEast =   # Bounding box - maximum X coordinate
- bboxNorth =   # Bounding box - maximum Y coordinate
- bboxCRS =   # Bounding box - coordinate system
- BBOX =   # Bounding box
- MAXFEATURES = 5000   # MaxFeatures
- WIDTH = 1500   # Width
- HEIGHT = 1500   # Height
- DestDataset_PNGRASTER = $(FME_MF_DIR)output_Jan_2015   # Destination PNG (Portable Network Graphics) Directory
- FORMAT = image/png   # Format

Readers:
- TEXTLINE_1: TEXTLINE from $(FME_MF_DIR)GetMapRequest.txt

Writers:
- PNGRASTER_1: PNGRASTER to $(DestDataset_PNGRASTER) in EPSG:32633

Tester
    BOOL_OP = OR
    TEST_DESCRIPTION = ""
    TEST_CLAUSE = TEST @Value(korallrev) = t
    TEST_MODE = Automatic
    PASSED -> MapnikRasterizer [input 1]
    FAILED -> MapnikRasterizer [input 2]
MapnikRasterizer_Raster: Inspector
Reprojector_2
    RASTER_CELL_SIZE = Preserve Cells
    INTERPOLATION_TYPE_NAME = Nearest Neighbor
    SOURCE = Read from feature
    DEST = EPSG:32633
    REPROJECTED -> Tester_2
Tester_2
    BOOL_OP = OR
    TEST_DESCRIPTION = ""
    TEST_CLAUSE = TEST @Value(akvakultur) = t
    TEST_MODE = Automatic
    PASSED -> MapnikRasterizer_2 [input 1]
    FAILED -> MapnikRasterizer_2 [input 2]
MapnikRasterizer_2_Raster: Inspector

Bookmark: Client Input
text_line (reader TEXTLINE_1)
    attributes: text_line_data buffer
    -> ParameterFetcher

Bookmark: Process GET Request
ParameterFetcher
    ATTR_LIST = _VERSION {$(VERSION)} _REQUEST {$(REQUEST)} _SERVICE {$(SERVICE)} _LAYERS {$(LAYERS)} _BBOX {$(BBOX)} _bboxWest {$(bboxWest)}
    -> TestFilter
TestFilter
    DEFAULT_VALUE = <UNFILTERED>
    TEST_LIST = BOOL_OP,OR,COMPOSITE_TEST,<Unused>,TEST_CLAUSE,"TEST @Value(_REQUEST) LIKE GetCapabilities",GetCapabilities,BOOL_OP,OR,COMPOSITE_TEST,<Unused>,TEST_CLAUSE,"TEST @Value(_REQUEST) LIKE GetMap",GetMap
    GetCapabilities -> TestFilter_GetCapabilities
    GetMap -> AttributeFilter

Bookmark: Error Response
TestFilter_GetCapabilities: Logger
    MAXFEATS = 20
    MESSAGE = ERROR Feature is:
    MAXCOORDS = 20
Reprojector
    RASTER_CELL_SIZE = Preserve Cells
    INTERPOLATION_TYPE_NAME = Nearest Neighbor
    SOURCE = Read from feature
    DEST = EPSG:32633
    REPROJECTED -> Tester

Bookmark: GetMap Request
AttributeFilter
    ATTR_NAME = _LAYERS
    ATTR_VALUES = Korallrev,<EMPTY>,<MISSING>,<NULL>,<UNFILTERED>,Akvakultur
    Korallrev -> dekningsoversikt
    Akvakultur -> dekningsoversikt_2
dekningsoversikt
    FeatureReader_3_dekningsoversikt.dekningsoversikt -> Reprojector
dekningsoversikt_2
    FeatureReader_3_dekningsoversikt.dekningsoversikt -> Reprojector_2

Bookmark: Style Layers
MapnikRasterizer
    NUM_COLUMNS = $(WIDTH)
    BACKGROUND_COLOR_ALPHA = 1.0
    SPECIFY_GROUND_EXTENTS = Use input data ground extents
    MAPNIK_CONFIG = Sann;polygon;__ignore__color-group;;fill;0,0.666667,0;fill-opacity;1;__ignore__smoothing-group;;gamma;1;gamma-method;power;smooth;0;__ignore__comp-group;;comp-op;src-over;Usann;polygon;__ignore__color-group;;fill;1,0,0;fill-opacity;1;__ignore__smoothing-group;;gamma;1;gamma-method;power;smooth;0;__ignore__comp-group;;comp-op;src-over
    NUM_ROWS = $(HEIGHT)
    COLROW_OR_SPACING = Columns and Rows
    BACKGROUND_COLOR = 1,1,1
    INTERPRETATION_TYPE = RGBA32
    RASTER -> ParameterFetcher_3
    RASTER -> MapnikRasterizer_Raster
MapnikRasterizer_2
    NUM_COLUMNS = $(WIDTH)
    BACKGROUND_COLOR_ALPHA = 1.0
    SPECIFY_GROUND_EXTENTS = Use input data ground extents
    MAPNIK_CONFIG = Sann;polygon;__ignore__color-group;;fill;0,1,1;fill-opacity;1;__ignore__smoothing-group;FME_DISCLOSURE_OPEN;gamma;1;gamma-method;power;smooth;0;__ignore__comp-group;FME_DISCLOSURE_OPEN;comp-op;src-over;Usann;polygon;__ignore__color-group;;fill;1,0.666667,0;fill-opacity;1;__ignore__smoothing-group;;gamma;1;gamma-method;power;smooth;0;__ignore__comp-group;;comp-op;src-over
    NUM_ROWS = $(HEIGHT)
    COLROW_OR_SPACING = Columns and Rows
    BACKGROUND_COLOR = 1,1,1
    INTERPRETATION_TYPE = RGBA32
    RASTER -> ParameterFetcher_3
    RASTER -> MapnikRasterizer_2_Raster

Bookmark: Output to WMS Image
ParameterFetcher_3
    ATTR_LIST = _VERSION {$(VERSION)} _REQUEST {$(REQUEST)} _SERVICE {$(SERVICE)} _LAYERS {$(LAYERS)} _BBOX {$(BBOX)} _bboxWest {$(bboxWest)}
    -> GetMapResult (writer PNGRASTER_1)
GetMapResult (writer PNGRASTER_1)

FME custom transformer GetBBOX
Generate bounding box depending on values of bbox parameters

Parameters:
- bboxWest =   # Bounding box - minimum X coordinate
- bboxSouth =   # Bounding box - minimum Y coordinate
- bboxEast =   # Bounding box - maximum X coordinate
- bboxNorth =   # Bounding box - maximum Y coordinate
- BBOX =

INPUT (input)
    -> ParameterFetcher

Bookmark: Determine BBox Type
ParameterFetcher
    ATTR_LIST = _BBOX {$(BBOX)} _bboxWest {$(bboxWest)} _bboxSouth {$(bboxSouth)} _bboxEast {$(bboxEast)} _bboxNorth {$(bboxNorth)}
    -> AttributeExposer
AttributeExposer
    ATTR_LIST = _bbox.coord{0},_bbox.coord{1},_bbox.coord{2},_bbox.coord{3},_bbox.coord{4}
    -> TestFilter_2
TestFilter_2
    DEFAULT_VALUE = <UNFILTERED>
    TEST_LIST = BOOL_OP,OR,COMPOSITE_TEST,<Unused>,TEST_CLAUSE,"TEST @Value(_BBOX) != """"",BBOX,BOOL_OP,OR,COMPOSITE_TEST,<Unused>,TEST_CLAUSE,"TEST @Value(_bboxWest) != """"",bboxCoords
    bboxCoords -> 2DBoxReplacer_coords
    BBOX -> Tester_7
    <UNFILTERED> -> <UNFILTERED> (output)
<UNFILTERED> (output)

Bookmark: Generate BBox Polygon from Parameters
Tester_7
    BOOL_OP = OR
    TEST_DESCRIPTION = ""
    TEST_CLAUSE = TEST @Value(_BBOX) NOT_CONTAINS %
    TEST_MODE = Automatic
    PASSED -> AttributeSplitter_2
    FAILED -> TextDecoder_2
TextDecoder_2
    ENCODING_TYPE = URL (Percent Encoding)
    DEST_ATTR = _BBOX
    STRING_TO_DECODE = @Value(_BBOX)
    -> Tester_2
AttributeSplitter_2
    LIST_NAME = _bbox.coord
    TRIM_OPTION = Both
    ATTR_NAME = _BBOX
    DELIMITER = ,
    DROP_EMPTY_PARTS = No
    -> AttributeCopier
AttributeCopier
    ATTR_LIST = Xmin,_bbox.coord{0},Ymin,_bbox.coord{1},Xmax,_bbox.coord{2},Ymax,_bbox.coord{3},epsg,_bbox.coord{4}
    -> 2DBoxReplacer_bbox
2DBoxReplacer_bbox
    MINYVALATTR = @Value(Ymin)
    MINXVALATTR = @Value(Xmin)
    MAXYVALATTR = @Value(Ymax)
    MAXXVALATTR = @Value(Xmax)
    BOX -> BBox (output)
2DBoxReplacer_coords
    MINYVALATTR = $(bboxSouth)
    MINXVALATTR = $(bboxWest)
    MAXYVALATTR = $(bboxNorth)
    MAXXVALATTR = $(bboxEast)
    BOX -> BBox (output)
BBox (output)

Bookmark: Double encoding bug from FME WMS
Tester_2
    BOOL_OP = OR
    TEST_DESCRIPTION = ""
    TEST_CLAUSE = TEST @Value(_BBOX) NOT_CONTAINS %
    TEST_MODE = Automatic
    PASSED -> AttributeSplitter_2
    FAILED -> TextDecoder_3
TextDecoder_3
    ENCODING_TYPE = URL (Percent Encoding)
    DEST_ATTR = _BBOX
    STRING_TO_DECODE = @Value(_BBOX)
    -> AttributeSplitter_2

FME custom transformer dekningsoversikt

Parameters:
- bboxWest =   # Bounding box - minimum X coordinate
- bboxSouth =   # Bounding box - minimum Y coordinate
- bboxEast =   # Bounding box - maximum X coordinate
- bboxNorth =   # Bounding box - maximum Y coordinate
- BBOX =   # Bounding box

GetBBOX_INPUT_1 (input)
    -> GetBBOX

Bookmark: Henter dekningsdata
GetBBOX
    bboxSouth = $(bboxSouth)
    bboxEast = $(bboxEast)
    BBOX = $(BBOX)
    bboxNorth = $(bboxNorth)
    bboxWest = $(bboxWest)
    BBox -> FeatureReader_3
    <UNFILTERED> -> FeatureReader_3
Note: Med extents
FeatureReader_3
    POSTGIS_PORT = 5432
    ATTRIBUTES = dekningsoversikt.dekningsoversikt,"kommuneid,akvakultur,korallrev,dsb_110sentral,dsb_brannstasjon,dsb_distrkont_siv,dsb_sivforsvdistr"
    POSTGIS_QUERY_FEATURE_TYPES_FOR_MERGE_FILTERS = Yes
    FORMAT = POSTGIS
    POSTGIS_CLIP_TO_ENVELOPE = NO
    POSTGIS_DISABLE_COLLECTION_SPLITTING = yes
    POSTGIS_USE_TRUE_POSTGIS_TYPES = yes
    POSTGIS_USE_SEARCH_ENVELOPE = NO
    POSTGIS_HOST = Nnridb504
    POSTGIS_USER_NAME = geonortst
    ATTR_ACCUM_MODE = Only Use Result
    COMBINE_GEOM = Use Result
    POSTGIS_PASSWORD =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
    SUPPORTED_SPATIAL_INTERACTIONS = ENVELOPE_INTERSECT%ENVELOPE_INTERSECT%INTERSECTS%CONTAINS%CROSSES%DISJOINT%EQUALS%OVERLAPS%TOUCHES%WITHIN
    DATASET = geonor01tst
    FEATURETYPES_RADIO = FEATURETYPES
    FEATURETYPES = dekningsoversikt.dekningsoversikt
    POSTGIS_SCHEMALIST = dekningsoversikt
    INTERACT = Envelope Intersect
    dekningsoversikt.dekningsoversikt -> FeatureReader_3_dekningsoversikt.dekningsoversikt (output)
FeatureReader_3_dekningsoversikt.dekningsoversikt (output)
