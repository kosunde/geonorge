FME workspace Dekningsanalyse_rastervisning.fmw

Parameters:
- SourceDataset_POSTGIS = geonortst@Nnridb504:5432/geonor01tst   # Connection
- DestDataset_PNGRASTER = Z:\Geonorge\Dekningsanalyse   # Destination PNG (Portable Network Graphics) Folder

Readers:
- POSTGIS_1: POSTGIS from $(SourceDataset_POSTGIS)

Writers:
- PNGRASTER_1: PNGRASTER to $(DestDataset_PNGRASTER)

dekningsoversikt.dekningsoversikt (reader POSTGIS_1)
    attributes: kommuneid int4, akvakultur bool, korallrev bool, dsb_110sentral bool, dsb_brannstasjon bool, dsb_distrkont_siv bool, dsb_sivforsvdistr bool, ra_brannsmitteomr bool, ra_tettetrehusm bool, ra_frededebygg bool, ra_enkeltminner bool, ra_kulturmiljo bool, ra_lokaliteter bool, ra_sikringssoner bool
    -> Tester
    -> TopologyBuilder [input 3]
Tester
    TEST_CLAUSE = TEST @Value(dsb_distrkont_siv) = t
    TEST_MODE = Automatic
    BOOL_OP = OR
    TEST_DESCRIPTION = ""
    FAILED -> MapnikRasterizer [input 2]
    PASSED -> MapnikRasterizer [input 1]
TopologyBuilder
    OVERLAPPING_MODE = No
    CLEAN_DATA = No
    PROP_ATTRS = No
    MAX = 0
    ALLOW_CYCLES = No
    ALL_EDGES = Yes
    LINE -> MapnikRasterizer [input 3]
MapnikRasterizer
    COLROW_OR_SPACING = Columns and Rows
    NUM_ROWS = 2500
    LAYER_CARDINALITY = Each rendering rule is a layer
    BACKGROUND_COLOR_ALPHA = 0
    SPECIFY_GROUND_EXTENTS = Use input data ground extents
    BACKGROUND_COLOR = 1,1,1
    MAPNIK_CONFIG = dekningsoversikt.dekningsoversikt;polygon;__ignore__color-group;;fill;0,1,0;fill-opacity;1;__ignore__smoothing-group;FME_DISCLOSURE_OPEN;gamma;1;gamma-method;power;smooth;0;__ignore__comp-group;FME_DISCLOSURE_OPEN;comp-op;src-over;failed;polygon;__ignore__color-group;;fill;1,0,0;fill-opacity;1;__ignore__smoothing-group;;gamma;1;gamma-method;power;smooth;0;__ignore__comp-group;;comp-op;src-over;Line;line;__ignore__color-group;;stroke;0,0,0;stroke-opacity;1;__ignore__line-style-group;;stroke-width;1;stroke-linejoin;miter;stroke-linecap;butt;stroke-dasharray;;stroke-miterlimit;4;__ignore__positioning-group;;offset;0;__ignore__smoothing-group;;stroke-gamma;1;stroke-gamma-method;power;smooth;0;rasterizer;full;__ignore__comp-group;;comp-op;src-over
    NUM_COLUMNS = 2500
    INTERPRETATION_TYPE = RGBA32
    RASTER -> MapnikRasterizer_Raster
    RASTER -> dekningsoversikt (writer PNGRASTER_1)
MapnikRasterizer_Raster: Inspector
dekningsoversikt (writer PNGRASTER_1)
