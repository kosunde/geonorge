FME workspace Dekningsanalyse2xlsx.fmw

Parameters:
- SourceDataset_POSTGIS = geonortst@nnridb504:5432/geonor01tst   # Connection
- DestDataset_XLSXW2 = D:\Data\Dekningsoversikt\Norge.xlsx   # Destination Microsoft Excel File
- SourceDataset_POSTGRES = geonortst@nnridb504:5432/geonor01tst   # Connection

Readers:
- POSTGIS_1: POSTGIS from $(SourceDataset_POSTGIS)
- POSTGRES_1: POSTGRES from $(SourceDataset_POSTGRES)

Writers:
- XLSXW2_1: XLSXW2 to $(DestDataset_XLSXW2)

dekningsoversikt.dekningsoversikt (reader POSTGIS_1)
    attributes: kommuneid int4, akvakultur bool, korallrev bool, dsb_110sentral bool, dsb_brannstasjon bool, dsb_distrkont_siv bool, dsb_sivforsvdistr bool, ra_brannsmitteomr bool, ra_tettetrehusm bool, ra_frededebygg bool, ra_enkeltminner bool, ra_kulturmiljo bool, ra_lokaliteter bool, ra_sikringssoner bool, kv_hovedbiled bool, kv_ispshavneanlegg bool, kv_losbordingsfelt bool, kv_losstasjoner bool, nve_flomsoner10 bool, nve_flomsoner20 bool, nve_flomsoner50 bool, nve_flomsoner100 bool, nve_flomsoner200 bool, nve_flomsoner500 bool, nve_flomsoner1000 bool, nve_flomsoner200_i_aar2100 bool, nve_flomsonekartplan bool, nve_elvis_hovedelv bool, nve_elvis_elvenett bool, nve_innsjodata bool,
      nve_dybdekart bool, nve_nedborfelt_regine bool, nve_vassdragsomrade bool, nve_totnedbfelt_mstasjon bool, nve_vannkraftverk bool, nve_vindparkomrader bool, nve_vindturbin bool, nve_kraftlinjer bool, nve_sjokabler bool, nve_transformatorstasjoner bool, nve_omradekonsesjoner bool, nve_sikringstiltak bool, nve_verneplan_vassdrag bool, nve_kvikkleire bool, nve_aktsomhet_snoskred bool, nve_aktsomhet_steinsprang bool, nve_aktsomhet_snosteinsprang bool, nve_aktsomhet_jordflomskred bool, nve_skredhendelser bool, nve_kraftverk_alle_kst bool, nve_magasin bool, nve_dam bool, nve_vanninntak bool, nve_vannvei bool, nve_delfelt_vannkraft bool, nve_vindkraftverk bool, nve_skredsoner bool, dsb_anleggfarligstoff bool, dsb_storulykkeanlegg bool, dsb_eksplosivanlegg bool,
      nibio_jordkvalitet bool, md_forurensetgrunn bool, md_frilstatligsikra bool, md_frilkartlverds bool, md_verdif_kulturlandsk bool, md_viktige_naturt bool, md_villreinomr bool, md_naturvernomr bool, md_naturvernomr_foresl bool, md_arter_nasjon_forv bool, md_naturt_landskap bool, md_naturt_utv bool, fkb_ar5 bool, fkb_adresse bool, fkb_arealbruk bool, fkb_bane bool, fkb_bygnanlegg bool, fkb_bygning bool, fkb_bygningspunkt bool, fkb_hoydekurve-5m bool, fkb_hoydekurve bool, fkb_ledning bool, fkb_ledningva bool, fkb_lufthavn bool, fkb_matrikkelkartdekteig bool, fkb_naturinfo bool, fkb_pbltiltak bool, fkb_servitutt bool, fkb_tekst1000 bool, fkb_tekst5000 bool,
      fkb_traktorvegsti bool, fkb_vann bool, fkb_vbase bool, fkb_veg bool, ldir_reinbeitedistrikt bool, ldir_reinbeiteomrade bool, ldir_reindriftsanlegg bool, ldir_beitehage bool, ldir_flyttlei bool, ldir_trekklei bool, ldir_oppsamlingsomrade bool, ldir_varbeite bool, ldir_sommerbeite bool, ldir_hostbeite bool, ldir_hostvinterbeite bool, ldir_vinterbeite bool, ldir_siidagrense bool, ldir_konvensjonsomrade bool, ldir_konsesjonsomrader bool, ldir_restriksjonsomrader bool, ldir_tamreinlag bool, ldir_restriksjonsgrense bool, ldir_rendal bool, ldir_trollheimen bool, ldir_avtaleomrader bool, ldir_ekspropriasjonsomrader bool, avinor_stoysoner bool, forsvaret_stoysoner bool, matrikkel_vegadresser bool, nibio_ar50 bool,
      sk_vbase bool, sk_n50 bool, sk_n250 bool, sk_n500 bool, sk_n1000 bool, sk_n5000 bool, sk_ssr bool, sk_abas bool, matrikkel_bygningspunkt bool, matrikkel_eiendom bool, ngu_losmasser bool, sk_norgesmargrenser bool, sk_sjokartraster bool, id int4,PRIKEY, svv_trafikkmengde bool, svv_trafikkulykker bool, sk_nrl bool, sk_turogfriluft bool, sk_uu_friluft bool, sk_uu_tettsted bool, sk_planomriss bool, ngu_grusogpukk bool, ngu_mineralressurser bool, ngu_grunnvannsborehull bool, ngu_radonaktsomhet bool, ngu_maringrense bool
    -> FeatureMerger [input 1]
admingrense.kommuner (reader POSTGRES_1)
    attributes: kommuneid int2,PRIKEY, navn varchar(80)
    -> AttributeRenamer_2
AttributeRenamer_2
    ATTR_LIST = navn,kommunenavn,
    -> FeatureMerger [input 2]
FeatureMerger
    MERGE_TYPE = Attributes Only
    ATTR_ACCUM_MODE = Merge Supplier
    JOIN_KEYS = @Value(kommuneid) @Value(kommuneid) AUTO
    PROCESS_DUPS = No
    ATTR_CONFLICT_RES = Use Requestor
    SUPPLIERS_FIRST = No
    IGNORE_NULLS = No
    MERGED -> SubstringExtractor
SubstringExtractor
    SRC_STRING = @Value(kommuneid)
    RESULT_ATTR = fylkeid
    END = -3
    START = 0
    -> FeatureMerger_2 [input 1]
admingrense.fylker (reader POSTGRES_1)
    attributes: fylkeid int2,PRIKEY, navn varchar(80)
    -> AttributeRenamer
AttributeRenamer
    ATTR_LIST = navn,fylkesnavn,
    -> FeatureMerger_2 [input 2]
FeatureMerger_2
    MERGE_TYPE = Attributes Only
    ATTR_ACCUM_MODE = Merge Supplier
    JOIN_KEYS = @Value(fylkeid) @Value(fylkeid) AUTO
    PROCESS_DUPS = No
    ATTR_CONFLICT_RES = Use Requestor
    SUPPLIERS_FIRST = No
    IGNORE_NULLS = No
    MERGED -> NullAttributeMapper
NullAttributeMapper
    ATTRCHOICE = All Attributes
    NULL_TREATMENT = New Value
    OTHER_VALUE = f
    NEW_VALUE = Ingen dekning
    -> NullAttributeMapper_2
NullAttributeMapper_2
    ATTRCHOICE = All Attributes
    NULL_TREATMENT = New Value
    OTHER_VALUE = t
    NEW_VALUE = Dekning
    -> AttributeRenamer_3
AttributeRenamer_3
    ATTR_LIST = akvakultur,Akvakultur,,avinor_stoysoner,Støysoner flyplasser,,dsb_110sentral,110-sentraldistrikter,,dsb_anleggfarligstoff,Anlegg farlig stoff,,dsb_brannstasjon,Brannstasjoner,,dsb_distrkont_siv,Distriktskontor sivilforsvaret,,dsb_eksplosivanlegg,Eksplosivanlegg,,dsb_sivforsvdistr,Sivilforsvarsdistrikter,,dsb_storulykkeanlegg,Storulykkeanlegg,,fkb_adresse,FKB Adresse,,fkb_ar5,FKB AR5,,fkb_arealbruk,FKB Arealbruk,,fkb_bane,FKB Bane,,fkb_bygnanlegg,FKB BygnAnlegg,,fkb_bygning,FKB Bygning,,fkb_bygningspunkt,FKB Bygningspunkt,,fkb_hoydekurve,FKB Høydekurve,,fkb_hoydekurve-5m,FKB Høydekurve 5m,,fkb_ledning,FKB Ledning,,fkb_ledningva,FKB LedningVa,,fkb_lufthavn,FKB Lufthavn,,fkb_matrikkelkartdekteig,FKB Matrikkelkart DEKTeig,,fkb_naturinfo,FKB Naturinfo,,fkb_pbltiltak,FKB PblTiltak,,fkb_servitutt,FKB Servitutt,,fkb_tekst1000,FKB Tekst1000,,fkb_tekst5000,FKB Tekst5000,,fkb_traktorvegsti,FKB TraktorvegSti,,fkb_vann,FKB Vann,,fkb_vbase,FKB Vbase,,fkb_veg,FKB Veg,,forsvaret_stoysoner,Støysoner skytefelt,,korallrev,Korallrev,,kv_hovedbiled,Hoved/biled,,kv_ispshavneanlegg,ISPS_havneanlegg,,kv_losbordingsfelt,Losbordingsfelt,,kv_losstasjoner,Losstasjoner,,ldir_avtaleomrader,Avtaleområder,,ldir_beitehage,Beitehage,,ldir_ekspropriasjonsomrader,Ekspropriasjonsområder,,ldir_flyttlei,Flyttlei,,ldir_hostbeite,Høstbeite,,ldir_hostvinterbeite,Høstvinterbeite,,ldir_konsesjonsomrader,Konsesjonsområder,,ldir_konvensjonsomrade,Konvensjonsområde,,ldir_oppsamlingsomrade,Oppsamlingsområde,,ldir_reinbeitedistrikt,Reinbeitedistrikt,,ldir_reinbeiteomrade,Reinbeiteområde,,ldir_reindriftsanlegg,Reindriftsanlegg,,ldir_rendal,Rendal renselskap,,ldir_restriksjonsgrense,Restriksjonsgrense,,ldir_restriksjonsomrader,Restriksjonsområder,,ldir_siidagrense,Siidagrense,,ldir_sommerbeite,Sommerbeite,,ldir_tamreinlag,Tamreinlag (Filefjell, Fram, Vaga og Lom),,ldir_trekklei,Trekklei,,ldir_trollheimen,Trollheimen,,ldir_varbeite,Vårbeite,,ldir_vinterbeite,Vinterbeite,,matrikkel_bygningspunkt,Bygningspunkt fra matrikkelen,,matrikkel_eiendom,Eiendomsflater fra matrikkelen,,matrikkel_vegadresser,Vegadresser fra matrikkelen,,md_arter_nasjon_forv,Arter av nasjonal forvaltningsinteresse,,md_forurensetgrunn,Forurenset grunn,,md_frilkartlverds,Kartlagte og verdsatte friluftsområder,,md_frilstatligsikra,Statlig sikra friluftsområder,,md_naturt_landskap,Naturtyper i Norge - landskap,,md_naturt_utv,Utvalgte naturtyper,,md_naturvernomr,Naturvernområder,,md_naturvernomr_foresl,Foreslåtte naturvernområder,,md_verdif_kulturlandsk,Verdifulle kulturlandskap,,md_viktige_naturt,Viktige naturtyper,,md_villreinomr,Villreinområder,,ngu_losmasser,Løsmasser,,nibio_ar50,AR50,,nibio_jordkvalitet,Jordkvalitet,,nve_aktsomhet_jordflomskred,Jord - og flomskred aktsomhetsområder,,nve_aktsomhet_snoskred,Snøskred aktsomhetsområder,,nve_aktsomhet_snosteinsprang,Snø - og steinskred aktsomhetsområder,,nve_aktsomhet_steinsprang,Steinsprang aktsomhetsområder,,nve_dam,Dam,,nve_delfelt_vannkraft,Delfelt vannkraft,,nve_dybdekart,Dybdekart innsjøer,,nve_elvis_elvenett,ELVIS Elvenett,,nve_elvis_hovedelv,ELVIS Hovedelv,,nve_flomsonekartplan,Flomsonekartplan,,nve_flomsoner10,Flomsoner 10,,nve_flomsoner100,Flomsoner 100,,nve_flomsoner1000,Flomsoner 1000,,nve_flomsoner20,Flomsoner 20,,nve_flomsoner200,Flomsoner 200,,nve_flomsoner200_i_aar2100,Flomsoner 200 i år 2100,,nve_flomsoner50,Flomsoner 50,,nve_flomsoner500,Flomsoner 500,,nve_innsjodata,Innsjødata,,nve_kraftlinjer,Kraftlinjer,,nve_kraftverk_alle_kst,Kraftverk, alle konsesjonsstadier,,nve_kvikkleire,Kvikkleire,,nve_magasin,Magasin,,nve_nedborfelt_regine,Nedbørfelt (REGINE),,nve_omradekonsesjoner,Områdekonsesjoner,,nve_sikringstiltak,Sikringstiltak,,nve_sjokabler,Sjøkabler,,nve_skredhendelser,Skredhendelser,,nve_skredsoner,Skredfaresoner,,nve_totnedbfelt_mstasjon,Totalnedbørfelt til målestasjon,,nve_transformatorstasjoner,Transformatorstasjoner,,nve_vanninntak,Vanninntak,,nve_vannkraftverk,Vannkraftverk,,nve_vannvei,Vannvei,,nve_vassdragsomrade,Vassdragsområde,,nve_verneplan_vassdrag,Verneplan for vassdrag,,nve_vindkraftverk,Vindkraftverk - utbygd og vindkraftverk - konsesjon,,nve_vindparkomrader,Vindparkområder - utbygd og vindparkområder - konsesjon,,nve_vindturbin,Vindturbin - utbygd,,ra_brannsmitteomr,Brannsmitteområder,,ra_enkeltminner,Kulturminne enkeltminner,,ra_frededebygg,Fredede bygninger,,ra_kulturmiljo,Kulturminne kulturmiljø,,ra_lokaliteter,Kulturminne lokaliteter,,ra_sikringssoner,Kulturminne sikringssoner,,ra_tettetrehusm,Tette trehusmiljø,,sk_abas,ABA (administrative enheter i Norge),,sk_n1000,N1000,,sk_n250,N250,,sk_n50,N50,,sk_n500,N500,,sk_n5000,N5000,,sk_norgesmargrenser,Norges maritime grenser,,sk_nrl,Luftfartshindere,,sk_planomriss,Planomriss,,sk_sjokartraster,Sjøkart raster,,sk_ssr,Sentralt stedsnavnsregister,,sk_turogfriluft,Tur og friluftsruter,,sk_uu_friluft,Universell utforming friluft,,sk_uu_tettsted,Universell utforming tettsted,,sk_vbase,Vbase,,svv_trafikkmengde,Trafikkmengde,,svv_trafikkulykker,Trafikkulykker,,ngu_grunnvannsborehull,Grunnvannsborehull,,ngu_grusogpukk,Grus og pukk,,ngu_mineralressurser,Mineralressurser,,ngu_radonaktsomhet,Radon Aktsomhet,,ngu_maringrense,Marin Grense,
    -> Sorter
    -> Sampler
    -> Sampler_2
Sorter
    SORT_PARM = kommuneid NUMERIC ASCENDING
    SORTED -> Norge (writer XLSXW2_1)
Norge (writer XLSXW2_1)
    attributes: Kommunenummer number(20), Kommunenavn auto(20), Akvakultur auto(20), Korallrev auto(20), 110-sentraldistrikter auto(20), Brannstasjoner auto(20), Distriktskontor sivilforsvaret auto(20), Sivilforsvarsdistrikter auto(20), Brannsmitteområder auto(20), Tette trehusmiljø auto(20), Fredede bygninger auto(20), Kulturminne enkeltminner auto(20), Kulturminne kulturmiljø auto(20), Kulturminne lokaliteter auto(20), Kulturminne sikringssoner auto(20), Hoved/biled auto(20), ISPS_havneanlegg auto(20), Losbordingsfelt auto(20), Losstasjoner auto(20), Flomsoner 10 auto(20), Flomsoner 20 auto(20), Flomsoner 50 auto(20), Flomsoner 100 auto(20), Flomsoner 200 auto(20), Flomsoner 500 auto(20), Flomsoner 1000 auto(20), Flomsoner 200 i år 2100 auto(20), Flomsonekartplan auto(20), ELVIS Hovedelv auto(20), ELVIS Elvenett auto(20),
      Innsjødata auto(20), Dybdekart innsjøer auto(20), Nedbørfelt (REGINE) auto(20), Vassdragsområde auto(20), Totalnedbørfelt til målestasjon auto(20), Vannkraftverk auto(20), Vindparkområder - utbygd og vindparkområder - konsesjon auto(20), Vindturbin - utbygd auto(20), Kraftlinjer auto(20), Sjøkabler auto(20), Transformatorstasjoner auto(20), Områdekonsesjoner auto(20), Sikringstiltak auto(20), Verneplan for vassdrag auto(20), Kvikkleire auto(20), Snøskred aktsomhetsområder auto(20), Steinsprang aktsomhetsområder auto(20), Snø - og steinskred aktsomhetsområder auto(20), Jord - og flomskred aktsomhetsområder auto(20), Skredhendelser auto(20), Kraftverk, alle konsesjonsstadier auto(20), Magasin auto(20), Dam auto(20), Vanninntak auto(20), Vannvei auto(20), Delfelt vannkraft auto(20), Vindkraftverk - utbygd og vindkraftverk - konsesjon auto(20), Skredfaresoner auto(20), Anlegg farlig stoff auto(20), Storulykkeanlegg auto(20),
      Eksplosivanlegg auto(20), Jordkvalitet auto(20), Forurenset grunn auto(20), Statlig sikra friluftsområder auto(20), Kartlagte og verdsatte friluftsområder auto(20), Verdifulle kulturlandskap auto(20), Viktige naturtyper auto(20), Villreinområder auto(20), Naturvernområder auto(20), Foreslåtte naturvernområder auto(20), Arter av nasjonal forvaltningsinteresse auto(20), Naturtyper i Norge - landskap auto(20), Utvalgte naturtyper auto(20), FKB AR5 auto(20), FKB Adresse auto(20), FKB Arealbruk auto(20), FKB Bane auto(20), FKB BygnAnlegg auto(20), FKB Bygning auto(20), FKB Bygningspunkt auto(20), FKB Høydekurve 5m auto(20), FKB Høydekurve auto(20), FKB Ledning auto(20), FKB LedningVa auto(20), FKB Lufthavn auto(20), FKB Matrikkelkart DEKTeig auto(20), FKB Naturinfo auto(20), FKB PblTiltak auto(20), FKB Servitutt auto(20), FKB Tekst1000 auto(20),
      FKB Tekst5000 auto(20), FKB TraktorvegSti auto(20), FKB Vann auto(20), FKB Vbase auto(20), FKB Veg auto(20), Reinbeitedistrikt auto(20), Reinbeiteområde auto(20), Reindriftsanlegg auto(20), Beitehage auto(20), Flyttlei auto(20), Trekklei auto(20), Oppsamlingsområde auto(20), Vårbeite auto(20), Sommerbeite auto(20), Høstbeite auto(20), Høstvinterbeite auto(20), Vinterbeite auto(20), Siidagrense auto(20), Konvensjonsområde auto(20), Konsesjonsområder auto(20), Restriksjonsområder auto(20), Tamreinlag (Filefjell, Fram, Vaga og Lom) auto(20), Restriksjonsgrense auto(20), Rendal renselskap auto(20), Trollheimen auto(20), Avtaleområder auto(20), Ekspropriasjonsområder auto(20), Støysoner flyplasser auto(20), Støysoner skytefelt auto(20), Vegadresser fra matrikkelen auto(20),
      AR50 auto(20), Vbase auto(20), N50 auto(20), N250 auto(20), N500 auto(20), N1000 auto(20), N5000 auto(20), Sentralt stedsnavnsregister auto(20), ABA (administrative enheter i Norge) auto(20), Bygningspunkt fra matrikkelen auto(20), Eiendomsflater fra matrikkelen auto(20), Løsmasser auto(20), Norges maritime grenser auto(20), Sjøkart raster auto(20), Trafikkmengde auto(20), Trafikkulykker auto(20), Luftfartshindere auto(20), Tur og friluftsruter auto(20), Universell utforming friluft auto(20), Universell utforming tettsted auto(20), Planomriss auto(20), Grus og pukk auto(20), Mineralressurser auto(20), Grunnvannsborehull auto(20), Radon Aktsomhet auto(20), Marin Grense auto(20)

Bookmark: DOK-attributt
Sampler
    RATE = 1
    SAMPLE_TYPE_LONG = First N Features
    SAMPLED -> AttributeRemover
AttributeRemover
    REMOVE_ATTRS = 110-sentraldistrikter,ABA (administrative enheter i Norge),Akvakultur,Anlegg farlig stoff,AR50,Arter av nasjonal forvaltningsinteresse,Avtaleområder,Beitehage,Brannsmitteområder,Brannstasjoner,Bygningspunkt fra matrikkelen,Dam,Delfelt vannkraft,Distriktskontor sivilforsvaret,Dybdekart innsjøer,Eiendomsflater fra matrikkelen,Eksplosivanlegg,Ekspropriasjonsområder,ELVIS Elvenett,ELVIS Hovedelv,FKB Adresse,FKB AR5,FKB Arealbruk,FKB Bane,FKB BygnAnlegg,FKB Bygning,FKB Bygningspunkt,FKB Høydekurve,FKB Høydekurve 5m,FKB Ledning,FKB LedningVa,FKB Lufthavn,FKB Matrikkelkart DEKTeig,FKB Naturinfo,FKB PblTiltak,FKB Servitutt,FKB Tekst1000,FKB Tekst5000,FKB TraktorvegSti,FKB Vann,FKB Vbase,FKB Veg,Flomsonekartplan,Flomsoner 10,Flomsoner 20,Flomsoner 50,Flomsoner 100,Flomsoner 200,Flomsoner 200 i år 2100,Flomsoner 500,Flomsoner 1000,Flyttlei,Foreslåtte naturvernområder,Forurenset grunn,Fredede bygninger,fylkeid,fylkesnavn,Hoved/biled,Høstbeite,Høstvinterbeite,id,Innsjødata,ISPS_havneanlegg,Jord - og flomskred aktsomhetsområder,Jordkvalitet,Kartlagte og verdsatte friluftsområder,Konsesjonsområder,Konvensjonsområde,Korallrev,Kraftlinjer,Kraftverk, alle konsesjonsstadier,Kulturminne enkeltminner,Kulturminne kulturmiljø,Kulturminne lokaliteter,Kulturminne sikringssoner,Kvikkleire,Losbordingsfelt,Losstasjoner,Luftfartshindere,Løsmasser,Magasin,N50,N250,N500,N1000,N5000,Naturtyper i Norge - landskap,Naturvernområder,Nedbørfelt (REGINE),Norges maritime grenser,Områdekonsesjoner,Oppsamlingsområde,Planomriss,Reinbeitedistrikt,Reinbeiteområde,Reindriftsanlegg,Rendal renselskap,Restriksjonsgrense,Restriksjonsområder,Sentralt stedsnavnsregister,Siidagrense,Sikringstiltak,Sivilforsvarsdistrikter,Sjøkabler,Sjøkart raster,Skredfaresoner,Skredhendelser,Snø - og steinskred aktsomhetsområder,Snøskred aktsomhetsområder,Sommerbeite,Statlig sikra friluftsområder,Steinsprang aktsomhetsområder,Storulykkeanlegg,Støysoner flyplasser,Støysoner skytefelt,Tamreinlag (Filefjell, Fram, Vaga og Lom),Tette trehusmiljø,Totalnedbørfelt til målestasjon,Trafikkmengde,Trafikkulykker,Transformatorstasjoner,Trekklei,Trollheimen,Tur og friluftsruter,Universell utforming friluft,Universell utforming tettsted,Utvalgte naturtyper,Vanninntak,Vannkraftverk,Vannvei,Vassdragsområde,Vbase,Vegadresser fra matrikkelen,Verdifulle kulturlandskap,Verneplan for vassdrag,Viktige naturtyper,Villreinområder,Vindkraftverk - utbygd og vindkraftverk - konsesjon,Vindparkområder - utbygd og vindparkområder - konsesjon,Vindturbin - utbygd,Vinterbeite,Vårbeite,kommuneid,kommunenavn
    -> AttributeCreator
AttributeCreator
    ATTR_LIST = Kommunenummer, ,Kommunenavn,DOK
    -> AttributeRenamer_4
AttributeRenamer_4
    ATTR_LIST = ABA (administrative enheter i Norge),ABA (administrative enheter i Norge),f,Anlegg farlig stoff,Anlegg farlig stoff,t,Arter av nasjonal forvaltningsinteresse,Arter av nasjonal forvaltningsinteresse,t,Bygningspunkt fra matrikkelen,Bygningspunkt fra matrikkelen,f,Delfelt vannkraft,Delfelt vannkraft,f,Distriktskontor sivilforsvaret,Distriktskontor sivilforsvaret,f,Dybdekart innsjøer,Dybdekart innsjøer,f,ELVIS Elvenett,ELVIS Elvenett,f,ELVIS Hovedelv,ELVIS Hovedelv,f,Eiendomsflater fra matrikkelen,Eiendomsflater fra matrikkelen,t,FKB AR5,FKB AR5,t,FKB Adresse,FKB Adresse,f,FKB Arealbruk,FKB Arealbruk,t,FKB Bane,FKB Bane,t,FKB BygnAnlegg,FKB BygnAnlegg,t,FKB Bygning,FKB Bygning,t,FKB Bygningspunkt,FKB Bygningspunkt,f,FKB Høydekurve 5m,FKB Høydekurve 5m,f,FKB Høydekurve,FKB Høydekurve,t,FKB Ledning,FKB Ledning,t,FKB LedningVa,FKB LedningVa,t,FKB Lufthavn,FKB Lufthavn,t,FKB Matrikkelkart DEKTeig,FKB Matrikkelkart DEKTeig,f,FKB Naturinfo,FKB Naturinfo,t,FKB PblTiltak,FKB PblTiltak,t,FKB Servitutt,FKB Servitutt,f,FKB Tekst1000,FKB Tekst1000,t,FKB Tekst5000,FKB Tekst5000,t,FKB TraktorvegSti,FKB TraktorvegSti,t,FKB Vann,FKB Vann,t,FKB Vbase,FKB Vbase,f,FKB Veg,FKB Veg,t,Flomsoner 10,Flomsoner 10,t,Flomsoner 100,Flomsoner 100,t,Flomsoner 1000,Flomsoner 1000,t,Flomsoner 20,Flomsoner 20,t,Flomsoner 200 i år 2100,Flomsoner 200 i år 2100,t,Flomsoner 200,Flomsoner 200,t,Flomsoner 50,Flomsoner 50,t,Flomsoner 500,Flomsoner 500,t,Foreslåtte naturvernområder,Foreslåtte naturvernområder,t,Forurenset grunn,Forurenset grunn,t,Fredede bygninger,Fredede bygninger,t,Jord - og flomskred aktsomhetsområder,Jord - og flomskred aktsomhetsområder,t,Kartlagte og verdsatte friluftsområder,Kartlagte og verdsatte friluftsområder,t,Konsesjonsområder ,Konsesjonsområder,f,Kraftverk, alle konsesjonsstadier,Kraftverk, alle konsesjonsstadier,f,Kulturminne enkeltminner,Kulturminne enkeltminner,t,Kulturminne kulturmiljø,Kulturminne kulturmiljø,t,Kulturminne lokaliteter,Kulturminne lokaliteter,t,Kulturminne sikringssoner,Kulturminne sikringssoner,t,Naturtyper i Norge - landskap,Naturtyper i Norge - landskap,f,Nedbørfelt (REGINE),Nedbørfelt (REGINE),f,Norges maritime grenser,Norges maritime grenser,t,Reinbeiteområde ,Reinbeiteområde,f,Rendal renselskap,Rendal renselskap,f,Sentralt stedsnavnsregister,Sentralt stedsnavnsregister,t,Sjøkart raster,Sjøkart raster,t,Snø - og steinskred aktsomhetsområder,Snø - og steinskred aktsomhetsområder,f,Snøskred aktsomhetsområder,Snøskred aktsomhetsområder,t,Statlig sikra friluftsområder,Statlig sikra friluftsområder,t,Steinsprang aktsomhetsområder,Steinsprang aktsomhetsområder,t,Støysoner flyplasser,Støysoner flyplasser,f,Støysoner skytefelt,Støysoner skytefelt,f,Tamreinlag (Filefjell, Fram, Vaga og Lom),Tamreinlag (Filefjell, Fram, Vaga og Lom),f,Tette trehusmiljø,Tette trehusmiljø,t,Totalnedbørfelt til målestasjon,Totalnedbørfelt til målestasjon,f,Trekklei ,Trekklei,t,Tur og friluftsruter,Tur og friluftsruter,f,Universell utforming friluft,Universell utforming friluft,f,Universell utforming tettsted,Universell utforming tettsted,f,Utvalgte naturtyper,Utvalgte naturtyper,t,Vegadresser fra matrikkelen,Vegadresser fra matrikkelen,f,Verdifulle kulturlandskap,Verdifulle kulturlandskap,t,Verneplan for vassdrag,Verneplan for vassdrag,t,Viktige naturtyper,Viktige naturtyper,t,Vindkraftverk - utbygd og vindkraftverk - konsesjon,Vindkraftverk - utbygd og vindkraftverk - konsesjon,f,Vindparkområder - utbygd og vindparkområder - konsesjon,Vindparkområder - utbygd og vindparkområder - konsesjon,f,Vindturbin - utbygd,Vindturbin - utbygd,f,110-sentraldistrikter,110-sentraldistrikter,f,AR50,AR50,f,Akvakultur,Akvakultur,t,Avtaleområder,Avtaleområder,f,Beitehage,Beitehage,f,Brannsmitteområder,Brannsmitteområder,f,Brannstasjoner,Brannstasjoner,f,Dam,Dam,f,Eksplosivanlegg,Eksplosivanlegg,t,Ekspropriasjonsområder,Ekspropriasjonsområder,f,Flomsonekartplan,Flomsonekartplan,t,Flyttlei,Flyttlei,t,Hoved/biled,Hoved/biled,t,Høstbeite,Høstbeite,f,Høstvinterbeite,Høstvinterbeite,t,ISPS_havneanlegg,ISPS_havneanlegg,FME_NULL_VALUE,Innsjødata,Innsjødata,f,Jordkvalitet,Jordkvalitet,t,Konvensjonsområde,Konvensjonsområde,f,Korallrev,Korallrev,t,Kraftlinjer,Kraftlinjer,f,Kvikkleire,Kvikkleire,t,Losbordingsfelt,Losbordingsfelt,f,Losstasjoner,Losstasjoner,f,Luftfartshindere,Luftfartshindere,f,Løsmasser,Løsmasser,t,Magasin,Magasin,f,N1000,N1000,t,N250,N250,t,N50,N50,t,N500,N500,f,N5000,N5000,t,Naturvernområder,Naturvernområder,t,Områdekonsesjoner,Områdekonsesjoner,f,Oppsamlingsområde,Oppsamlingsområde,t,Planomriss,Planomriss,f,Reinbeitedistrikt,Reinbeitedistrikt,f,Reindriftsanlegg,Reindriftsanlegg,t,Restriksjonsgrense,Restriksjonsgrense,f,Restriksjonsområder,Restriksjonsområder,f,Siidagrense,Siidagrense,f,Sikringstiltak,Sikringstiltak,f,Sivilforsvarsdistrikter,Sivilforsvarsdistrikter,f,Sjøkabler,Sjøkabler,f,Skredfaresoner,Skredfaresoner,f,Skredhendelser,Skredhendelser,t,Sommerbeite,Sommerbeite,t,Storulykkeanlegg,Storulykkeanlegg,t,Trafikkmengde,Trafikkmengde,t,Trafikkulykker,Trafikkulykker,f,Transformatorstasjoner,Transformatorstasjoner,f,Trollheimen,Trollheimen,f,Vanninntak,Vanninntak,f,Vannkraftverk,Vannkraftverk,f,Vannvei,Vannvei,f,Vassdragsområde,Vassdragsområde,f,Vbase,Vbase,f,Villreinområder,Villreinområder,t,Vinterbeite,Vinterbeite,t,Vårbeite,Vårbeite,t
    -> NullAttributeMapper_3
NullAttributeMapper_3
    ATTRCHOICE = All Attributes
    NULL_TREATMENT = New Value
    OTHER_VALUE = f
    NEW_VALUE = Nei
    -> NullAttributeMapper_4
NullAttributeMapper_4
    ATTRCHOICE = All Attributes
    NULL_TREATMENT = New Value
    OTHER_VALUE = t
    NEW_VALUE = Ja
    -> Norge (writer XLSXW2_1)

Bookmark: Metadatalink
Sampler_2
    RATE = 1
    SAMPLE_TYPE_LONG = First N Features
    SAMPLED -> AttributeRemover_2
AttributeRemover_2
    REMOVE_ATTRS = 110-sentraldistrikter,ABA (administrative enheter i Norge),Akvakultur,Anlegg farlig stoff,AR50,Arter av nasjonal forvaltningsinteresse,Avtaleområder,Beitehage,Brannsmitteområder,Brannstasjoner,Bygningspunkt fra matrikkelen,Dam,Delfelt vannkraft,Distriktskontor sivilforsvaret,Dybdekart innsjøer,Eiendomsflater fra matrikkelen,Eksplosivanlegg,Ekspropriasjonsområder,ELVIS Elvenett,ELVIS Hovedelv,FKB Adresse,FKB AR5,FKB Arealbruk,FKB Bane,FKB BygnAnlegg,FKB Bygning,FKB Bygningspunkt,FKB Høydekurve,FKB Høydekurve 5m,FKB Ledning,FKB LedningVa,FKB Lufthavn,FKB Matrikkelkart DEKTeig,FKB Naturinfo,FKB PblTiltak,FKB Servitutt,FKB Tekst1000,FKB Tekst5000,FKB TraktorvegSti,FKB Vann,FKB Vbase,FKB Veg,Flomsonekartplan,Flomsoner 10,Flomsoner 20,Flomsoner 50,Flomsoner 100,Flomsoner 200,Flomsoner 200 i år 2100,Flomsoner 500,Flomsoner 1000,Flyttlei,Foreslåtte naturvernområder,Forurenset grunn,Fredede bygninger,fylkeid,fylkesnavn,Hoved/biled,Høstbeite,Høstvinterbeite,id,Innsjødata,ISPS_havneanlegg,Jord - og flomskred aktsomhetsområder,Jordkvalitet,Kartlagte og verdsatte friluftsområder,kommuneid,kommunenavn,Konsesjonsområder,Konvensjonsområde,Korallrev,Kraftlinjer,Kraftverk, alle konsesjonsstadier,Kulturminne enkeltminner,Kulturminne kulturmiljø,Kulturminne lokaliteter,Kulturminne sikringssoner,Kvikkleire,Losbordingsfelt,Losstasjoner,Luftfartshindere,Løsmasser,Magasin,N50,N250,N500,N1000,N5000,Naturtyper i Norge - landskap,Naturvernområder,Nedbørfelt (REGINE),Norges maritime grenser,Områdekonsesjoner,Oppsamlingsområde,Planomriss,Reinbeitedistrikt,Reinbeiteområde,Reindriftsanlegg,Rendal renselskap,Restriksjonsgrense,Restriksjonsområder,Sentralt stedsnavnsregister,Siidagrense,Sikringstiltak,Sivilforsvarsdistrikter,Sjøkabler,Sjøkart raster,Skredfaresoner,Skredhendelser,Snø - og steinskred aktsomhetsområder,Snøskred aktsomhetsområder,Sommerbeite,Statlig sikra friluftsområder,Steinsprang aktsomhetsområder,Storulykkeanlegg,Støysoner flyplasser,Støysoner skytefelt,Tamreinlag (Filefjell, Fram, Vaga og Lom),Tette trehusmiljø,Totalnedbørfelt til målestasjon,Trafikkmengde,Trafikkulykker,Transformatorstasjoner,Trekklei,Trollheimen,Tur og friluftsruter,Universell utforming friluft,Universell utforming tettsted,Utvalgte naturtyper,Vanninntak,Vannkraftverk,Vannvei,Vassdragsområde,Vbase,Vegadresser fra matrikkelen,Verdifulle kulturlandskap,Verneplan for vassdrag,Viktige naturtyper,Villreinområder,Vindkraftverk - utbygd og vindkraftverk - konsesjon,Vindparkområder - utbygd og vindparkområder - konsesjon,Vindturbin - utbygd,Vinterbeite,Vårbeite
    -> AttributeCreator_2
AttributeCreator_2
    ATTR_LIST = Kommunenummer, ,Kommunenavn,Link Metadata
    -> AttributeRenamer_5
AttributeRenamer_5
    ATTR_LIST = ABA (administrative enheter i Norge),ABA (administrative enheter i Norge),FME_NULL_VALUE,Anlegg farlig stoff,Anlegg farlig stoff,https://kartkatalog.geonorge.no/metadata/uuid/12fa3360-ce91-4f02-82c8-22ff85cf0c67,Arter av nasjonal forvaltningsinteresse,Arter av nasjonal forvaltningsinteresse,https://kartkatalog.geonorge.no/metadata/uuid/a8456aed-441a-40c4-831f-46bcbe4e6ff1,Bygningspunkt fra matrikkelen,Bygningspunkt fra matrikkelen,FME_NULL_VALUE,Delfelt vannkraft,Delfelt vannkraft,FME_NULL_VALUE,Distriktskontor sivilforsvaret,Distriktskontor sivilforsvaret,https://kartkatalog.geonorge.no/metadata/uuid/44ecfa66-3d7e-4ace-a10a-fccb6961301c,Dybdekart innsjøer,Dybdekart innsjøer,https://kartkatalog.geonorge.no/metadata/uuid/9285f93e-d6d7-498c-a289-35700d795fc1,ELVIS Elvenett,ELVIS Elvenett,https://kartkatalog.geonorge.no/metadata/uuid/3f95a194-0968-4457-a500-912958de3d39,ELVIS Hovedelv,ELVIS Hovedelv,https://kartkatalog.geonorge.no/metadata/uuid/b2300e43-2a61-4e77-ab97-27567b2295e6,Eiendomsflater fra matrikkelen,Eiendomsflater fra matrikkelen,https://kartkatalog.geonorge.no/metadata/uuid/13336c7c-e150-4497-915a-281f3bd34a2e,FKB AR5,FKB AR5,https://kartkatalog.geonorge.no/metadata/uuid/166382b4-82d6-4ea9-a68e-6fd0c87bf788,FKB Adresse,FKB Adresse,FME_NULL_VALUE,FKB Arealbruk,FKB Arealbruk,https://kartkatalog.geonorge.no/metadata/uuid/87b31015-a3de-4540-9b8b-cb1bf4e1cb3a,FKB Bane,FKB Bane,https://kartkatalog.geonorge.no/metadata/uuid/3165138f-1461-44fe-8b10-eac44e08a10a,FKB BygnAnlegg,FKB BygnAnlegg,https://kartkatalog.geonorge.no/metadata/uuid/ede5ffb2-ee2a-44a3-852d-369a14d97f2e,FKB Bygning,FKB Bygning,https://kartkatalog.geonorge.no/metadata/uuid/8b4304ea-4fb0-479c-a24d-fa225e2c6e97,FKB Bygningspunkt,FKB Bygningspunkt,FME_NULL_VALUE,FKB Høydekurve 5m,FKB Høydekurve 5m,FME_NULL_VALUE,FKB Høydekurve,FKB Høydekurve,https://kartkatalog.geonorge.no/metadata/uuid/b49478fd-038e-4c2c-ae28-dda1958a8048,FKB Ledning,FKB Ledning,https://kartkatalog.geonorge.no/metadata/uuid/6e05aefb-f90e-4c7d-9fb9-299574d0bbf6,FKB LedningVa,FKB LedningVa,https://kartkatalog.geonorge.no/metadata/uuid/128248ad-f4f0-4543-901e-5e0c3bbaecfc,FKB Lufthavn,FKB Lufthavn,https://kartkatalog.geonorge.no/metadata/uuid/23dfcc33-fb04-4898-aa88-68b49c4bfea7,FKB Matrikkelkart DEKTeig,FKB Matrikkelkart DEKTeig,FME_NULL_VALUE,FKB Naturinfo,FKB Naturinfo,https://kartkatalog.geonorge.no/metadata/uuid/aa3c01f3-0678-470d-b03b-33085a7bae28,FKB PblTiltak,FKB PblTiltak,https://kartkatalog.geonorge.no/metadata/uuid/8944603c-9414-43a7-9421-9a1de9850a96,FKB Servitutt,FKB Servitutt,https://kartkatalog.geonorge.no/metadata/uuid/7e39afd2-5af6-435f-a859-5a86d136945b,FKB Tekst1000,FKB Tekst1000,https://kartkatalog.geonorge.no/metadata/uuid/9bc229df-3f97-476e-9fb2-093793356f9a,FKB Tekst5000,FKB Tekst5000,https://kartkatalog.geonorge.no/metadata/uuid/42104679-7712-45e5-b09d-8a99967ae060,FKB TraktorvegSti,FKB TraktorvegSti,https://kartkatalog.geonorge.no/metadata/uuid/cc3a2d98-52ac-4699-9947-ed0625903de4,FKB Vann,FKB Vann,https://kartkatalog.geonorge.no/metadata/uuid/595e47d9-d201-479c-a77d-cbc1f573a76b,FKB Vbase,FKB Vbase,FME_NULL_VALUE,FKB Veg,FKB Veg,https://kartkatalog.geonorge.no/metadata/uuid/4920b452-75cc-45f2-964c-3378204c3517,Flomsoner 10,Flomsoner 10,https://kartkatalog.geonorge.no/metadata/uuid/e95008fc-0945-4d66-8bc9-e50ab3f50401,Flomsoner 100,Flomsoner 100,https://kartkatalog.geonorge.no/metadata/uuid/e95008fc-0945-4d66-8bc9-e50ab3f50401,Flomsoner 1000,Flomsoner 1000,https://kartkatalog.geonorge.no/metadata/uuid/e95008fc-0945-4d66-8bc9-e50ab3f50401,Flomsoner 20,Flomsoner 20,https://kartkatalog.geonorge.no/metadata/uuid/e95008fc-0945-4d66-8bc9-e50ab3f50401,Flomsoner 200 i år 2100,Flomsoner 200 i år 2100,https://kartkatalog.geonorge.no/metadata/uuid/e95008fc-0945-4d66-8bc9-e50ab3f50401,Flomsoner 200,Flomsoner 200,https://kartkatalog.geonorge.no/metadata/uuid/e95008fc-0945-4d66-8bc9-e50ab3f50401,Flomsoner 50,Flomsoner 50,https://kartkatalog.geonorge.no/metadata/uuid/e95008fc-0945-4d66-8bc9-e50ab3f50401,Flomsoner 500,Flomsoner 500,https://kartkatalog.geonorge.no/metadata/uuid/e95008fc-0945-4d66-8bc9-e50ab3f50401,Foreslåtte naturvernområder,Foreslåtte naturvernområder,https://kartkatalog.geonorge.no/metadata/uuid/0e7eb17f-35ef-46d3-a465-3112d8bb2b5e,Forurenset grunn,Forurenset grunn,https://kartkatalog.geonorge.no/metadata/uuid/e48e71ac-16fc-4e47-9e7f-c0a4a4bbfad0,Fredede bygninger,Fredede bygninger,https://kartkatalog.geonorge.no/metadata/uuid/a4bfd879-120f-490e-9907-68ba870664b1,Grus og pukk,Grus og pukk,https://kartkatalog.geonorge.no/metadata/uuid/a26e57bc-15bd-46db-8504-6c6ed1e7c501,ISPS havneanlegg,ISPS havneanlegg,https://kartkatalog.geonorge.no/metadata/uuid/dc9b4d63-8597-4971-92a4-9f665abc3e21,Jord - og flomskred aktsomhetsområder,Jord - og flomskred aktsomhetsområder,https://kartkatalog.geonorge.no/metadata/uuid/30e1883e-70e9-4510-9e97-00edbdcddc02,Kartlagte og verdsatte friluftsområder,Kartlagte og verdsatte friluftsområder,https://kartkatalog.geonorge.no/metadata/uuid/91e31bb7-356f-4478-bcba-d5c2de6e91bc,Konsesjonsområder ,Konsesjonsområder,FME_NULL_VALUE,Kraftverk, alle konsesjonsstadier,Kraftverk, alle konsesjonsstadier,FME_NULL_VALUE,Kulturminne enkeltminner,Kulturminne enkeltminner,https://kartkatalog.geonorge.no/metadata/uuid/17150d2c-b50d-4792-80f4-0cb2ec5eaa79,Kulturminne kulturmiljø,Kulturminne kulturmiljø,https://kartkatalog.geonorge.no/metadata/uuid/17adbcac-bbb2-4efc-ab51-756573c8f178,Kulturminne lokaliteter,Kulturminne lokaliteter,https://kartkatalog.geonorge.no/metadata/uuid/c6896f24-71f9-4203-9b6f-faf3bfe1f5ed,Kulturminne sikringssoner,Kulturminne sikringssoner,https://kartkatalog.geonorge.no/metadata/uuid/0a3251bb-2a50-45d3-8674-58bade2fe673,Marin grense,Marin grense,https://kartkatalog.geonorge.no/metadata/uuid/cf8ccec7-9505-4d84-94a9-eac9c69971d3,Naturtyper i Norge - landskap,Naturtyper i Norge - landskap,FME_NULL_VALUE,Nedbørfelt (REGINE),Nedbørfelt (REGINE),https://kartkatalog.geonorge.no/metadata/uuid/8721cdac-f959-4adc-9d54-d3b770e5fa1e,Norges maritime grenser,Norges maritime grenser,https://kartkatalog.geonorge.no/metadata/uuid/e106adf4-c9d8-4fce-a9b5-7886a4126d23,Radon aktsomhet,Radon aktsomhet,https://kartkatalog.geonorge.no/metadata/uuid/dc0605f3-2301-4abe-a91f-6da42464c281,Reinbeiteområde ,Reinbeiteområde,https://kartkatalog.geonorge.no/metadata/uuid/bc5e4c60-9292-4a30-8417-28a193ec4569,Rendal renselskap,Rendal renselskap,FME_NULL_VALUE,Sentralt stedsnavnsregister,Sentralt stedsnavnsregister,https://kartkatalog.geonorge.no/metadata/uuid/30caed2f-454e-44be-b5cc-26bb5c0110ca,Sjøkart raster,Sjøkart raster,https://kartkatalog.geonorge.no/metadata/uuid/09d3a23e-7652-4f15-8248-968afae350f5,Snø - og steinskred aktsomhetsområder,Snø - og steinskred aktsomhetsområder,https://kartkatalog.geonorge.no/metadata/uuid/b68212a2-ecb4-4733-8964-2882dc2ea363,Snøskred aktsomhetsområder,Snøskred aktsomhetsområder,https://kartkatalog.geonorge.no/metadata/uuid/e9542260-6315-4770-b085-86e95179f735,Statlig sikra friluftsområder,Statlig sikra friluftsområder,https://kartkatalog.geonorge.no/metadata/uuid/e08ad2cb-3262-4a78-bc58-2f3b5c5ccfd2,Steinsprang aktsomhetsområder,Steinsprang aktsomhetsområder,https://kartkatalog.geonorge.no/metadata/uuid/02c6d51c-4e8c-4948-a620-dc046c8cb747,Støysoner flyplasser,Støysoner flyplasser,https://kartkatalog.geonorge.no/metadata/uuid/1489f7f8-40c8-4dc4-83b6-bcf277b56506,Støysoner skytefelt,Støysoner skytefelt,https://kartkatalog.geonorge.no/metadata/uuid/21d93ab2-868f-4ef9-986b-bf362746f4bd,Tamreinlag (Filefjell, Fram, Vaga og Lom),Tamreinlag (Filefjell, Fram, Vaga og Lom),FME_NULL_VALUE,Tette trehusmiljø,Tette trehusmiljø,https://kartkatalog.geonorge.no/metadata/uuid/420a0af3-135c-49de-bd14-e4dec9c858db,Totalnedbørfelt til målestasjon,Totalnedbørfelt til målestasjon,FME_NULL_VALUE,Trekklei ,Trekklei,https://kartkatalog.geonorge.no/metadata/uuid/f9c1e228-892f-4f1a-9e4e-b6d6149f373c,Tur og friluftsruter,Tur og friluftsruter,https://kartkatalog.geonorge.no/metadata/uuid/d1422d17-6d95-4ef1-96ab-8af31744dd63,Universell utforming friluft,Universell utforming friluft,FME_NULL_VALUE,Universell utforming tettsted,Universell utforming tettsted,FME_NULL_VALUE,Utvalgte naturtyper,Utvalgte naturtyper,https://kartkatalog.geonorge.no/metadata/uuid/2c0072de-f702-401e-bfb3-5ad3d08d4c2d,Vegadresser fra matrikkelen,Vegadresser fra matrikkelen,FME_NULL_VALUE,Verdifulle kulturlandskap,Verdifulle kulturlandskap,https://kartkatalog.geonorge.no/metadata/uuid/a6368bed-4896-41d3-92aa-cc2b4261adc3,Verneplan for vassdrag,Verneplan for vassdrag,https://kartkatalog.geonorge.no/metadata/uuid/df5c70a1-e9cf-4b2c-bf9a-7dce453830cd,Viktige naturtyper,Viktige naturtyper,https://kartkatalog.geonorge.no/metadata/uuid/d776ff93-104d-4aa5-a8d9-276df01eb51c,Vindkraftverk - utbygd og vindkraftverk - konsesjon,Vindkraftverk - utbygd og vindkraftverk - konsesjon,https://kartkatalog.geonorge.no/metadata/uuid/ac249604-cd82-490c-83cc-9cd24fe18088,Vindparkområder - utbygd og vindparkområder - konsesjon,Vindparkområder - utbygd og vindparkområder - konsesjon,https://kartkatalog.geonorge.no/metadata/uuid/ac249604-cd82-490c-83cc-9cd24fe18088,Vindturbin - utbygd,Vindturbin - utbygd,https://kartkatalog.geonorge.no/metadata/uuid/ac249604-cd82-490c-83cc-9cd24fe18088,110-sentraldistrikter,110-sentraldistrikter,https://kartkatalog.geonorge.no/metadata/uuid/c4436a5f-1e22-461a-8209-786f7052acb5,AR50,AR50,https://kartkatalog.geonorge.no/metadata/uuid/d5ab0e04-421b-4a04-ba46-8921b57951b2,Akvakultur,Akvakultur,https://kartkatalog.geonorge.no/metadata/uuid/a33feac6-2c6f-4541-babd-290db1fe8a68,Avtaleområder,Avtaleområder,FME_NULL_VALUE,Beitehage,Beitehage,https://kartkatalog.geonorge.no/metadata/uuid/df2db95d-adbc-4807-bb46-00b729caed7c,Brannsmitteområder,Brannsmitteområder,https://kartkatalog.geonorge.no/metadata/uuid/e10028c8-e044-41dc-9e25-ec27df5f9be7,Brannstasjoner,Brannstasjoner,https://kartkatalog.geonorge.no/metadata/uuid/0ccce81d-a72e-46ca-8bd9-57b362376485,Dam,Dam,FME_NULL_VALUE,Eksplosivanlegg,Eksplosivanlegg,https://kartkatalog.geonorge.no/metadata/uuid/ceef6c79-27ea-4e3e-895d-33d2a64763bf,Ekspropriasjonsområder,Ekspropriasjonsområder,FME_NULL_VALUE,Flomsonekartplan,Flomsonekartplan,https://kartkatalog.geonorge.no/metadata/uuid/e95008fc-0945-4d66-8bc9-e50ab3f50401,Flyttlei,Flyttlei,https://kartkatalog.geonorge.no/metadata/uuid/f9c1e228-892f-4f1a-9e4e-b6d6149f373c,Grunnvannsborehull,Grunnvannsborehull,https://kartkatalog.geonorge.no/metadata/uuid/82cd33ef-52dd-4c83-b2d6-e55a0941b33b,Hoved/biled,Hoved/biled,https://kartkatalog.geonorge.no/metadata/uuid/8ff1538a-a93c-4391-8d6f-3555fc37819c,Høstbeite,Høstbeite,FME_NULL_VALUE,Høstvinterbeite,Høstvinterbeite,https://kartkatalog.geonorge.no/metadata/uuid/85a4c5e3-25ab-427c-b664-bbac2d0c9e79,Innsjødata,Innsjødata,https://kartkatalog.geonorge.no/metadata/uuid/823b8639-9a49-41bf-8571-3608435eb149,Jordkvalitet,Jordkvalitet,https://kartkatalog.geonorge.no/metadata/uuid/112d6261-f649-4668-ab3a-8d6ed3fc63d9,Konvensjonsområde,Konvensjonsområde,FME_NULL_VALUE,Korallrev,Korallrev,https://kartkatalog.geonorge.no/metadata/uuid/7dce1e0c-7a70-442a-924a-0e29f6f526d3,Kraftlinjer,Kraftlinjer,FME_NULL_VALUE,Kvikkleire,Kvikkleire,https://kartkatalog.geonorge.no/metadata/uuid/a29b905c-6aaa-4283-ae2c-d167624c08a8,Losbordingsfelt,Losbordingsfelt,https://kartkatalog.geonorge.no/metadata/uuid/f0083871-0d21-44e2-945f-9de9ea94d484,Losstasjoner,Losstasjoner,FME_NULL_VALUE,Luftfartshindere,Luftfartshindere,https://kartkatalog.geonorge.no/metadata/uuid/28c896d0-8a0d-4209-bf31-4931033b1082,Løsmasser,Løsmasser,https://kartkatalog.geonorge.no/metadata/uuid/3de4ddf6-d6b8-4398-8222-f5c47791a757,Magasin,Magasin,https://kartkatalog.geonorge.no/metadata/uuid/5d13cd67-dc03-458d-8715-548bafbeb2c1,Mineralressurser,Mineralressurser,https://kartkatalog.geonorge.no/metadata/uuid/378d5f88-de1f-4d1e-b99a-7b0f0dd52951,N1000,N1000,https://kartkatalog.geonorge.no/metadata/uuid/aee42bb6-d0e9-4d70-86fe-6ea76c381055,N250,N250,https://kartkatalog.geonorge.no/metadata/uuid/442cae64-b447-478d-b384-545bc1d9ab48,N50,N50,https://kartkatalog.geonorge.no/metadata/uuid/ea192681-d039-42ec-b1bc-f3ce04c189ac,N500,N500,https://kartkatalog.geonorge.no/metadata/uuid/58e0dbf8-0d47-47c8-8086-107a3fa2dfa4,N5000,N5000,https://kartkatalog.geonorge.no/metadata/uuid/c777d53d-8916-4d9d-bae4-6d5140e0c569,Naturvernområder,Naturvernområder,https://kartkatalog.geonorge.no/metadata/uuid/5857ec0a-8d2c-4cd8-baa2-0dc54ae213b4,Områdekonsesjoner,Områdekonsesjoner,FME_NULL_VALUE,Oppsamlingsområde,Oppsamlingsområde,https://kartkatalog.geonorge.no/metadata/uuid/f9c1e228-892f-4f1a-9e4e-b6d6149f373c,Planomriss,Planomriss,FME_NULL_VALUE,Reinbeitedistrikt,Reinbeitedistrikt,https://kartkatalog.geonorge.no/metadata/uuid/6bfec384-92cf-44d3-863b-0187afa06658,Reindriftsanlegg,Reindriftsanlegg,https://kartkatalog.geonorge.no/metadata/uuid/8dfa67c5-3099-4353-9ce0-72f9ebd44a2c,Restriksjonsgrense,Restriksjonsgrense,FME_NULL_VALUE,Restriksjonsområder,Restriksjonsområder,FME_NULL_VALUE,Siidagrense,Siidagrense,https://kartkatalog.geonorge.no/metadata/uuid/00828ff6-b1e4-4916-9d65-50199e293c1e,Sikringstiltak,Sikringstiltak,https://kartkatalog.geonorge.no/metadata/uuid/bc27d7aa-afaf-43c2-802f-6a47f792b2aa,Sivilforsvarsdistrikter,Sivilforsvarsdistrikter,https://kartkatalog.geonorge.no/metadata/uuid/44ecfa66-3d7e-4ace-a10a-fccb6961301c,Sjøkabler,Sjøkabler,FME_NULL_VALUE,Skredfaresoner,Skredfaresoner,https://kartkatalog.geonorge.no/metadata/uuid/b2d5aaf8-79ac-40f3-9cd6-fdc30bc42ea1,Skredhendelser,Skredhendelser,https://kartkatalog.geonorge.no/metadata/uuid/de19fbbf-3734-47a0-89f5-6c5769071cdd,Sommerbeite,Sommerbeite,https://kartkatalog.geonorge.no/metadata/uuid/d5d1e2d4-7dc0-47ce-8776-ff64b07d788e,Storulykkeanlegg,Storulykkeanlegg,https://kartkatalog.geonorge.no/metadata/uuid/63190f80-8692-492a-8e7a-b2cb0a59d27a,Trafikkmengde,Trafikkmengde,https://kartkatalog.geonorge.no/metadata/uuid/af2c4a0a-1978-4e62-b08d-ed1f36bd5023,Trafikkulykker,Trafikkulykker,FME_NULL_VALUE,Transformatorstasjoner,Transformatorstasjoner,FME_NULL_VALUE,Trollheimen,Trollheimen,FME_NULL_VALUE,Vanninntak,Vanninntak,FME_NULL_VALUE,Vannkraftverk,Vannkraftverk,https://kartkatalog.geonorge.no/metadata/uuid/a9a17e54-de1f-49e0-9c4e-8311abb4781a,Vannvei,Vannvei,https://kartkatalog.geonorge.no/metadata/uuid/1dc3a086-cdf8-4791-86d8-159123437315,Vassdragsområde,Vassdragsområde,https://kartkatalog.geonorge.no/metadata/uuid/390afc10-ea03-46b0-821e-fad606a99a7f,Vbase,Vbase,FME_NULL_VALUE,Villreinområder,Villreinområder,https://kartkatalog.geonorge.no/metadata/uuid/fc59e9a4-59df-4eb3-978a-1c173b84bf4e,Vinterbeite,Vinterbeite,https://kartkatalog.geonorge.no/metadata/uuid/63f655ef-f625-43cf-a512-bb8164bf53a4,Vårbeite,Vårbeite,https://kartkatalog.geonorge.no/metadata/uuid/fa02a652-cd6d-4828-9fb5-7bd4515aa6d0
    -> Norge (writer XLSXW2_1)
