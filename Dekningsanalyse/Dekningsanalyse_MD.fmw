FME workspace Dekningsanalyse_MD.fmw

Parameters:
- SourceDataset_POSTGIS = geonortst@nnridb504:5432/geonor01tst   # Connection
- DestDataset_POSTGIS = geonortst@nnridb504:5432/geonor01tst   # Connection
- SourceDataset_SHAPE_3 = ""$(FME_MF_DIR)Temp_data\MD\arter_nasj_for_int.shp" "$(FME_MF_DIR)Temp_data\MD\Fril_kartlverd.shp" "$(FME_MF_DIR)Temp_data\MD\Fril_statligsikra.shp" "$(FME_MF_DIR)Temp_data\MD\GF_lokalitet.shp" "$(FME_MF_DIR)Temp_data\MD\Naturnvernomr.shp" "$(FME_MF_DIR)Temp_data\MD\Naturnvernomr_foreslaatt.shp" "$(FME_MF_DIR)Temp_data\MD\naturt_i_norge_landskap.shp" "$(FME_MF_DIR)Temp_data\MD\naturt_utvalgte.shp" "$(FME_MF_DIR)Temp_data\MD\Verdifulle_kulturlandskap.shp" "$(FME_MF_DIR)Temp_data\MD\Viktige_naturtyper.shp" "$(FME_MF_DIR)Temp_data\MD\Villreinomrader.shp""   # Source Esri Shape File(s)

Readers:
- POSTGIS_1: POSTGIS from $(SourceDataset_POSTGIS)
- SHAPE_1: SHAPE from $(SourceDataset_SHAPE_3)

Writers:
- POSTGIS_2: POSTGIS to $(DestDataset_POSTGIS)

admingrense.kommuneflate (reader POSTGIS_1)
    attributes: kommuneid int4
    -> Deaggregator
Deaggregator
    GEOM_NAME_FIELD = _geometry_name
    SPLIT_COMPOSITES = No
    EXPLODE_INSTANCES = No
    MODE = Flatten One Level
    PART_NUMBER_FIELD = _part_number
    LIST_ATTR_MODE_LOOKUP = LEAN
    DEAGGREGATED -> GeometryCoercer
GeometryCoercer
    GQUERY:
      for $geom in //geometry
      where $geom/count(parent::geometry) = 0
      return number($geom/@fme_id)
    KIND = fme_polygon
    COERCED -> SpatialFilter_2 [input 2]
    UNTOUCHED -> SpatialFilter_2 [input 2]
    UNTOUCHED -> SpatialFilter_3 [input 2]
    COERCED -> SpatialFilter_3 [input 2]
    UNTOUCHED -> SpatialFilter_4 [input 2]
    COERCED -> SpatialFilter_4 [input 2]
    UNTOUCHED -> SpatialFilter_5 [input 2]
    COERCED -> SpatialFilter_5 [input 2]
    UNTOUCHED -> SpatialFilter_6 [input 2]
    COERCED -> SpatialFilter_6 [input 2]
    UNTOUCHED -> SpatialFilter_7 [input 2]
    COERCED -> SpatialFilter_7 [input 2]
    UNTOUCHED -> SpatialFilter_8 [input 2]
    COERCED -> SpatialFilter_8 [input 2]
    UNTOUCHED -> SpatialFilter_9 [input 2]
    COERCED -> SpatialFilter_9 [input 2]
    COERCED -> SpatialFilter_10 [input 2]
    UNTOUCHED -> SpatialFilter_10 [input 2]
    COERCED -> SpatialFilter_11 [input 2]
    UNTOUCHED -> SpatialFilter_11 [input 2]
    UNTOUCHED -> SpatialFilter_12 [input 2]
    COERCED -> SpatialFilter_12 [input 2]
GF_lokalitet (reader SHAPE_1)
    attributes: _match_id char(200)
    -> Reprojector_12
Reprojector_12
    INTERPOLATION_TYPE_NAME = Nearest Neighbor
    SOURCE = Read from feature
    RASTER_CELL_SIZE = Preserve Cells
    DEST = EPSG:4258
    REPROJECTED -> Deaggregator_12
Deaggregator_12
    COPY_ATTR = Every Node
    GEOM_NAME_FIELD = _geometry_name
    SPLIT_COMPOSITES = No
    EXPLODE_INSTANCES = No
    ID_SELECTION = ID and Parent ID
    CHILD_ID_ATTR = _hierarchy_child_id_list
    PARENT_ID_ATTR = _hierarchy_parent_id
    ID_ATTR = _hierarchy_id
    MODE = Flatten One Level
    PART_NUMBER_FIELD = _part_number
    LIST_ATTR_MODE_LOOKUP = LEAN
    DEAGGREGATED -> SpatialFilter_12 [input 1]
SpatialFilter_12
    MERGE_ATTRS = Yes
    BASE_TYPE = Multiple Filters
    CURVE_BOUNDARY_RULE_PARAM = Default Rule
    USE_BOUNDING_BOX = No
    PREDICATE_VALUE = Intersects
    PREDATTR = _predicate
    PASS_CRITERIA = Pass Against One Filter
    PASSED -> AttributeCreator_22
    FAILED -> AttributeCreator_23
AttributeCreator_22
    ATTR_LIST = md_forurensetgrunn,1
    -> dekningsoversikt.dekningsoversikt (writer POSTGIS_2)
AttributeCreator_23
    ATTR_LIST = md_forurensetgrunn,0
    -> dekningsoversikt.dekningsoversikt (writer POSTGIS_2)
Naturnvernomr_foreslaatt (reader SHAPE_1)
    attributes: _match_id char(200)
    -> Reprojector_2
Reprojector_2
    INTERPOLATION_TYPE_NAME = Nearest Neighbor
    SOURCE = Read from feature
    RASTER_CELL_SIZE = Preserve Cells
    DEST = EPSG:4258
    REPROJECTED -> Deaggregator_2
Deaggregator_2
    COPY_ATTR = Every Node
    GEOM_NAME_FIELD = _geometry_name
    SPLIT_COMPOSITES = No
    EXPLODE_INSTANCES = No
    ID_SELECTION = ID and Parent ID
    CHILD_ID_ATTR = _hierarchy_child_id_list
    PARENT_ID_ATTR = _hierarchy_parent_id
    ID_ATTR = _hierarchy_id
    MODE = Flatten One Level
    PART_NUMBER_FIELD = _part_number
    LIST_ATTR_MODE_LOOKUP = LEAN
    DEAGGREGATED -> SpatialFilter_2 [input 1]
SpatialFilter_2
    MERGE_ATTRS = Yes
    BASE_TYPE = Multiple Filters
    CURVE_BOUNDARY_RULE_PARAM = Default Rule
    USE_BOUNDING_BOX = No
    PREDICATE_VALUE = Intersects
    PREDATTR = _predicate
    PASS_CRITERIA = Pass Against One Filter
    PASSED -> AttributeCreator_2
    FAILED -> AttributeCreator_3
AttributeCreator_2
    ATTR_LIST = md_naturvernomr_foresl,1
    -> dekningsoversikt.dekningsoversikt (writer POSTGIS_2)
AttributeCreator_3
    ATTR_LIST = md_naturvernomr_foresl,0
    -> dekningsoversikt.dekningsoversikt (writer POSTGIS_2)
Verdifulle_kulturlandskap (reader SHAPE_1)
    attributes: _match_id char(200)
    -> Reprojector_3
Reprojector_3
    INTERPOLATION_TYPE_NAME = Nearest Neighbor
    SOURCE = Read from feature
    RASTER_CELL_SIZE = Preserve Cells
    DEST = EPSG:4258
    REPROJECTED -> Deaggregator_3
Deaggregator_3
    COPY_ATTR = Every Node
    GEOM_NAME_FIELD = _geometry_name
    SPLIT_COMPOSITES = No
    EXPLODE_INSTANCES = No
    ID_SELECTION = ID and Parent ID
    CHILD_ID_ATTR = _hierarchy_child_id_list
    PARENT_ID_ATTR = _hierarchy_parent_id
    ID_ATTR = _hierarchy_id
    MODE = Flatten One Level
    PART_NUMBER_FIELD = _part_number
    LIST_ATTR_MODE_LOOKUP = LEAN
    DEAGGREGATED -> SpatialFilter_3 [input 1]
SpatialFilter_3
    MERGE_ATTRS = Yes
    BASE_TYPE = Multiple Filters
    CURVE_BOUNDARY_RULE_PARAM = Default Rule
    USE_BOUNDING_BOX = No
    PREDICATE_VALUE = Intersects
    PREDATTR = _predicate
    PASS_CRITERIA = Pass Against One Filter
    PASSED -> AttributeCreator_4
    FAILED -> AttributeCreator_5
AttributeCreator_4
    ATTR_LIST = md_verdif_kulturlandsk,1
    -> dekningsoversikt.dekningsoversikt (writer POSTGIS_2)
AttributeCreator_5
    ATTR_LIST = md_verdif_kulturlandsk,0
    -> dekningsoversikt.dekningsoversikt (writer POSTGIS_2)
Viktige_naturtyper (reader SHAPE_1)
    attributes: _match_id char(200)
    -> Reprojector_4
Reprojector_4
    INTERPOLATION_TYPE_NAME = Nearest Neighbor
    SOURCE = Read from feature
    RASTER_CELL_SIZE = Preserve Cells
    DEST = EPSG:4258
    REPROJECTED -> Deaggregator_4
Deaggregator_4
    COPY_ATTR = Every Node
    GEOM_NAME_FIELD = _geometry_name
    SPLIT_COMPOSITES = No
    EXPLODE_INSTANCES = No
    ID_SELECTION = ID and Parent ID
    CHILD_ID_ATTR = _hierarchy_child_id_list
    PARENT_ID_ATTR = _hierarchy_parent_id
    ID_ATTR = _hierarchy_id
    MODE = Flatten One Level
    PART_NUMBER_FIELD = _part_number
    LIST_ATTR_MODE_LOOKUP = LEAN
    DEAGGREGATED -> SpatialFilter_4 [input 1]
SpatialFilter_4
    MERGE_ATTRS = Yes
    BASE_TYPE = Multiple Filters
    CURVE_BOUNDARY_RULE_PARAM = Default Rule
    USE_BOUNDING_BOX = No
    PREDICATE_VALUE = Intersects
    PREDATTR = _predicate
    PASS_CRITERIA = Pass Against One Filter
    PASSED -> AttributeCreator_6
    FAILED -> AttributeCreator_7
AttributeCreator_6
    ATTR_LIST = md_viktige_naturt,1
    -> dekningsoversikt.dekningsoversikt (writer POSTGIS_2)
AttributeCreator_7
    ATTR_LIST = md_viktige_naturt,0
    -> dekningsoversikt.dekningsoversikt (writer POSTGIS_2)
Fril_kartlverd (reader SHAPE_1)
    attributes: _match_id char(200)
    -> Reprojector_5
Reprojector_5
    INTERPOLATION_TYPE_NAME = Nearest Neighbor
    SOURCE = Read from feature
    RASTER_CELL_SIZE = Preserve Cells
    DEST = EPSG:4258
    REPROJECTED -> Deaggregator_5
Deaggregator_5
    COPY_ATTR = Every Node
    GEOM_NAME_FIELD = _geometry_name
    SPLIT_COMPOSITES = No
    EXPLODE_INSTANCES = No
    ID_SELECTION = ID and Parent ID
    CHILD_ID_ATTR = _hierarchy_child_id_list
    PARENT_ID_ATTR = _hierarchy_parent_id
    ID_ATTR = _hierarchy_id
    MODE = Flatten One Level
    PART_NUMBER_FIELD = _part_number
    LIST_ATTR_MODE_LOOKUP = LEAN
    DEAGGREGATED -> SpatialFilter_5 [input 1]
SpatialFilter_5
    MERGE_ATTRS = Yes
    BASE_TYPE = Multiple Filters
    CURVE_BOUNDARY_RULE_PARAM = Default Rule
    USE_BOUNDING_BOX = No
    PREDICATE_VALUE = Intersects
    PREDATTR = _predicate
    PASS_CRITERIA = Pass Against One Filter
    PASSED -> AttributeCreator_8
    FAILED -> AttributeCreator_9
AttributeCreator_8
    ATTR_LIST = md_frilkartlverds,1
    -> dekningsoversikt.dekningsoversikt (writer POSTGIS_2)
AttributeCreator_9
    ATTR_LIST = md_frilkartlverds,0
    -> dekningsoversikt.dekningsoversikt (writer POSTGIS_2)
Villreinomrader (reader SHAPE_1)
    attributes: _match_id char(200)
    -> Reprojector_6
Reprojector_6
    INTERPOLATION_TYPE_NAME = Nearest Neighbor
    SOURCE = Read from feature
    RASTER_CELL_SIZE = Preserve Cells
    DEST = EPSG:4258
    REPROJECTED -> Deaggregator_6
Deaggregator_6
    COPY_ATTR = Every Node
    GEOM_NAME_FIELD = _geometry_name
    SPLIT_COMPOSITES = No
    EXPLODE_INSTANCES = No
    ID_SELECTION = ID and Parent ID
    CHILD_ID_ATTR = _hierarchy_child_id_list
    PARENT_ID_ATTR = _hierarchy_parent_id
    ID_ATTR = _hierarchy_id
    MODE = Flatten One Level
    PART_NUMBER_FIELD = _part_number
    LIST_ATTR_MODE_LOOKUP = LEAN
    DEAGGREGATED -> SpatialFilter_6 [input 1]
SpatialFilter_6
    MERGE_ATTRS = Yes
    BASE_TYPE = Multiple Filters
    CURVE_BOUNDARY_RULE_PARAM = Default Rule
    USE_BOUNDING_BOX = No
    PREDICATE_VALUE = Intersects
    PREDATTR = _predicate
    PASS_CRITERIA = Pass Against One Filter
    PASSED -> AttributeCreator_10
    FAILED -> AttributeCreator_11
AttributeCreator_10
    ATTR_LIST = md_villreinomr,1
    -> dekningsoversikt.dekningsoversikt (writer POSTGIS_2)
AttributeCreator_11
    ATTR_LIST = md_villreinomr,0
    -> dekningsoversikt.dekningsoversikt (writer POSTGIS_2)
Naturnvernomr (reader SHAPE_1)
    attributes: _match_id char(200)
    -> Reprojector_7
Reprojector_7
    INTERPOLATION_TYPE_NAME = Nearest Neighbor
    SOURCE = Read from feature
    RASTER_CELL_SIZE = Preserve Cells
    DEST = EPSG:4258
    REPROJECTED -> Deaggregator_7
Deaggregator_7
    COPY_ATTR = Every Node
    GEOM_NAME_FIELD = _geometry_name
    SPLIT_COMPOSITES = No
    EXPLODE_INSTANCES = No
    ID_SELECTION = ID and Parent ID
    CHILD_ID_ATTR = _hierarchy_child_id_list
    PARENT_ID_ATTR = _hierarchy_parent_id
    ID_ATTR = _hierarchy_id
    MODE = Flatten One Level
    PART_NUMBER_FIELD = _part_number
    LIST_ATTR_MODE_LOOKUP = LEAN
    DEAGGREGATED -> SpatialFilter_7 [input 1]
SpatialFilter_7
    MERGE_ATTRS = Yes
    BASE_TYPE = Multiple Filters
    CURVE_BOUNDARY_RULE_PARAM = Default Rule
    USE_BOUNDING_BOX = No
    PREDICATE_VALUE = Intersects
    PREDATTR = _predicate
    PASS_CRITERIA = Pass Against One Filter
    PASSED -> AttributeCreator_12
    FAILED -> AttributeCreator_13
AttributeCreator_12
    ATTR_LIST = md_naturvernomr,1
    -> dekningsoversikt.dekningsoversikt (writer POSTGIS_2)
AttributeCreator_13
    ATTR_LIST = md_naturvernomr,0
    -> dekningsoversikt.dekningsoversikt (writer POSTGIS_2)
arter_nasj_for_int (reader SHAPE_1)
    attributes: _match_id char(200)
    -> Reprojector_8
Reprojector_8
    INTERPOLATION_TYPE_NAME = Nearest Neighbor
    SOURCE = Read from feature
    RASTER_CELL_SIZE = Preserve Cells
    DEST = EPSG:4258
    REPROJECTED -> Deaggregator_8
Deaggregator_8
    COPY_ATTR = Every Node
    GEOM_NAME_FIELD = _geometry_name
    SPLIT_COMPOSITES = No
    EXPLODE_INSTANCES = No
    ID_SELECTION = ID and Parent ID
    CHILD_ID_ATTR = _hierarchy_child_id_list
    PARENT_ID_ATTR = _hierarchy_parent_id
    ID_ATTR = _hierarchy_id
    MODE = Flatten One Level
    PART_NUMBER_FIELD = _part_number
    LIST_ATTR_MODE_LOOKUP = LEAN
    DEAGGREGATED -> SpatialFilter_8 [input 1]
SpatialFilter_8
    MERGE_ATTRS = Yes
    BASE_TYPE = Multiple Filters
    CURVE_BOUNDARY_RULE_PARAM = Default Rule
    USE_BOUNDING_BOX = No
    PREDICATE_VALUE = Intersects
    PREDATTR = _predicate
    PASS_CRITERIA = Pass Against One Filter
    PASSED -> AttributeCreator_14
    FAILED -> AttributeCreator_15
AttributeCreator_14
    ATTR_LIST = md_arter_nasjon_forv,1
    -> dekningsoversikt.dekningsoversikt (writer POSTGIS_2)
AttributeCreator_15
    ATTR_LIST = md_arter_nasjon_forv,0
    -> dekningsoversikt.dekningsoversikt (writer POSTGIS_2)
naturt_i_norge_landskap (reader SHAPE_1)
    attributes: _match_id char(200)
    -> Reprojector_9
Reprojector_9
    INTERPOLATION_TYPE_NAME = Nearest Neighbor
    SOURCE = Read from feature
    RASTER_CELL_SIZE = Preserve Cells
    DEST = EPSG:4258
    REPROJECTED -> Deaggregator_9
Deaggregator_9
    COPY_ATTR = Every Node
    GEOM_NAME_FIELD = _geometry_name
    SPLIT_COMPOSITES = No
    EXPLODE_INSTANCES = No
    ID_SELECTION = ID and Parent ID
    CHILD_ID_ATTR = _hierarchy_child_id_list
    PARENT_ID_ATTR = _hierarchy_parent_id
    ID_ATTR = _hierarchy_id
    MODE = Flatten One Level
    PART_NUMBER_FIELD = _part_number
    LIST_ATTR_MODE_LOOKUP = LEAN
    DEAGGREGATED -> SpatialFilter_9 [input 1]
SpatialFilter_9
    MERGE_ATTRS = Yes
    BASE_TYPE = Multiple Filters
    CURVE_BOUNDARY_RULE_PARAM = Default Rule
    USE_BOUNDING_BOX = No
    PREDICATE_VALUE = Intersects
    PREDATTR = _predicate
    PASS_CRITERIA = Pass Against One Filter
    PASSED -> AttributeCreator_16
    FAILED -> AttributeCreator_17
AttributeCreator_16
    ATTR_LIST = md_naturt_landskap,1
    -> dekningsoversikt.dekningsoversikt (writer POSTGIS_2)
AttributeCreator_17
    ATTR_LIST = md_naturt_landskap,0
    -> dekningsoversikt.dekningsoversikt (writer POSTGIS_2)
naturt_utvalgte (reader SHAPE_1)
    attributes: _match_id char(200)
    -> Reprojector_10
Reprojector_10
    INTERPOLATION_TYPE_NAME = Nearest Neighbor
    SOURCE = Read from feature
    RASTER_CELL_SIZE = Preserve Cells
    DEST = EPSG:4258
    REPROJECTED -> Deaggregator_10
Deaggregator_10
    COPY_ATTR = Every Node
    GEOM_NAME_FIELD = _geometry_name
    SPLIT_COMPOSITES = No
    EXPLODE_INSTANCES = No
    ID_SELECTION = ID and Parent ID
    CHILD_ID_ATTR = _hierarchy_child_id_list
    PARENT_ID_ATTR = _hierarchy_parent_id
    ID_ATTR = _hierarchy_id
    MODE = Flatten One Level
    PART_NUMBER_FIELD = _part_number
    LIST_ATTR_MODE_LOOKUP = LEAN
    DEAGGREGATED -> SpatialFilter_10 [input 1]
SpatialFilter_10
    MERGE_ATTRS = Yes
    BASE_TYPE = Multiple Filters
    CURVE_BOUNDARY_RULE_PARAM = Default Rule
    USE_BOUNDING_BOX = No
    PREDICATE_VALUE = Intersects
    PREDATTR = _predicate
    PASS_CRITERIA = Pass Against One Filter
    PASSED -> AttributeCreator_18
    FAILED -> AttributeCreator_19
AttributeCreator_18
    ATTR_LIST = md_naturt_utv,1
    -> dekningsoversikt.dekningsoversikt (writer POSTGIS_2)
AttributeCreator_19
    ATTR_LIST = md_naturt_utv,0
    -> dekningsoversikt.dekningsoversikt (writer POSTGIS_2)
Fril_statligsikra (reader SHAPE_1)
    attributes: _match_id char(200)
    -> Reprojector_11
Reprojector_11
    INTERPOLATION_TYPE_NAME = Nearest Neighbor
    SOURCE = Read from feature
    RASTER_CELL_SIZE = Preserve Cells
    DEST = EPSG:4258
    REPROJECTED -> Deaggregator_11
Deaggregator_11
    COPY_ATTR = Every Node
    GEOM_NAME_FIELD = _geometry_name
    SPLIT_COMPOSITES = No
    EXPLODE_INSTANCES = No
    ID_SELECTION = ID and Parent ID
    CHILD_ID_ATTR = _hierarchy_child_id_list
    PARENT_ID_ATTR = _hierarchy_parent_id
    ID_ATTR = _hierarchy_id
    MODE = Flatten One Level
    PART_NUMBER_FIELD = _part_number
    LIST_ATTR_MODE_LOOKUP = LEAN
    DEAGGREGATED -> SpatialFilter_11 [input 1]
SpatialFilter_11
    MERGE_ATTRS = Yes
    BASE_TYPE = Multiple Filters
    CURVE_BOUNDARY_RULE_PARAM = Default Rule
    USE_BOUNDING_BOX = No
    PREDICATE_VALUE = Intersects
    PREDATTR = _predicate
    PASS_CRITERIA = Pass Against One Filter
    PASSED -> AttributeCreator_20
    FAILED -> AttributeCreator_21
AttributeCreator_20
    ATTR_LIST = md_frilstatligsikra,1
    -> dekningsoversikt.dekningsoversikt (writer POSTGIS_2)
AttributeCreator_21
    ATTR_LIST = md_frilstatligsikra,0
    -> dekningsoversikt.dekningsoversikt (writer POSTGIS_2)
dekningsoversikt.dekningsoversikt (writer POSTGIS_2)
    attributes: kommuneid int4, akvakultur bool, korallrev bool, dsb_110sentral bool, dsb_brannstasjon bool, dsb_distrkont_siv bool, dsb_sivforsvdistr bool, ra_brannsmitteomr bool, ra_tettetrehusm bool, ra_frededebygg bool, ra_enkeltminner bool, ra_kulturmiljo bool, ra_lokaliteter bool, ra_sikringssoner bool, kv_hovedbiled bool, kv_ispshavneanlegg bool, kv_losbordingsfelt bool, kv_losstasjoner bool, nve_flomsoner10 bool, nve_flomsoner20 bool, nve_flomsoner50 bool, nve_flomsoner100 bool, nve_flomsoner200 bool, nve_flomsoner500 bool, nve_flomsoner1000 bool, nve_flomsoner200_i_aar2100 bool, nve_flomsonekartplan bool, nve_elvis_hovedelv bool, nve_elvis_elvenett bool, nve_innsjodata bool,
      nve_dybdekart bool, nve_nedborfelt_regine bool, nve_vassdragsomrade bool, nve_totnedbfelt_mstasjon bool, nve_vannkraftverk bool, nve_vindparkomrader bool, nve_vindturbin bool, nve_kraftlinjer bool, nve_sjokabler bool, nve_transformatorstasjoner bool, nve_omradekonsesjoner bool, nve_sikringstiltak bool, nve_verneplan_vassdrag bool, nve_kvikkleire bool, nve_aktsomhet_snoskred bool, nve_aktsomhet_steinsprang bool, nve_aktsomhet_snosteinsprang bool, nve_aktsomhet_jordflomskred bool, nve_skredhendelser bool, nve_kraftverk_alle_kst bool, nve_magasin bool, nve_dam bool, nve_vanninntak bool, nve_vannvei bool, nve_delfelt_vannkraft bool, nve_vindkraftverk bool, nve_skredsoner bool, dsb_anleggfarligstoff bool, dsb_storulykkeanlegg bool, dsb_eksplosivanlegg bool,
      nibio_jordkvalitet bool, md_forurensetgrunn bool, md_frilstatligsikra bool, md_frilkartlverds bool, md_verdif_kulturlandsk bool, md_viktige_naturt bool, md_villreinomr bool, md_naturvernomr bool, md_naturvernomr_foresl bool, md_arter_nasjon_forv bool, md_naturt_landskap bool, md_naturt_utv bool
