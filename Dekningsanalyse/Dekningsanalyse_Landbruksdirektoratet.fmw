FME workspace Dekningsanalyse_Landbruksdirektoratet.fmw

Parameters:
- SourceDataset_POSTGRES = geonor01tst   # Database
- DestDataset_POSTGRES = geonor01tst   # Database

Readers:
- POSTGRES_1: POSTGRES from $(SourceDataset_POSTGRES)

Writers:
- POSTGRES_2: POSTGRES to $(DestDataset_POSTGRES)

admingrense.kommuner (reader POSTGRES_1)
    attributes: kommuneid int2,PRIKEY, navn varchar(80)
    -> AttributeCreator
AttributeCreator
    NUM_SUBSEQUENT_FEATURES = 0
    NUM_PRIOR_FEATURES = 0
    -> Tester
Tester
    TEST_DESCRIPTION = ""
    TEST_CLAUSE = TEST @Value(kommuneid) < 1000
    TEST_MODE = Automatic
    BOOL_OP = OR
    PASSED -> AttributeCreator_2
    FAILED -> TestFilter
AttributeCreator_2
    ATTR_LIST = kommuneid,0@Value(kommuneid)
    -> TestFilter
TestFilter
    DEFAULT_VALUE = Sone35
    TEST_LIST = BOOL_OP,OR,COMPOSITE_TEST,<Unused>,TEST_CLAUSE,"TEST @Value(kommuneid) < 1800",Sone32,BOOL_OP,OR,COMPOSITE_TEST,<Unused>,TEST_CLAUSE,"TEST @Value(kommuneid) < 2000",Sone33
    Sone32 -> HTTPCaller
    Sone33 -> HTTPCaller_2
    Sone35 -> HTTPCaller_3
    Sone32 -> HTTPCaller_4
    Sone33 -> HTTPCaller_5
    Sone35 -> HTTPCaller_6
    Sone32 -> HTTPCaller_7
    Sone33 -> HTTPCaller_8
    Sone35 -> HTTPCaller_9
    Sone32 -> HTTPCaller_10
    Sone33 -> HTTPCaller_11
    Sone35 -> HTTPCaller_12
    Sone32 -> HTTPCaller_13
    Sone33 -> HTTPCaller_14
    Sone35 -> HTTPCaller_15
    Sone32 -> HTTPCaller_16
    Sone33 -> HTTPCaller_17
    Sone35 -> HTTPCaller_18
    Sone32 -> HTTPCaller_19
    Sone33 -> HTTPCaller_20
    Sone35 -> HTTPCaller_21
    Sone32 -> HTTPCaller_22
    Sone33 -> HTTPCaller_23
    Sone35 -> HTTPCaller_24
    Sone32 -> HTTPCaller_25
    Sone33 -> HTTPCaller_26
    Sone35 -> HTTPCaller_27
    Sone32 -> HTTPCaller_28
    Sone33 -> HTTPCaller_29
    Sone35 -> HTTPCaller_30
    Sone32 -> HTTPCaller_31
    Sone33 -> HTTPCaller_32
    Sone35 -> HTTPCaller_33
    Sone32 -> HTTPCaller_34
    Sone33 -> HTTPCaller_35
    Sone35 -> HTTPCaller_36
    Sone32 -> HTTPCaller_37
    Sone33 -> HTTPCaller_38
    Sone35 -> HTTPCaller_39
    Sone32 -> HTTPCaller_40
    Sone33 -> HTTPCaller_41
    Sone35 -> HTTPCaller_42
    Sone32 -> HTTPCaller_43
    Sone33 -> HTTPCaller_44
    Sone35 -> HTTPCaller_45
    Sone32 -> HTTPCaller_46
    Sone33 -> HTTPCaller_47
    Sone35 -> HTTPCaller_48
    Sone32 -> HTTPCaller_49
    Sone33 -> HTTPCaller_50
    Sone35 -> HTTPCaller_51
    Sone32 -> HTTPCaller_52
    Sone33 -> HTTPCaller_53
    Sone35 -> HTTPCaller_54
Tester_3
    TEST_DESCRIPTION = ""
    TEST_CLAUSE = TEST @Value(kommuneid) BEGINS_WITH 0
    TEST_MODE = Automatic
    BOOL_OP = OR
    PASSED -> SubstringExtractor
    FAILED -> dekningsoversikt.dekningsoversikt (writer POSTGRES_2)
SubstringExtractor
    SRC_STRING = @Value(kommuneid)
    RESULT_ATTR = kommuneid
    START = 1
    END = -1
    -> dekningsoversikt.dekningsoversikt (writer POSTGRES_2)
dekningsoversikt.dekningsoversikt (writer POSTGRES_2)
    attributes: kommuneid int4,PRIKEY, akvakultur bool, korallrev bool, dsb_110sentral bool, dsb_brannstasjon bool, dsb_distrkont_siv bool, dsb_sivforsvdistr bool, ra_brannsmitteomr bool, ra_tettetrehusm bool, ra_frededebygg bool, ra_enkeltminner bool, ra_kulturmiljo bool, ra_lokaliteter bool, ra_sikringssoner bool, kv_hovedbiled bool, kv_ispshavneanlegg bool, kv_losbordingsfelt bool, kv_losstasjoner bool, nve_flomsoner10 bool, nve_flomsoner20 bool, nve_flomsoner50 bool, nve_flomsoner100 bool, nve_flomsoner200 bool, nve_flomsoner500 bool, nve_flomsoner1000 bool, nve_flomsoner200_i_aar2100 bool, nve_flomsonekartplan bool, nve_elvis_hovedelv bool, nve_elvis_elvenett bool, nve_innsjodata bool,
      nve_dybdekart bool, nve_nedborfelt_regine bool, nve_vassdragsomrade bool, nve_totnedbfelt_mstasjon bool, nve_vannkraftverk bool, nve_vindparkomrader bool, nve_vindturbin bool, nve_kraftlinjer bool, nve_sjokabler bool, nve_transformatorstasjoner bool, nve_omradekonsesjoner bool, nve_sikringstiltak bool, nve_verneplan_vassdrag bool, nve_kvikkleire bool, nve_aktsomhet_snoskred bool, nve_aktsomhet_steinsprang bool, nve_aktsomhet_snosteinsprang bool, nve_aktsomhet_jordflomskred bool, nve_skredhendelser bool, nve_kraftverk_alle_kst bool, nve_magasin bool, nve_dam bool, nve_vanninntak bool, nve_vannvei bool, nve_delfelt_vannkraft bool, nve_vindkraftverk bool, nve_skredsoner bool, dsb_anleggfarligstoff bool, dsb_storulykkeanlegg bool, dsb_eksplosivanlegg bool,
      nibio_jordkvalitet bool, md_forurensetgrunn bool, md_frilstatligsikra bool, md_frilkartlverds bool, md_verdif_kulturlandsk bool, md_viktige_naturt bool, md_villreinomr bool, md_naturvernomr bool, md_naturvernomr_foresl bool, md_arter_nasjon_forv bool, md_naturt_landskap bool, md_naturt_utv bool, fkb_ar5 bool, fkb_adresse bool, fkb_arealbruk bool, fkb_bane bool, fkb_bygnanlegg bool, fkb_bygning bool, fkb_bygningspunkt bool, fkb_hoydekurve-5m bool, fkb_hoydekurve bool, fkb_ledning bool, fkb_ledningva bool, fkb_lufthavn bool, fkb_matrikkelkartdekteig bool, fkb_naturinfo bool, fkb_pbltiltak bool, fkb_servitutt bool, fkb_tekst1000 bool, fkb_tekst5000 bool,
      fkb_traktorvegsti bool, fkb_vann bool, fkb_vbase bool, fkb_veg bool, ldir_reinbeitedistrikt bool, ldir_reinbeiteomrade bool, ldir_reindriftsanlegg bool, ldir_beitehage bool, ldir_flyttlei bool, ldir_trekklei bool, ldir_oppsamlingsomrade bool, ldir_varbeite bool, ldir_sommerbeite bool, ldir_hostbeite bool, ldir_hostvinterbeite bool, ldir_vinterbeite bool, ldir_siidagrense bool, ldir_konvensjonsomrade bool, ldir_konsesjonsomrader bool, ldir_restriksjonsomrader bool, ldir_tamreinlag bool, ldir_restriksjonsgrense bool, ldir_rendal bool, ldir_trollheimen bool, ldir_avtaleomrader bool, ldir_ekspropriasjonsomrader bool

Bookmark: Reinbeitedistrikt
HTTPCaller
    TARGET_ATTR = _response_body
    HTTP_METHOD = GET
    RESPONSE_HEADER_LIST_ATTR = _headers
    STATUS_CODE_ATTR = _http_status_code
    USE_COOKIES = No
    SAVE_FILE = Attribute
    CONNECTION_TIMEOUT_LENGTH = 60
    TARGET_URL = http://159.162.103.4/metadata/temadata/RDG22@Value(kommuneid).xml
    TARGET_ATTR_ENCODING = auto-detect
    VERIFY_SSL_CERTIFICATES = Yes
    FOLLOW_REDIRECTS = Yes
    ERROR_ATTR = _error
    TRANSFER_TIMEOUT_LENGTH = 90
    -> XMLFlattener
HTTPCaller_2
    TARGET_ATTR = _response_body
    HTTP_METHOD = GET
    RESPONSE_HEADER_LIST_ATTR = _headers
    STATUS_CODE_ATTR = _http_status_code
    USE_COOKIES = No
    SAVE_FILE = Attribute
    CONNECTION_TIMEOUT_LENGTH = 60
    TARGET_URL = http://159.162.103.4/metadata/temadata/RDG23@Value(kommuneid).xml
    TARGET_ATTR_ENCODING = auto-detect
    VERIFY_SSL_CERTIFICATES = Yes
    FOLLOW_REDIRECTS = Yes
    ERROR_ATTR = _error
    TRANSFER_TIMEOUT_LENGTH = 90
    -> XMLFlattener
HTTPCaller_3
    TARGET_ATTR = _response_body
    HTTP_METHOD = GET
    RESPONSE_HEADER_LIST_ATTR = _headers
    STATUS_CODE_ATTR = _http_status_code
    USE_COOKIES = No
    SAVE_FILE = Attribute
    CONNECTION_TIMEOUT_LENGTH = 60
    TARGET_URL = http://159.162.103.4/metadata/temadata/RDG25@Value(kommuneid).xml
    TARGET_ATTR_ENCODING = auto-detect
    VERIFY_SSL_CERTIFICATES = Yes
    FOLLOW_REDIRECTS = Yes
    ERROR_ATTR = _error
    TRANSFER_TIMEOUT_LENGTH = 90
    -> XMLFlattener
XMLFlattener
    EMBEDDED_EXPRESSIONS = *
    NEW_ATTRIBUTES = transSize
    XML_SOURCE_TYPE = Attribute with XML document
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    ATTRIBUTE_XML = _response_body
    -> Tester_2
Tester_2
    TEST_DESCRIPTION = ""
    TEST_CLAUSE = TEST @Value(transSize) > 0
    TEST_MODE = Automatic
    BOOL_OP = OR
    PASSED -> AttributeCreator_3
    FAILED -> AttributeCreator_5
AttributeCreator_3
    ATTR_LIST = ldir_reinbeitedistrikt,1
    -> Tester_3
AttributeCreator_5
    ATTR_LIST = ldir_reinbeitedistrikt,0
    -> Tester_3

Bookmark: Reinbeiteområde
HTTPCaller_4
    TARGET_ATTR = _response_body
    HTTP_METHOD = GET
    RESPONSE_HEADER_LIST_ATTR = _headers
    STATUS_CODE_ATTR = _http_status_code
    USE_COOKIES = No
    SAVE_FILE = Attribute
    CONNECTION_TIMEOUT_LENGTH = 60
    TARGET_URL = http://159.162.103.4/metadata/temadata/REB22@Value(kommuneid).xml
    TARGET_ATTR_ENCODING = auto-detect
    VERIFY_SSL_CERTIFICATES = Yes
    FOLLOW_REDIRECTS = Yes
    ERROR_ATTR = _error
    TRANSFER_TIMEOUT_LENGTH = 90
    -> XMLFlattener_2
HTTPCaller_5
    TARGET_ATTR = _response_body
    HTTP_METHOD = GET
    RESPONSE_HEADER_LIST_ATTR = _headers
    STATUS_CODE_ATTR = _http_status_code
    USE_COOKIES = No
    SAVE_FILE = Attribute
    CONNECTION_TIMEOUT_LENGTH = 60
    TARGET_URL = http://159.162.103.4/metadata/temadata/REB23@Value(kommuneid).xml
    TARGET_ATTR_ENCODING = auto-detect
    VERIFY_SSL_CERTIFICATES = Yes
    FOLLOW_REDIRECTS = Yes
    ERROR_ATTR = _error
    TRANSFER_TIMEOUT_LENGTH = 90
    -> XMLFlattener_2
HTTPCaller_6
    TARGET_ATTR = _response_body
    HTTP_METHOD = GET
    RESPONSE_HEADER_LIST_ATTR = _headers
    STATUS_CODE_ATTR = _http_status_code
    USE_COOKIES = No
    SAVE_FILE = Attribute
    CONNECTION_TIMEOUT_LENGTH = 60
    TARGET_URL = http://159.162.103.4/metadata/temadata/REB25@Value(kommuneid).xml
    TARGET_ATTR_ENCODING = auto-detect
    VERIFY_SSL_CERTIFICATES = Yes
    FOLLOW_REDIRECTS = Yes
    ERROR_ATTR = _error
    TRANSFER_TIMEOUT_LENGTH = 90
    -> XMLFlattener_2
XMLFlattener_2
    EMBEDDED_EXPRESSIONS = *
    NEW_ATTRIBUTES = transSize
    XML_SOURCE_TYPE = Attribute with XML document
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    ATTRIBUTE_XML = _response_body
    -> Tester_4
Tester_4
    TEST_DESCRIPTION = ""
    TEST_CLAUSE = TEST @Value(transSize) > 0
    TEST_MODE = Automatic
    BOOL_OP = OR
    PASSED -> AttributeCreator_4
    FAILED -> AttributeCreator_6
AttributeCreator_4
    ATTR_LIST = ldir_reinbeiteomrade,1
    -> Tester_3
AttributeCreator_6
    ATTR_LIST = ldir_reinbeiteomrade,0
    -> Tester_3

Bookmark: Reindriftsanlegg
HTTPCaller_7
    TARGET_ATTR = _response_body
    HTTP_METHOD = GET
    RESPONSE_HEADER_LIST_ATTR = _headers
    STATUS_CODE_ATTR = _http_status_code
    USE_COOKIES = No
    SAVE_FILE = Attribute
    CONNECTION_TIMEOUT_LENGTH = 60
    TARGET_URL = http://159.162.103.4/metadata/temadata/RAN22@Value(kommuneid).xml
    TARGET_ATTR_ENCODING = auto-detect
    VERIFY_SSL_CERTIFICATES = Yes
    FOLLOW_REDIRECTS = Yes
    ERROR_ATTR = _error
    TRANSFER_TIMEOUT_LENGTH = 90
    -> XMLFlattener_3
HTTPCaller_8
    TARGET_ATTR = _response_body
    HTTP_METHOD = GET
    RESPONSE_HEADER_LIST_ATTR = _headers
    STATUS_CODE_ATTR = _http_status_code
    USE_COOKIES = No
    SAVE_FILE = Attribute
    CONNECTION_TIMEOUT_LENGTH = 60
    TARGET_URL = http://159.162.103.4/metadata/temadata/RAN23@Value(kommuneid).xml
    TARGET_ATTR_ENCODING = auto-detect
    VERIFY_SSL_CERTIFICATES = Yes
    FOLLOW_REDIRECTS = Yes
    ERROR_ATTR = _error
    TRANSFER_TIMEOUT_LENGTH = 90
    -> XMLFlattener_3
HTTPCaller_9
    TARGET_ATTR = _response_body
    HTTP_METHOD = GET
    RESPONSE_HEADER_LIST_ATTR = _headers
    STATUS_CODE_ATTR = _http_status_code
    USE_COOKIES = No
    SAVE_FILE = Attribute
    CONNECTION_TIMEOUT_LENGTH = 60
    TARGET_URL = http://159.162.103.4/metadata/temadata/RAN25@Value(kommuneid).xml
    TARGET_ATTR_ENCODING = auto-detect
    VERIFY_SSL_CERTIFICATES = Yes
    FOLLOW_REDIRECTS = Yes
    ERROR_ATTR = _error
    TRANSFER_TIMEOUT_LENGTH = 90
    -> XMLFlattener_3
XMLFlattener_3
    EMBEDDED_EXPRESSIONS = *
    NEW_ATTRIBUTES = transSize
    XML_SOURCE_TYPE = Attribute with XML document
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    ATTRIBUTE_XML = _response_body
    -> Tester_5
Tester_5
    TEST_DESCRIPTION = ""
    TEST_CLAUSE = TEST @Value(transSize) > 0
    TEST_MODE = Automatic
    BOOL_OP = OR
    PASSED -> AttributeCreator_7
    FAILED -> AttributeCreator_8
AttributeCreator_7
    ATTR_LIST = ldir_reindriftsanlegg,1
    -> Tester_3
AttributeCreator_8
    ATTR_LIST = ldir_reindriftsanlegg,0
    -> Tester_3

Bookmark: Beitehage
HTTPCaller_10
    TARGET_ATTR = _response_body
    HTTP_METHOD = GET
    RESPONSE_HEADER_LIST_ATTR = _headers
    STATUS_CODE_ATTR = _http_status_code
    USE_COOKIES = No
    SAVE_FILE = Attribute
    CONNECTION_TIMEOUT_LENGTH = 60
    TARGET_URL = http://159.162.103.4/metadata/temadata/RBH22@Value(kommuneid).xml
    TARGET_ATTR_ENCODING = auto-detect
    VERIFY_SSL_CERTIFICATES = Yes
    FOLLOW_REDIRECTS = Yes
    ERROR_ATTR = _error
    TRANSFER_TIMEOUT_LENGTH = 90
    -> XMLFlattener_4
HTTPCaller_11
    TARGET_ATTR = _response_body
    HTTP_METHOD = GET
    RESPONSE_HEADER_LIST_ATTR = _headers
    STATUS_CODE_ATTR = _http_status_code
    USE_COOKIES = No
    SAVE_FILE = Attribute
    CONNECTION_TIMEOUT_LENGTH = 60
    TARGET_URL = http://159.162.103.4/metadata/temadata/RBH23@Value(kommuneid).xml
    TARGET_ATTR_ENCODING = auto-detect
    VERIFY_SSL_CERTIFICATES = Yes
    FOLLOW_REDIRECTS = Yes
    ERROR_ATTR = _error
    TRANSFER_TIMEOUT_LENGTH = 90
    -> XMLFlattener_4
HTTPCaller_12
    TARGET_ATTR = _response_body
    HTTP_METHOD = GET
    RESPONSE_HEADER_LIST_ATTR = _headers
    STATUS_CODE_ATTR = _http_status_code
    USE_COOKIES = No
    SAVE_FILE = Attribute
    CONNECTION_TIMEOUT_LENGTH = 60
    TARGET_URL = http://159.162.103.4/metadata/temadata/RBH25@Value(kommuneid).xml
    TARGET_ATTR_ENCODING = auto-detect
    VERIFY_SSL_CERTIFICATES = Yes
    FOLLOW_REDIRECTS = Yes
    ERROR_ATTR = _error
    TRANSFER_TIMEOUT_LENGTH = 90
    -> XMLFlattener_4
XMLFlattener_4
    EMBEDDED_EXPRESSIONS = *
    NEW_ATTRIBUTES = transSize
    XML_SOURCE_TYPE = Attribute with XML document
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    ATTRIBUTE_XML = _response_body
    -> Tester_6
Tester_6
    TEST_DESCRIPTION = ""
    TEST_CLAUSE = TEST @Value(transSize) > 0
    TEST_MODE = Automatic
    BOOL_OP = OR
    PASSED -> AttributeCreator_9
    FAILED -> AttributeCreator_10
AttributeCreator_9
    ATTR_LIST = ldir_beitehage,1
    -> Tester_3
AttributeCreator_10
    ATTR_LIST = ldir_beitehage,0
    -> Tester_3

Bookmark: Flyttlei
HTTPCaller_13
    TARGET_ATTR = _response_body
    HTTP_METHOD = GET
    RESPONSE_HEADER_LIST_ATTR = _headers
    STATUS_CODE_ATTR = _http_status_code
    USE_COOKIES = No
    SAVE_FILE = Attribute
    CONNECTION_TIMEOUT_LENGTH = 60
    TARGET_URL = http://159.162.103.4/metadata/temadata/RDR22@Value(kommuneid).xml
    TARGET_ATTR_ENCODING = auto-detect
    VERIFY_SSL_CERTIFICATES = Yes
    FOLLOW_REDIRECTS = Yes
    ERROR_ATTR = _error
    TRANSFER_TIMEOUT_LENGTH = 90
    -> XMLFlattener_5
HTTPCaller_14
    TARGET_ATTR = _response_body
    HTTP_METHOD = GET
    RESPONSE_HEADER_LIST_ATTR = _headers
    STATUS_CODE_ATTR = _http_status_code
    USE_COOKIES = No
    SAVE_FILE = Attribute
    CONNECTION_TIMEOUT_LENGTH = 60
    TARGET_URL = http://159.162.103.4/metadata/temadata/RDR23@Value(kommuneid).xml
    TARGET_ATTR_ENCODING = auto-detect
    VERIFY_SSL_CERTIFICATES = Yes
    FOLLOW_REDIRECTS = Yes
    ERROR_ATTR = _error
    TRANSFER_TIMEOUT_LENGTH = 90
    -> XMLFlattener_5
HTTPCaller_15
    TARGET_ATTR = _response_body
    HTTP_METHOD = GET
    RESPONSE_HEADER_LIST_ATTR = _headers
    STATUS_CODE_ATTR = _http_status_code
    USE_COOKIES = No
    SAVE_FILE = Attribute
    CONNECTION_TIMEOUT_LENGTH = 60
    TARGET_URL = http://159.162.103.4/metadata/temadata/RDR25@Value(kommuneid).xml
    TARGET_ATTR_ENCODING = auto-detect
    VERIFY_SSL_CERTIFICATES = Yes
    FOLLOW_REDIRECTS = Yes
    ERROR_ATTR = _error
    TRANSFER_TIMEOUT_LENGTH = 90
    -> XMLFlattener_5
XMLFlattener_5
    EMBEDDED_EXPRESSIONS = *
    NEW_ATTRIBUTES = transSize
    XML_SOURCE_TYPE = Attribute with XML document
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    ATTRIBUTE_XML = _response_body
    -> Tester_7
Tester_7
    TEST_DESCRIPTION = ""
    TEST_CLAUSE = TEST @Value(transSize) > 0
    TEST_MODE = Automatic
    BOOL_OP = OR
    PASSED -> AttributeCreator_11
    FAILED -> AttributeCreator_12
AttributeCreator_11
    ATTR_LIST = ldir_flyttlei,1
    -> Tester_3
AttributeCreator_12
    ATTR_LIST = ldir_flyttlei,0
    -> Tester_3

Bookmark: Trekklei
HTTPCaller_16
    TARGET_ATTR = _response_body
    HTTP_METHOD = GET
    RESPONSE_HEADER_LIST_ATTR = _headers
    STATUS_CODE_ATTR = _http_status_code
    USE_COOKIES = No
    SAVE_FILE = Attribute
    CONNECTION_TIMEOUT_LENGTH = 60
    TARGET_URL = http://159.162.103.4/metadata/temadata/RTR22@Value(kommuneid).xml
    TARGET_ATTR_ENCODING = auto-detect
    VERIFY_SSL_CERTIFICATES = Yes
    FOLLOW_REDIRECTS = Yes
    ERROR_ATTR = _error
    TRANSFER_TIMEOUT_LENGTH = 90
    -> XMLFlattener_6
HTTPCaller_17
    TARGET_ATTR = _response_body
    HTTP_METHOD = GET
    RESPONSE_HEADER_LIST_ATTR = _headers
    STATUS_CODE_ATTR = _http_status_code
    USE_COOKIES = No
    SAVE_FILE = Attribute
    CONNECTION_TIMEOUT_LENGTH = 60
    TARGET_URL = http://159.162.103.4/metadata/temadata/RTR23@Value(kommuneid).xml
    TARGET_ATTR_ENCODING = auto-detect
    VERIFY_SSL_CERTIFICATES = Yes
    FOLLOW_REDIRECTS = Yes
    ERROR_ATTR = _error
    TRANSFER_TIMEOUT_LENGTH = 90
    -> XMLFlattener_6
HTTPCaller_18
    TARGET_ATTR = _response_body
    HTTP_METHOD = GET
    RESPONSE_HEADER_LIST_ATTR = _headers
    STATUS_CODE_ATTR = _http_status_code
    USE_COOKIES = No
    SAVE_FILE = Attribute
    CONNECTION_TIMEOUT_LENGTH = 60
    TARGET_URL = http://159.162.103.4/metadata/temadata/RTR25@Value(kommuneid).xml
    TARGET_ATTR_ENCODING = auto-detect
    VERIFY_SSL_CERTIFICATES = Yes
    FOLLOW_REDIRECTS = Yes
    ERROR_ATTR = _error
    TRANSFER_TIMEOUT_LENGTH = 90
    -> XMLFlattener_6
XMLFlattener_6
    EMBEDDED_EXPRESSIONS = *
    NEW_ATTRIBUTES = transSize
    XML_SOURCE_TYPE = Attribute with XML document
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    ATTRIBUTE_XML = _response_body
    -> Tester_8
Tester_8
    TEST_DESCRIPTION = ""
    TEST_CLAUSE = TEST @Value(transSize) > 0
    TEST_MODE = Automatic
    BOOL_OP = OR
    PASSED -> AttributeCreator_13
    FAILED -> AttributeCreator_14
AttributeCreator_13
    ATTR_LIST = ldir_trekklei,1
    -> Tester_3
AttributeCreator_14
    ATTR_LIST = ldir_trekklei,0
    -> Tester_3

Bookmark: Oppsamlingsområde
HTTPCaller_19
    TARGET_ATTR = _response_body
    HTTP_METHOD = GET
    RESPONSE_HEADER_LIST_ATTR = _headers
    STATUS_CODE_ATTR = _http_status_code
    USE_COOKIES = No
    SAVE_FILE = Attribute
    CONNECTION_TIMEOUT_LENGTH = 60
    TARGET_URL = http://159.162.103.4/metadata/temadata/ROP22@Value(kommuneid).xml
    TARGET_ATTR_ENCODING = auto-detect
    VERIFY_SSL_CERTIFICATES = Yes
    FOLLOW_REDIRECTS = Yes
    ERROR_ATTR = _error
    TRANSFER_TIMEOUT_LENGTH = 90
    -> XMLFlattener_7
HTTPCaller_20
    TARGET_ATTR = _response_body
    HTTP_METHOD = GET
    RESPONSE_HEADER_LIST_ATTR = _headers
    STATUS_CODE_ATTR = _http_status_code
    USE_COOKIES = No
    SAVE_FILE = Attribute
    CONNECTION_TIMEOUT_LENGTH = 60
    TARGET_URL = http://159.162.103.4/metadata/temadata/ROP23@Value(kommuneid).xml
    TARGET_ATTR_ENCODING = auto-detect
    VERIFY_SSL_CERTIFICATES = Yes
    FOLLOW_REDIRECTS = Yes
    ERROR_ATTR = _error
    TRANSFER_TIMEOUT_LENGTH = 90
    -> XMLFlattener_7
HTTPCaller_21
    TARGET_ATTR = _response_body
    HTTP_METHOD = GET
    RESPONSE_HEADER_LIST_ATTR = _headers
    STATUS_CODE_ATTR = _http_status_code
    USE_COOKIES = No
    SAVE_FILE = Attribute
    CONNECTION_TIMEOUT_LENGTH = 60
    TARGET_URL = http://159.162.103.4/metadata/temadata/ROP25@Value(kommuneid).xml
    TARGET_ATTR_ENCODING = auto-detect
    VERIFY_SSL_CERTIFICATES = Yes
    FOLLOW_REDIRECTS = Yes
    ERROR_ATTR = _error
    TRANSFER_TIMEOUT_LENGTH = 90
    -> XMLFlattener_7
XMLFlattener_7
    EMBEDDED_EXPRESSIONS = *
    NEW_ATTRIBUTES = transSize
    XML_SOURCE_TYPE = Attribute with XML document
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    ATTRIBUTE_XML = _response_body
    -> Tester_9
Tester_9
    TEST_DESCRIPTION = ""
    TEST_CLAUSE = TEST @Value(transSize) > 0
    TEST_MODE = Automatic
    BOOL_OP = OR
    PASSED -> AttributeCreator_15
    FAILED -> AttributeCreator_16
AttributeCreator_15
    ATTR_LIST = ldir_oppsamlingsomrade,1
    -> Tester_3
AttributeCreator_16
    ATTR_LIST = ldir_oppsamlingsomrade,0
    -> Tester_3

Bookmark: Vårbeite
HTTPCaller_22
    TARGET_ATTR = _response_body
    HTTP_METHOD = GET
    RESPONSE_HEADER_LIST_ATTR = _headers
    STATUS_CODE_ATTR = _http_status_code
    USE_COOKIES = No
    SAVE_FILE = Attribute
    CONNECTION_TIMEOUT_LENGTH = 60
    TARGET_URL = http://159.162.103.4/metadata/temadata/RVR22@Value(kommuneid).xml
    TARGET_ATTR_ENCODING = auto-detect
    VERIFY_SSL_CERTIFICATES = Yes
    FOLLOW_REDIRECTS = Yes
    ERROR_ATTR = _error
    TRANSFER_TIMEOUT_LENGTH = 90
    -> XMLFlattener_8
HTTPCaller_23
    TARGET_ATTR = _response_body
    HTTP_METHOD = GET
    RESPONSE_HEADER_LIST_ATTR = _headers
    STATUS_CODE_ATTR = _http_status_code
    USE_COOKIES = No
    SAVE_FILE = Attribute
    CONNECTION_TIMEOUT_LENGTH = 60
    TARGET_URL = http://159.162.103.4/metadata/temadata/RVR23@Value(kommuneid).xml
    TARGET_ATTR_ENCODING = auto-detect
    VERIFY_SSL_CERTIFICATES = Yes
    FOLLOW_REDIRECTS = Yes
    ERROR_ATTR = _error
    TRANSFER_TIMEOUT_LENGTH = 90
    -> XMLFlattener_8
HTTPCaller_24
    TARGET_ATTR = _response_body
    HTTP_METHOD = GET
    RESPONSE_HEADER_LIST_ATTR = _headers
    STATUS_CODE_ATTR = _http_status_code
    USE_COOKIES = No
    SAVE_FILE = Attribute
    CONNECTION_TIMEOUT_LENGTH = 60
    TARGET_URL = http://159.162.103.4/metadata/temadata/RVR25@Value(kommuneid).xml
    TARGET_ATTR_ENCODING = auto-detect
    VERIFY_SSL_CERTIFICATES = Yes
    FOLLOW_REDIRECTS = Yes
    ERROR_ATTR = _error
    TRANSFER_TIMEOUT_LENGTH = 90
    -> XMLFlattener_8
XMLFlattener_8
    EMBEDDED_EXPRESSIONS = *
    NEW_ATTRIBUTES = transSize
    XML_SOURCE_TYPE = Attribute with XML document
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    ATTRIBUTE_XML = _response_body
    -> Tester_10
Tester_10
    TEST_DESCRIPTION = ""
    TEST_CLAUSE = TEST @Value(transSize) > 0
    TEST_MODE = Automatic
    BOOL_OP = OR
    PASSED -> AttributeCreator_17
    FAILED -> AttributeCreator_18
AttributeCreator_17
    ATTR_LIST = ldir_varbeite,1
    -> Tester_3
AttributeCreator_18
    ATTR_LIST = ldir_varbeite,0
    -> Tester_3

Bookmark: Sommerbeite
HTTPCaller_25
    TARGET_ATTR = _response_body
    HTTP_METHOD = GET
    RESPONSE_HEADER_LIST_ATTR = _headers
    STATUS_CODE_ATTR = _http_status_code
    USE_COOKIES = No
    SAVE_FILE = Attribute
    CONNECTION_TIMEOUT_LENGTH = 60
    TARGET_URL = http://159.162.103.4/metadata/temadata/RSO22@Value(kommuneid).xml
    TARGET_ATTR_ENCODING = auto-detect
    VERIFY_SSL_CERTIFICATES = Yes
    FOLLOW_REDIRECTS = Yes
    ERROR_ATTR = _error
    TRANSFER_TIMEOUT_LENGTH = 90
    -> XMLFlattener_9
HTTPCaller_26
    TARGET_ATTR = _response_body
    HTTP_METHOD = GET
    RESPONSE_HEADER_LIST_ATTR = _headers
    STATUS_CODE_ATTR = _http_status_code
    USE_COOKIES = No
    SAVE_FILE = Attribute
    CONNECTION_TIMEOUT_LENGTH = 60
    TARGET_URL = http://159.162.103.4/metadata/temadata/RSO23@Value(kommuneid).xml
    TARGET_ATTR_ENCODING = auto-detect
    VERIFY_SSL_CERTIFICATES = Yes
    FOLLOW_REDIRECTS = Yes
    ERROR_ATTR = _error
    TRANSFER_TIMEOUT_LENGTH = 90
    -> XMLFlattener_9
HTTPCaller_27
    TARGET_ATTR = _response_body
    HTTP_METHOD = GET
    RESPONSE_HEADER_LIST_ATTR = _headers
    STATUS_CODE_ATTR = _http_status_code
    USE_COOKIES = No
    SAVE_FILE = Attribute
    CONNECTION_TIMEOUT_LENGTH = 60
    TARGET_URL = http://159.162.103.4/metadata/temadata/RSO25@Value(kommuneid).xml
    TARGET_ATTR_ENCODING = auto-detect
    VERIFY_SSL_CERTIFICATES = Yes
    FOLLOW_REDIRECTS = Yes
    ERROR_ATTR = _error
    TRANSFER_TIMEOUT_LENGTH = 90
    -> XMLFlattener_9
XMLFlattener_9
    EMBEDDED_EXPRESSIONS = *
    NEW_ATTRIBUTES = transSize
    XML_SOURCE_TYPE = Attribute with XML document
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    ATTRIBUTE_XML = _response_body
    -> Tester_11
Tester_11
    TEST_DESCRIPTION = ""
    TEST_CLAUSE = TEST @Value(transSize) > 0
    TEST_MODE = Automatic
    BOOL_OP = OR
    PASSED -> AttributeCreator_19
    FAILED -> AttributeCreator_20
AttributeCreator_19
    ATTR_LIST = ldir_sommerbeite,1
    -> Tester_3
AttributeCreator_20
    ATTR_LIST = ldir_sommerbeite,0
    -> Tester_3

Bookmark: Høstbeite
HTTPCaller_28
    TARGET_ATTR = _response_body
    HTTP_METHOD = GET
    RESPONSE_HEADER_LIST_ATTR = _headers
    STATUS_CODE_ATTR = _http_status_code
    USE_COOKIES = No
    SAVE_FILE = Attribute
    CONNECTION_TIMEOUT_LENGTH = 60
    TARGET_URL = http://159.162.103.4/metadata/temadata/RHS22@Value(kommuneid).xml
    TARGET_ATTR_ENCODING = auto-detect
    VERIFY_SSL_CERTIFICATES = Yes
    FOLLOW_REDIRECTS = Yes
    ERROR_ATTR = _error
    TRANSFER_TIMEOUT_LENGTH = 90
    -> XMLFlattener_10
HTTPCaller_29
    TARGET_ATTR = _response_body
    HTTP_METHOD = GET
    RESPONSE_HEADER_LIST_ATTR = _headers
    STATUS_CODE_ATTR = _http_status_code
    USE_COOKIES = No
    SAVE_FILE = Attribute
    CONNECTION_TIMEOUT_LENGTH = 60
    TARGET_URL = http://159.162.103.4/metadata/temadata/RHS23@Value(kommuneid).xml
    TARGET_ATTR_ENCODING = auto-detect
    VERIFY_SSL_CERTIFICATES = Yes
    FOLLOW_REDIRECTS = Yes
    ERROR_ATTR = _error
    TRANSFER_TIMEOUT_LENGTH = 90
    -> XMLFlattener_10
HTTPCaller_30
    TARGET_ATTR = _response_body
    HTTP_METHOD = GET
    RESPONSE_HEADER_LIST_ATTR = _headers
    STATUS_CODE_ATTR = _http_status_code
    USE_COOKIES = No
    SAVE_FILE = Attribute
    CONNECTION_TIMEOUT_LENGTH = 60
    TARGET_URL = http://159.162.103.4/metadata/temadata/RHS25@Value(kommuneid).xml
    TARGET_ATTR_ENCODING = auto-detect
    VERIFY_SSL_CERTIFICATES = Yes
    FOLLOW_REDIRECTS = Yes
    ERROR_ATTR = _error
    TRANSFER_TIMEOUT_LENGTH = 90
    -> XMLFlattener_10
XMLFlattener_10
    EMBEDDED_EXPRESSIONS = *
    NEW_ATTRIBUTES = transSize
    XML_SOURCE_TYPE = Attribute with XML document
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    ATTRIBUTE_XML = _response_body
    -> Tester_12
Tester_12
    TEST_DESCRIPTION = ""
    TEST_CLAUSE = TEST @Value(transSize) > 0
    TEST_MODE = Automatic
    BOOL_OP = OR
    PASSED -> AttributeCreator_21
    FAILED -> AttributeCreator_22
AttributeCreator_21
    ATTR_LIST = ldir_hostbeite,1
    -> Tester_3
AttributeCreator_22
    ATTR_LIST = ldir_hostbeite,0
    -> Tester_3

Bookmark: Høstvinterbeite
HTTPCaller_31
    TARGET_ATTR = _response_body
    HTTP_METHOD = GET
    RESPONSE_HEADER_LIST_ATTR = _headers
    STATUS_CODE_ATTR = _http_status_code
    USE_COOKIES = No
    SAVE_FILE = Attribute
    CONNECTION_TIMEOUT_LENGTH = 60
    TARGET_URL = http://159.162.103.4/metadata/temadata/RHV22@Value(kommuneid).xml
    TARGET_ATTR_ENCODING = auto-detect
    VERIFY_SSL_CERTIFICATES = Yes
    FOLLOW_REDIRECTS = Yes
    ERROR_ATTR = _error
    TRANSFER_TIMEOUT_LENGTH = 90
    -> XMLFlattener_11
HTTPCaller_32
    TARGET_ATTR = _response_body
    HTTP_METHOD = GET
    RESPONSE_HEADER_LIST_ATTR = _headers
    STATUS_CODE_ATTR = _http_status_code
    USE_COOKIES = No
    SAVE_FILE = Attribute
    CONNECTION_TIMEOUT_LENGTH = 60
    TARGET_URL = http://159.162.103.4/metadata/temadata/RHV23@Value(kommuneid).xml
    TARGET_ATTR_ENCODING = auto-detect
    VERIFY_SSL_CERTIFICATES = Yes
    FOLLOW_REDIRECTS = Yes
    ERROR_ATTR = _error
    TRANSFER_TIMEOUT_LENGTH = 90
    -> XMLFlattener_11
HTTPCaller_33
    TARGET_ATTR = _response_body
    HTTP_METHOD = GET
    RESPONSE_HEADER_LIST_ATTR = _headers
    STATUS_CODE_ATTR = _http_status_code
    USE_COOKIES = No
    SAVE_FILE = Attribute
    CONNECTION_TIMEOUT_LENGTH = 60
    TARGET_URL = http://159.162.103.4/metadata/temadata/RHV25@Value(kommuneid).xml
    TARGET_ATTR_ENCODING = auto-detect
    VERIFY_SSL_CERTIFICATES = Yes
    FOLLOW_REDIRECTS = Yes
    ERROR_ATTR = _error
    TRANSFER_TIMEOUT_LENGTH = 90
    -> XMLFlattener_11
XMLFlattener_11
    EMBEDDED_EXPRESSIONS = *
    NEW_ATTRIBUTES = transSize
    XML_SOURCE_TYPE = Attribute with XML document
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    ATTRIBUTE_XML = _response_body
    -> Tester_13
Tester_13
    TEST_DESCRIPTION = ""
    TEST_CLAUSE = TEST @Value(transSize) > 0
    TEST_MODE = Automatic
    BOOL_OP = OR
    PASSED -> AttributeCreator_23
    FAILED -> AttributeCreator_24
AttributeCreator_23
    ATTR_LIST = ldir_hostvinterbeite,1
    -> Tester_3
AttributeCreator_24
    ATTR_LIST = ldir_hostvinterbeite,0
    -> Tester_3

Bookmark: Vinterbeite
HTTPCaller_34
    TARGET_ATTR = _response_body
    HTTP_METHOD = GET
    RESPONSE_HEADER_LIST_ATTR = _headers
    STATUS_CODE_ATTR = _http_status_code
    USE_COOKIES = No
    SAVE_FILE = Attribute
    CONNECTION_TIMEOUT_LENGTH = 60
    TARGET_URL = http://159.162.103.4/metadata/temadata/RVI22@Value(kommuneid).xml
    TARGET_ATTR_ENCODING = auto-detect
    VERIFY_SSL_CERTIFICATES = Yes
    FOLLOW_REDIRECTS = Yes
    ERROR_ATTR = _error
    TRANSFER_TIMEOUT_LENGTH = 90
    -> XMLFlattener_12
HTTPCaller_35
    TARGET_ATTR = _response_body
    HTTP_METHOD = GET
    RESPONSE_HEADER_LIST_ATTR = _headers
    STATUS_CODE_ATTR = _http_status_code
    USE_COOKIES = No
    SAVE_FILE = Attribute
    CONNECTION_TIMEOUT_LENGTH = 60
    TARGET_URL = http://159.162.103.4/metadata/temadata/RVI23@Value(kommuneid).xml
    TARGET_ATTR_ENCODING = auto-detect
    VERIFY_SSL_CERTIFICATES = Yes
    FOLLOW_REDIRECTS = Yes
    ERROR_ATTR = _error
    TRANSFER_TIMEOUT_LENGTH = 90
    -> XMLFlattener_12
HTTPCaller_36
    TARGET_ATTR = _response_body
    HTTP_METHOD = GET
    RESPONSE_HEADER_LIST_ATTR = _headers
    STATUS_CODE_ATTR = _http_status_code
    USE_COOKIES = No
    SAVE_FILE = Attribute
    CONNECTION_TIMEOUT_LENGTH = 60
    TARGET_URL = http://159.162.103.4/metadata/temadata/RVI25@Value(kommuneid).xml
    TARGET_ATTR_ENCODING = auto-detect
    VERIFY_SSL_CERTIFICATES = Yes
    FOLLOW_REDIRECTS = Yes
    ERROR_ATTR = _error
    TRANSFER_TIMEOUT_LENGTH = 90
    -> XMLFlattener_12
XMLFlattener_12
    EMBEDDED_EXPRESSIONS = *
    NEW_ATTRIBUTES = transSize
    XML_SOURCE_TYPE = Attribute with XML document
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    ATTRIBUTE_XML = _response_body
    -> Tester_14
Tester_14
    TEST_DESCRIPTION = ""
    TEST_CLAUSE = TEST @Value(transSize) > 0
    TEST_MODE = Automatic
    BOOL_OP = OR
    PASSED -> AttributeCreator_25
    FAILED -> AttributeCreator_26
AttributeCreator_25
    ATTR_LIST = ldir_vinterbeite,1
    -> Tester_3
AttributeCreator_26
    ATTR_LIST = ldir_vinterbeite,0
    -> Tester_3

Bookmark: Siidagrense
HTTPCaller_37
    TARGET_ATTR = _response_body
    HTTP_METHOD = GET
    RESPONSE_HEADER_LIST_ATTR = _headers
    STATUS_CODE_ATTR = _http_status_code
    USE_COOKIES = No
    SAVE_FILE = Attribute
    CONNECTION_TIMEOUT_LENGTH = 60
    TARGET_URL = http://159.162.103.4/metadata/temadata/RSI22@Value(kommuneid).xml
    TARGET_ATTR_ENCODING = auto-detect
    VERIFY_SSL_CERTIFICATES = Yes
    FOLLOW_REDIRECTS = Yes
    ERROR_ATTR = _error
    TRANSFER_TIMEOUT_LENGTH = 90
    -> XMLFlattener_13
HTTPCaller_38
    TARGET_ATTR = _response_body
    HTTP_METHOD = GET
    RESPONSE_HEADER_LIST_ATTR = _headers
    STATUS_CODE_ATTR = _http_status_code
    USE_COOKIES = No
    SAVE_FILE = Attribute
    CONNECTION_TIMEOUT_LENGTH = 60
    TARGET_URL = http://159.162.103.4/metadata/temadata/RSI23@Value(kommuneid).xml
    TARGET_ATTR_ENCODING = auto-detect
    VERIFY_SSL_CERTIFICATES = Yes
    FOLLOW_REDIRECTS = Yes
    ERROR_ATTR = _error
    TRANSFER_TIMEOUT_LENGTH = 90
    -> XMLFlattener_13
HTTPCaller_39
    TARGET_ATTR = _response_body
    HTTP_METHOD = GET
    RESPONSE_HEADER_LIST_ATTR = _headers
    STATUS_CODE_ATTR = _http_status_code
    USE_COOKIES = No
    SAVE_FILE = Attribute
    CONNECTION_TIMEOUT_LENGTH = 60
    TARGET_URL = http://159.162.103.4/metadata/temadata/RSI25@Value(kommuneid).xml
    TARGET_ATTR_ENCODING = auto-detect
    VERIFY_SSL_CERTIFICATES = Yes
    FOLLOW_REDIRECTS = Yes
    ERROR_ATTR = _error
    TRANSFER_TIMEOUT_LENGTH = 90
    -> XMLFlattener_13
XMLFlattener_13
    EMBEDDED_EXPRESSIONS = *
    NEW_ATTRIBUTES = transSize
    XML_SOURCE_TYPE = Attribute with XML document
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    ATTRIBUTE_XML = _response_body
    -> Tester_15
Tester_15
    TEST_DESCRIPTION = ""
    TEST_CLAUSE = TEST @Value(transSize) > 0
    TEST_MODE = Automatic
    BOOL_OP = OR
    PASSED -> AttributeCreator_27
    FAILED -> AttributeCreator_28
AttributeCreator_27
    ATTR_LIST = ldir_siidagrense,1
    -> Tester_3
AttributeCreator_28
    ATTR_LIST = ldir_siidagrense,0
    -> Tester_3

Bookmark: Konvensjonsområde
HTTPCaller_40
    TARGET_ATTR = _response_body
    HTTP_METHOD = GET
    RESPONSE_HEADER_LIST_ATTR = _headers
    STATUS_CODE_ATTR = _http_status_code
    USE_COOKIES = No
    SAVE_FILE = Attribute
    CONNECTION_TIMEOUT_LENGTH = 60
    TARGET_URL = http://159.162.103.4/metadata/temadata/RKO22@Value(kommuneid).xml
    TARGET_ATTR_ENCODING = auto-detect
    VERIFY_SSL_CERTIFICATES = Yes
    FOLLOW_REDIRECTS = Yes
    ERROR_ATTR = _error
    TRANSFER_TIMEOUT_LENGTH = 90
    -> XMLFlattener_14
HTTPCaller_41
    TARGET_ATTR = _response_body
    HTTP_METHOD = GET
    RESPONSE_HEADER_LIST_ATTR = _headers
    STATUS_CODE_ATTR = _http_status_code
    USE_COOKIES = No
    SAVE_FILE = Attribute
    CONNECTION_TIMEOUT_LENGTH = 60
    TARGET_URL = http://159.162.103.4/metadata/temadata/RKO23@Value(kommuneid).xml
    TARGET_ATTR_ENCODING = auto-detect
    VERIFY_SSL_CERTIFICATES = Yes
    FOLLOW_REDIRECTS = Yes
    ERROR_ATTR = _error
    TRANSFER_TIMEOUT_LENGTH = 90
    -> XMLFlattener_14
HTTPCaller_42
    TARGET_ATTR = _response_body
    HTTP_METHOD = GET
    RESPONSE_HEADER_LIST_ATTR = _headers
    STATUS_CODE_ATTR = _http_status_code
    USE_COOKIES = No
    SAVE_FILE = Attribute
    CONNECTION_TIMEOUT_LENGTH = 60
    TARGET_URL = http://159.162.103.4/metadata/temadata/RKO25@Value(kommuneid).xml
    TARGET_ATTR_ENCODING = auto-detect
    VERIFY_SSL_CERTIFICATES = Yes
    FOLLOW_REDIRECTS = Yes
    ERROR_ATTR = _error
    TRANSFER_TIMEOUT_LENGTH = 90
    -> XMLFlattener_14
XMLFlattener_14
    EMBEDDED_EXPRESSIONS = *
    NEW_ATTRIBUTES = transSize
    XML_SOURCE_TYPE = Attribute with XML document
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    ATTRIBUTE_XML = _response_body
    -> Tester_16
Tester_16
    TEST_DESCRIPTION = ""
    TEST_CLAUSE = TEST @Value(transSize) > 0
    TEST_MODE = Automatic
    BOOL_OP = OR
    PASSED -> AttributeCreator_29
    FAILED -> AttributeCreator_30
AttributeCreator_29
    ATTR_LIST = ldir_konvensjonsomrade,1
    -> Tester_3
AttributeCreator_30
    ATTR_LIST = ldir_konvensjonsomrade,0
    -> Tester_3

Bookmark: Konsesjonsområde
HTTPCaller_43
    TARGET_ATTR = _response_body
    HTTP_METHOD = GET
    RESPONSE_HEADER_LIST_ATTR = _headers
    STATUS_CODE_ATTR = _http_status_code
    USE_COOKIES = No
    SAVE_FILE = Attribute
    CONNECTION_TIMEOUT_LENGTH = 60
    TARGET_URL = http://159.162.103.4/metadata/temadata/RKS22@Value(kommuneid).xml
    TARGET_ATTR_ENCODING = auto-detect
    VERIFY_SSL_CERTIFICATES = Yes
    FOLLOW_REDIRECTS = Yes
    ERROR_ATTR = _error
    TRANSFER_TIMEOUT_LENGTH = 90
    -> XMLFlattener_15
HTTPCaller_44
    TARGET_ATTR = _response_body
    HTTP_METHOD = GET
    RESPONSE_HEADER_LIST_ATTR = _headers
    STATUS_CODE_ATTR = _http_status_code
    USE_COOKIES = No
    SAVE_FILE = Attribute
    CONNECTION_TIMEOUT_LENGTH = 60
    TARGET_URL = http://159.162.103.4/metadata/temadata/RKS23@Value(kommuneid).xml
    TARGET_ATTR_ENCODING = auto-detect
    VERIFY_SSL_CERTIFICATES = Yes
    FOLLOW_REDIRECTS = Yes
    ERROR_ATTR = _error
    TRANSFER_TIMEOUT_LENGTH = 90
    -> XMLFlattener_15
HTTPCaller_45
    TARGET_ATTR = _response_body
    HTTP_METHOD = GET
    RESPONSE_HEADER_LIST_ATTR = _headers
    STATUS_CODE_ATTR = _http_status_code
    USE_COOKIES = No
    SAVE_FILE = Attribute
    CONNECTION_TIMEOUT_LENGTH = 60
    TARGET_URL = http://159.162.103.4/metadata/temadata/RKS25@Value(kommuneid).xml
    TARGET_ATTR_ENCODING = auto-detect
    VERIFY_SSL_CERTIFICATES = Yes
    FOLLOW_REDIRECTS = Yes
    ERROR_ATTR = _error
    TRANSFER_TIMEOUT_LENGTH = 90
    -> XMLFlattener_15
XMLFlattener_15
    EMBEDDED_EXPRESSIONS = *
    NEW_ATTRIBUTES = transSize
    XML_SOURCE_TYPE = Attribute with XML document
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    ATTRIBUTE_XML = _response_body
    -> Tester_17
Tester_17
    TEST_DESCRIPTION = ""
    TEST_CLAUSE = TEST @Value(transSize) > 0
    TEST_MODE = Automatic
    BOOL_OP = OR
    PASSED -> AttributeCreator_31
    FAILED -> AttributeCreator_32
AttributeCreator_31
    ATTR_LIST = ldir_konsesjonsomrader,1
    -> Tester_3
AttributeCreator_32
    ATTR_LIST = ldir_konsesjonsomrader,0
    -> Tester_3

Bookmark: Restriksjonsområde
HTTPCaller_46
    TARGET_ATTR = _response_body
    HTTP_METHOD = GET
    RESPONSE_HEADER_LIST_ATTR = _headers
    STATUS_CODE_ATTR = _http_status_code
    USE_COOKIES = No
    SAVE_FILE = Attribute
    CONNECTION_TIMEOUT_LENGTH = 60
    TARGET_URL = http://159.162.103.4/metadata/temadata/RRO22@Value(kommuneid).xml
    TARGET_ATTR_ENCODING = auto-detect
    VERIFY_SSL_CERTIFICATES = Yes
    FOLLOW_REDIRECTS = Yes
    ERROR_ATTR = _error
    TRANSFER_TIMEOUT_LENGTH = 90
    -> XMLFlattener_16
HTTPCaller_47
    TARGET_ATTR = _response_body
    HTTP_METHOD = GET
    RESPONSE_HEADER_LIST_ATTR = _headers
    STATUS_CODE_ATTR = _http_status_code
    USE_COOKIES = No
    SAVE_FILE = Attribute
    CONNECTION_TIMEOUT_LENGTH = 60
    TARGET_URL = http://159.162.103.4/metadata/temadata/RRO23@Value(kommuneid).xml
    TARGET_ATTR_ENCODING = auto-detect
    VERIFY_SSL_CERTIFICATES = Yes
    FOLLOW_REDIRECTS = Yes
    ERROR_ATTR = _error
    TRANSFER_TIMEOUT_LENGTH = 90
    -> XMLFlattener_16
HTTPCaller_48
    TARGET_ATTR = _response_body
    HTTP_METHOD = GET
    RESPONSE_HEADER_LIST_ATTR = _headers
    STATUS_CODE_ATTR = _http_status_code
    USE_COOKIES = No
    SAVE_FILE = Attribute
    CONNECTION_TIMEOUT_LENGTH = 60
    TARGET_URL = http://159.162.103.4/metadata/temadata/RRO25@Value(kommuneid).xml
    TARGET_ATTR_ENCODING = auto-detect
    VERIFY_SSL_CERTIFICATES = Yes
    FOLLOW_REDIRECTS = Yes
    ERROR_ATTR = _error
    TRANSFER_TIMEOUT_LENGTH = 90
    -> XMLFlattener_16
XMLFlattener_16
    EMBEDDED_EXPRESSIONS = *
    NEW_ATTRIBUTES = transSize
    XML_SOURCE_TYPE = Attribute with XML document
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    ATTRIBUTE_XML = _response_body
    -> Tester_18
Tester_18
    TEST_DESCRIPTION = ""
    TEST_CLAUSE = TEST @Value(transSize) > 0
    TEST_MODE = Automatic
    BOOL_OP = OR
    PASSED -> AttributeCreator_33
    FAILED -> AttributeCreator_34
AttributeCreator_33
    ATTR_LIST = ldir_restriksjonsomrader,1
    -> Tester_3
AttributeCreator_34
    ATTR_LIST = ldir_restriksjonsomrader,0
    -> Tester_3

Bookmark: Avtaleområde
HTTPCaller_49
    TARGET_ATTR = _response_body
    HTTP_METHOD = GET
    RESPONSE_HEADER_LIST_ATTR = _headers
    STATUS_CODE_ATTR = _http_status_code
    USE_COOKIES = No
    SAVE_FILE = Attribute
    CONNECTION_TIMEOUT_LENGTH = 60
    TARGET_URL = http://159.162.103.4/metadata/temadata/RAV22@Value(kommuneid).xml
    TARGET_ATTR_ENCODING = auto-detect
    VERIFY_SSL_CERTIFICATES = Yes
    FOLLOW_REDIRECTS = Yes
    ERROR_ATTR = _error
    TRANSFER_TIMEOUT_LENGTH = 90
    -> XMLFlattener_17
HTTPCaller_50
    TARGET_ATTR = _response_body
    HTTP_METHOD = GET
    RESPONSE_HEADER_LIST_ATTR = _headers
    STATUS_CODE_ATTR = _http_status_code
    USE_COOKIES = No
    SAVE_FILE = Attribute
    CONNECTION_TIMEOUT_LENGTH = 60
    TARGET_URL = http://159.162.103.4/metadata/temadata/RAV23@Value(kommuneid).xml
    TARGET_ATTR_ENCODING = auto-detect
    VERIFY_SSL_CERTIFICATES = Yes
    FOLLOW_REDIRECTS = Yes
    ERROR_ATTR = _error
    TRANSFER_TIMEOUT_LENGTH = 90
    -> XMLFlattener_17
HTTPCaller_51
    TARGET_ATTR = _response_body
    HTTP_METHOD = GET
    RESPONSE_HEADER_LIST_ATTR = _headers
    STATUS_CODE_ATTR = _http_status_code
    USE_COOKIES = No
    SAVE_FILE = Attribute
    CONNECTION_TIMEOUT_LENGTH = 60
    TARGET_URL = http://159.162.103.4/metadata/temadata/RAV25@Value(kommuneid).xml
    TARGET_ATTR_ENCODING = auto-detect
    VERIFY_SSL_CERTIFICATES = Yes
    FOLLOW_REDIRECTS = Yes
    ERROR_ATTR = _error
    TRANSFER_TIMEOUT_LENGTH = 90
    -> XMLFlattener_17
XMLFlattener_17
    EMBEDDED_EXPRESSIONS = *
    NEW_ATTRIBUTES = transSize
    XML_SOURCE_TYPE = Attribute with XML document
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    ATTRIBUTE_XML = _response_body
    -> Tester_19
Tester_19
    TEST_DESCRIPTION = ""
    TEST_CLAUSE = TEST @Value(transSize) > 0
    TEST_MODE = Automatic
    BOOL_OP = OR
    PASSED -> AttributeCreator_35
    FAILED -> AttributeCreator_36
AttributeCreator_35
    ATTR_LIST = ldir_avtaleomrader,1
    -> Tester_3
AttributeCreator_36
    ATTR_LIST = ldir_avtaleomrader,0
    -> Tester_3

Bookmark: Ekspropriasjonsområde
HTTPCaller_52
    TARGET_ATTR = _response_body
    HTTP_METHOD = GET
    RESPONSE_HEADER_LIST_ATTR = _headers
    STATUS_CODE_ATTR = _http_status_code
    USE_COOKIES = No
    SAVE_FILE = Attribute
    CONNECTION_TIMEOUT_LENGTH = 60
    TARGET_URL = http://159.162.103.4/metadata/temadata/REO22@Value(kommuneid).xml
    TARGET_ATTR_ENCODING = auto-detect
    VERIFY_SSL_CERTIFICATES = Yes
    FOLLOW_REDIRECTS = Yes
    ERROR_ATTR = _error
    TRANSFER_TIMEOUT_LENGTH = 90
    -> XMLFlattener_18
HTTPCaller_53
    TARGET_ATTR = _response_body
    HTTP_METHOD = GET
    RESPONSE_HEADER_LIST_ATTR = _headers
    STATUS_CODE_ATTR = _http_status_code
    USE_COOKIES = No
    SAVE_FILE = Attribute
    CONNECTION_TIMEOUT_LENGTH = 60
    TARGET_URL = http://159.162.103.4/metadata/temadata/REO23@Value(kommuneid).xml
    TARGET_ATTR_ENCODING = auto-detect
    VERIFY_SSL_CERTIFICATES = Yes
    FOLLOW_REDIRECTS = Yes
    ERROR_ATTR = _error
    TRANSFER_TIMEOUT_LENGTH = 90
    -> XMLFlattener_18
HTTPCaller_54
    TARGET_ATTR = _response_body
    HTTP_METHOD = GET
    RESPONSE_HEADER_LIST_ATTR = _headers
    STATUS_CODE_ATTR = _http_status_code
    USE_COOKIES = No
    SAVE_FILE = Attribute
    CONNECTION_TIMEOUT_LENGTH = 60
    TARGET_URL = http://159.162.103.4/metadata/temadata/REO25@Value(kommuneid).xml
    TARGET_ATTR_ENCODING = auto-detect
    VERIFY_SSL_CERTIFICATES = Yes
    FOLLOW_REDIRECTS = Yes
    ERROR_ATTR = _error
    TRANSFER_TIMEOUT_LENGTH = 90
    -> XMLFlattener_18
XMLFlattener_18
    EMBEDDED_EXPRESSIONS = *
    NEW_ATTRIBUTES = transSize
    XML_SOURCE_TYPE = Attribute with XML document
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    ATTRIBUTE_XML = _response_body
    -> Tester_20
Tester_20
    TEST_DESCRIPTION = ""
    TEST_CLAUSE = TEST @Value(transSize) > 0
    TEST_MODE = Automatic
    BOOL_OP = OR
    PASSED -> AttributeCreator_37
    FAILED -> AttributeCreator_38
AttributeCreator_37
    ATTR_LIST = ldir_ekspropriasjonsomrader,1
    -> Tester_3
AttributeCreator_38
    ATTR_LIST = ldir_ekspropriasjonsomrader,0
    -> Tester_3
