FME workspace Dekningsanalyse_FKB.fmw

Parameters:
- FKB_datasett = PblTiltak   # Datasett som skal analyseres
- SourceDataset_POSTGRES = geonor01tst   # Database
- DestDataset_POSTGRES = geonor01tst   # Database

Readers:
- POSTGRES_1: POSTGRES from $(SourceDataset_POSTGRES)

Writers:
- POSTGRES_2: POSTGRES to $(DestDataset_POSTGRES)

Note: Leser kommunetabell (uten geometri)
admingrense.kommuner (reader POSTGRES_1)
    attributes: kommuneid int2,PRIKEY, navn varchar(80)
    -> Tester
Note: Henter ut transSize-attributten
XMLFlattener
    XML_SOURCE_TYPE = Attribute with XML document
    ATTRIBUTE_XML = _response_body
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    EMBEDDED_EXPRESSIONS = *
    NEW_ATTRIBUTES = transSize
    -> Tester_2
Note: Er filstørrelsen (data) større enn 0?
Tester_2
    TEST_MODE = Automatic
    BOOL_OP = OR
    TEST_CLAUSE = TEST @Value(transSize) > 0
    TEST_DESCRIPTION = ""
    PASSED -> AttributeCreator_3
    FAILED -> AttributeCreator_5
Note: Dynamisk attributtnavn fra parameter
BulkAttributeRenamer
    PATTERN_ACTION_DISP = Add String Suffix
    ATTRCHOICE = Selected Attributes
    REPLACE_STR = $(FKB_datasett)
    ATTRLIST = fkb_
    -> BulkAttributeRenamer_2
Note: Alle attributter til små bokstaver
BulkAttributeRenamer_2
    PATTERN_ACTION_DISP = Change Case
    CASE_CHANGE_TYPE = lowercase
    ATTRCHOICE = All Attributes
    -> Tester_3
Note: Oppdaterer postgres
dekningsoversikt.dekningsoversikt (writer POSTGRES_2)
    attributes: kommuneid int4,PRIKEY, akvakultur bool, korallrev bool, dsb_110sentral bool, dsb_brannstasjon bool, dsb_distrkont_siv bool, dsb_sivforsvdistr bool, ra_brannsmitteomr bool, ra_tettetrehusm bool, ra_frededebygg bool, ra_enkeltminner bool, ra_kulturmiljo bool, ra_lokaliteter bool, ra_sikringssoner bool, kv_hovedbiled bool, kv_ispshavneanlegg bool, kv_losbordingsfelt bool, kv_losstasjoner bool, nve_flomsoner10 bool, nve_flomsoner20 bool, nve_flomsoner50 bool, nve_flomsoner100 bool, nve_flomsoner200 bool, nve_flomsoner500 bool, nve_flomsoner1000 bool, nve_flomsoner200_i_aar2100 bool, nve_flomsonekartplan bool, nve_elvis_hovedelv bool, nve_elvis_elvenett bool, nve_innsjodata bool,
      nve_dybdekart bool, nve_nedborfelt_regine bool, nve_vassdragsomrade bool, nve_totnedbfelt_mstasjon bool, nve_vannkraftverk bool, nve_vindparkomrader bool, nve_vindturbin bool, nve_kraftlinjer bool, nve_sjokabler bool, nve_transformatorstasjoner bool, nve_omradekonsesjoner bool, nve_sikringstiltak bool, nve_verneplan_vassdrag bool, nve_kvikkleire bool, nve_aktsomhet_snoskred bool, nve_aktsomhet_steinsprang bool, nve_aktsomhet_snosteinsprang bool, nve_aktsomhet_jordflomskred bool, nve_skredhendelser bool, nve_kraftverk_alle_kst bool, nve_magasin bool, nve_dam bool, nve_vanninntak bool, nve_vannvei bool, nve_delfelt_vannkraft bool, nve_vindkraftverk bool, nve_skredsoner bool, dsb_anleggfarligstoff bool, dsb_storulykkeanlegg bool, dsb_eksplosivanlegg bool,
      nibio_jordkvalitet bool, md_forurensetgrunn bool, md_frilstatligsikra bool, md_frilkartlverds bool, md_verdif_kulturlandsk bool, md_viktige_naturt bool, md_villreinomr bool, md_naturvernomr bool, md_naturvernomr_foresl bool, md_arter_nasjon_forv bool, md_naturt_landskap bool, md_naturt_utv bool, fkb_ar5 bool, fkb_adresse bool, fkb_arealbruk bool, fkb_bane bool, fkb_bygnanlegg bool, fkb_bygning bool, fkb_bygningspunkt bool, fkb_hoydekurve-5m bool, fkb_hoydekurve bool, fkb_ledning bool, fkb_ledningva bool, fkb_lufthavn bool, fkb_matrikkelkartdekteig bool, fkb_naturinfo bool, fkb_pbltiltak bool, fkb_servitutt bool, fkb_tekst1000 bool, fkb_tekst5000 bool,
      fkb_traktorvegsti bool, fkb_vann bool, fkb_vbase bool, fkb_veg bool

Bookmark: KommuneID ledende 0
Tester
    TEST_MODE = Automatic
    BOOL_OP = OR
    TEST_CLAUSE = TEST @Value(kommuneid) < 1000
    TEST_DESCRIPTION = ""
    PASSED -> AttributeCreator_2
    FAILED -> TestFilter
AttributeCreator_2
    ATTR_LIST = kommuneid,0@Value(kommuneid)
    -> TestFilter

Bookmark: Finner lokale UTM-soner
TestFilter
    TEST_LIST = BOOL_OP,OR,COMPOSITE_TEST,<Unused>,TEST_CLAUSE,"TEST @Value(kommuneid) < 1800",Sone32,BOOL_OP,OR,COMPOSITE_TEST,<Unused>,TEST_CLAUSE,"TEST @Value(kommuneid) < 2000",Sone33
    DEFAULT_VALUE = Sone35
    Sone32 -> HTTPCaller
    Sone33 -> HTTPCaller_2
    Sone35 -> HTTPCaller_3

Bookmark: Leser XML Metadata
HTTPCaller
    USE_COOKIES = No
    CONNECTION_TIMEOUT_LENGTH = 60
    ERROR_ATTR = _error
    RESPONSE_HEADER_LIST_ATTR = _headers
    SAVE_FILE = Attribute
    STATUS_CODE_ATTR = _http_status_code
    TRANSFER_TIMEOUT_LENGTH = 90
    TARGET_ATTR_ENCODING = auto-detect
    TARGET_ATTR = _response_body
    HTTP_METHOD = GET
    TARGET_URL = http://159.162.103.4/metadata/FKB40/32_@Value(kommuneid)$(FKB_datasett).xml
    VERIFY_SSL_CERTIFICATES = Yes
    FOLLOW_REDIRECTS = Yes
    -> XMLFlattener
HTTPCaller_2
    USE_COOKIES = No
    CONNECTION_TIMEOUT_LENGTH = 60
    ERROR_ATTR = _error
    RESPONSE_HEADER_LIST_ATTR = _headers
    SAVE_FILE = Attribute
    STATUS_CODE_ATTR = _http_status_code
    TRANSFER_TIMEOUT_LENGTH = 90
    TARGET_ATTR_ENCODING = auto-detect
    TARGET_ATTR = _response_body
    HTTP_METHOD = GET
    TARGET_URL = http://159.162.103.4/metadata/FKB40/33_@Value(kommuneid)$(FKB_datasett).xml
    VERIFY_SSL_CERTIFICATES = Yes
    FOLLOW_REDIRECTS = Yes
    -> XMLFlattener
HTTPCaller_3
    USE_COOKIES = No
    CONNECTION_TIMEOUT_LENGTH = 60
    ERROR_ATTR = _error
    RESPONSE_HEADER_LIST_ATTR = _headers
    SAVE_FILE = Attribute
    STATUS_CODE_ATTR = _http_status_code
    TRANSFER_TIMEOUT_LENGTH = 90
    TARGET_ATTR_ENCODING = auto-detect
    TARGET_ATTR = _response_body
    HTTP_METHOD = GET
    TARGET_URL = http://159.162.103.4/metadata/FKB40/35_@Value(kommuneid)$(FKB_datasett).xml
    VERIFY_SSL_CERTIFICATES = Yes
    FOLLOW_REDIRECTS = Yes
    -> XMLFlattener

Bookmark: Er det dekning?
AttributeCreator_3
    ATTR_LIST = fkb_,1
    -> BulkAttributeRenamer
AttributeCreator_5
    ATTR_LIST = fkb_,0
    -> BulkAttributeRenamer

Bookmark: KommuneID ledende 0
Tester_3
    TEST_MODE = Automatic
    BOOL_OP = OR
    TEST_CLAUSE = TEST @Value(kommuneid) BEGINS_WITH 0
    TEST_DESCRIPTION = ""
    PASSED -> SubstringExtractor
    FAILED -> dekningsoversikt.dekningsoversikt (writer POSTGRES_2)
SubstringExtractor
    END = -1
    SRC_STRING = @Value(kommuneid)
    RESULT_ATTR = kommuneid
    START = 1
    -> dekningsoversikt.dekningsoversikt (writer POSTGRES_2)
