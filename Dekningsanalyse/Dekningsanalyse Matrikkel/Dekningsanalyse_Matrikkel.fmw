FME workspace Dekningsanalyse_Matrikkel.fmw

Parameters:
- DestDataset_POSTGIS = geonortst@nnridb504:5432/geonor01tst   # Connection
- SourceDataset_XLSXR = $(FME_MF_DIR)Antall_vegadresser_og_matrikkeladresser_22.09.2015.xls   # Source Microsoft Excel File(s)
- SourceDataset_POSTGRES = geonortst@nnridb504:5432/geonor01tst   # Connection
- SourceDataset_SOSI = C:\Users\xmaland\Documents\GitHub\geonorge\Dekningsanalyse\Temp_data\ADM_maritim_versjon_2015-1.sos   # Source SOSI File
- SourceDataset_POSTGIS = geonortst@nnridb504:5432/geonor01tst   # Connection

Readers:
- XLSXR_1: XLSXR from $(SourceDataset_XLSXR)
- POSTGRES_1: POSTGRES from $(SourceDataset_POSTGRES)
- SOSI_1: SOSI from $(SourceDataset_SOSI)
- POSTGIS_1: POSTGIS from $(SourceDataset_POSTGIS)

Writers:
- POSTGIS_2: POSTGIS to $(DestDataset_POSTGIS)

Totaloversikt (reader XLSXR_1)
    attributes: Fylke char(33), Kommune char(21), Adresser_totalt number(6,0), Veg-_adresser number(6,0), Prosent vegadr. number(20,15), Matrikkel-_adresser number(5,0), Prosent matr.adr number(22,17), H string, I char(50), J char(33), K string, L string, M string, N number(2,0), O number(2,0)
    -> Tester_3 [off]
Tester_3 [off]
    TEST_CLAUSE = TEST Kommune NOT_ATTRIBUTE_IS_MISSING ""
    BOOL_OP = OR
    TEST_DESCRIPTION = ""
    TEST_MODE = Automatic
    PASSED -> SubstringExtractor [off]
SubstringExtractor [off]
    START = 0
    RESULT_ATTR = _kommune
    SRC_STRING = @Value(Kommune)
    END = 3
    -> Tester_2 [off]
Tester_2 [off]
    TEST_CLAUSE = TEST @Value(_kommune) BEGINS_WITH 0
    BOOL_OP = OR
    TEST_DESCRIPTION = ""
    TEST_MODE = Automatic
    PASSED -> SubstringExtractor_2 [off]
    FAILED -> AttributeRenamer [off]
SubstringExtractor_2 [off]
    START = 1
    RESULT_ATTR = kommuneid
    SRC_STRING = @Value(_kommune)
    END = -1
    -> Tester [off]
AttributeRenamer [off]
    ATTR_LIST = _kommune,kommuneid,
    -> Tester [off]
Tester [off]
    TEST_CLAUSE = TEST @Value(Veg-_adresser) = 0
    BOOL_OP = OR
    TEST_DESCRIPTION = ""
    TEST_MODE = Automatic
    PASSED -> AttributeCreator [off]
    FAILED -> AttributeCreator_2 [off]
AttributeCreator [off]
    ATTR_LIST = matrikkel_vegadresser,0
    -> dekningsoversikt.dekningsoversikt (writer POSTGIS_2)
AttributeCreator_2 [off]
    ATTR_LIST = matrikkel_vegadresser,1
    -> dekningsoversikt.dekningsoversikt (writer POSTGIS_2)
admingrense.kommuneflate (reader POSTGIS_1)
    attributes: kommuneid int4, navn varchar(80)
    -> Deaggregator
Deaggregator
    SPLIT_COMPOSITES = No
    PART_NUMBER_FIELD = _part_number
    GEOM_NAME_FIELD = _geometry_name
    MODE = Flatten One Level
    ID_SELECTION = ID and Parent ID
    LIST_ATTR_MODE_LOOKUP = LEAN
    PARENT_ID_ATTR = _hierarchy_parent_id
    CHILD_ID_ATTR = _hierarchy_child_id_list
    EXPLODE_INSTANCES = No
    ID_ATTR = _hierarchy_id
    COPY_ATTR = Every Node
    DEAGGREGATED -> SpatialFilter [input 2]
    DEAGGREGATED -> SpatialFilter_2 [input 2]
admingrense.kommuner (reader POSTGRES_1)
    attributes: kommuneid int2,PRIKEY, navn varchar(80)
    -> AttributeCreator_3 [off]
AttributeCreator_3 [off]
    ATTR_LIST = nibio_ar50,1,sk_vbase,1,sk_n50,1,sk_n250,1,sk_n500,1,sk_n1000,1,sk_n5000,1,sk_ssr,1,sk_abas,1,matrikkel_bygningspunkt,1,matrikkel_eiendom,1,ngu_losmasser,1
    -> dekningsoversikt.dekningsoversikt (writer POSTGIS_2)
dekningsoversikt.dekningsoversikt (writer POSTGIS_2)
    attributes: kommuneid int4,PRIKEY, akvakultur bool, dsb_sivforsvdistr bool, korallrev bool, dsb_brannstasjon bool, dsb_110sentral bool, dsb_distrkont_siv bool, ra_brannsmitteomr bool, ra_tettetrehusm bool, ra_frededebygg bool, ra_enkeltminner bool, ra_kulturmiljo bool, ra_lokaliteter bool, ra_sikringssoner bool, kv_hovedbiled bool, kv_ispshavneanlegg bool, kv_losbordingsfelt bool, kv_losstasjoner bool, nve_flomsoner10 bool, nve_flomsoner20 bool, nve_flomsoner50 bool, nve_flomsoner100 bool, nve_flomsoner200 bool, nve_flomsoner500 bool, nve_flomsoner1000 bool, nve_flomsoner200_i_aar2100 bool, nve_flomsonekartplan bool, nve_elvis_hovedelv bool, nve_elvis_elvenett bool, nve_innsjodata bool,
      nve_dybdekart bool, nve_nedborfelt_regine bool, nve_vassdragsomrade bool, nve_totnedbfelt_mstasjon bool, nve_vannkraftverk bool, nve_vindparkomrader bool, nve_vindturbin bool, nve_kraftlinjer bool, nve_sjokabler bool, nve_transformatorstasjoner bool, nve_omradekonsesjoner bool, nve_sikringstiltak bool, nve_verneplan_vassdrag bool, nve_kvikkleire bool, nve_aktsomhet_snoskred bool, nve_aktsomhet_steinsprang bool, nve_aktsomhet_snosteinsprang bool, nve_aktsomhet_jordflomskred bool, nve_skredhendelser bool, nve_kraftverk_alle_kst bool, nve_magasin bool, nve_dam bool, nve_vanninntak bool, nve_vannvei bool, nve_delfelt_vannkraft bool, nve_vindkraftverk bool, nve_skredsoner bool, dsb_anleggfarligstoff bool, dsb_storulykkeanlegg bool, dsb_eksplosivanlegg bool,
      nibio_jordkvalitet bool, md_forurensetgrunn bool, md_frilstatligsikra bool, md_frilkartlverds bool, md_verdif_kulturlandsk bool, md_viktige_naturt bool, md_villreinomr bool, md_naturvernomr bool, md_naturvernomr_foresl bool, md_arter_nasjon_forv bool, md_naturt_landskap bool, md_naturt_utv bool, fkb_ar5 bool, fkb_adresse bool, fkb_arealbruk bool, fkb_bane bool, fkb_bygnanlegg bool, fkb_bygning bool, fkb_bygningspunkt bool, fkb_hoydekurve-5m bool, fkb_hoydekurve bool, fkb_ledning bool, fkb_ledningva bool, fkb_lufthavn bool, fkb_matrikkelkartdekteig bool, fkb_naturinfo bool, fkb_pbltiltak bool, fkb_servitutt bool, fkb_tekst1000 bool, fkb_tekst5000 bool,
      fkb_traktorvegsti bool, fkb_vann bool, fkb_vbase bool, fkb_veg bool, ldir_reinbeitedistrikt bool, ldir_reinbeiteomrade bool, ldir_reindriftsanlegg bool, ldir_beitehage bool, ldir_flyttlei bool, ldir_trekklei bool, ldir_oppsamlingsomrade bool, ldir_varbeite bool, ldir_sommerbeite bool, ldir_hostbeite bool, ldir_hostvinterbeite bool, ldir_vinterbeite bool, ldir_siidagrense bool, ldir_konvensjonsomrade bool, ldir_konsesjonsomrader bool, ldir_restriksjonsomrader bool, ldir_tamreinlag bool, ldir_restriksjonsgrense bool, ldir_rendal bool, ldir_trollheimen bool, ldir_avtaleomrader bool, ldir_ekspropriasjonsomrader bool, avinor_stoysoner bool, forsvaret_stoysoner bool, matrikkel_vegadresser bool, nibio_ar50 bool,
      sk_vbase bool, sk_n50 bool, sk_n250 bool, sk_n500 bool, sk_n1000 bool, sk_n5000 bool, sk_ssr bool, sk_abas bool, matrikkel_bygningspunkt bool, matrikkel_eiendom bool, ngu_losmasser bool, sk_norgesmargrenser bool, sk_sjokartraster bool

Bookmark: Maritime grenser
InternasjonaltFarvann (reader SOSI_1)
    attributes: SOSI_id SOSI_int32, OPPDATERINGSDATO SOSI_datetime, NAVN SOSI_char(60), INFORMASJON SOSI_char(255), OBJTYPE SOSI_char(32)
    -> SpatialFilter [input 1]
Fiskevernsone (reader SOSI_1)
    attributes: SOSI_id SOSI_int32, LANDKODE SOSI_char(2), GYLDIG_FRA SOSI_char(255), LINK SOSI_char(255), DATAFANGSTDATO SOSI_datetime, STATUS SOSI_char(2), LOVREF SOSI_char(255), SOSI_guid SOSI_char(36), NAVN SOSI_char(60), INFORMASJON SOSI_char(255), OBJTYPE SOSI_char(32), AREAL_KM2 SOSI_char(255), OPPDATERINGSDATO SOSI_datetime
    -> SpatialFilter [input 1]
Territorialgrense (reader SOSI_1)
    attributes: SOSI_id SOSI_int32, LANDKODE SOSI_char(2), GYLDIG_FRA SOSI_char(255), LINK SOSI_char(255), DATAFANGSTDATO SOSI_datetime, NOYAKTIGHET SOSI_number(6,0), STATUS SOSI_char(2), LOVREF SOSI_char(255), MALEMETODE SOSI_int16, SOSI_guid SOSI_char(36), NAVN SOSI_char(60), INFORMASJON SOSI_char(255), OBJTYPE SOSI_char(32), OPPDATERINGSDATO SOSI_datetime
    -> SpatialFilter [input 1]
EksklusivOkonomiskSone (reader SOSI_1)
    attributes: SOSI_id SOSI_int32, LANDKODE SOSI_char(2), GYLDIG_FRA SOSI_char(255), LINK SOSI_char(255), DATAFANGSTDATO SOSI_datetime, STATUS SOSI_char(2), LOVREF SOSI_char(255), SOSI_guid SOSI_char(36), NAVN SOSI_char(60), INFORMASJON SOSI_char(255), OBJTYPE SOSI_char(32), AREAL_KM2 SOSI_char(255), OPPDATERINGSDATO SOSI_datetime
    -> SpatialFilter [input 1]
Sjoterritorium (reader SOSI_1)
    attributes: SOSI_id SOSI_int32, LANDKODE SOSI_char(2), GYLDIG_FRA SOSI_char(255), LINK SOSI_char(255), DATAFANGSTDATO SOSI_datetime, STATUS SOSI_char(2), LOVREF SOSI_char(255), SOSI_guid SOSI_char(36), NAVN SOSI_char(60), INFORMASJON SOSI_char(255), OBJTYPE SOSI_char(32), AREAL_KM2 SOSI_char(255), OPPDATERINGSDATO SOSI_datetime
    -> SpatialFilter [input 1]
Kystkontur (reader SOSI_1)
    attributes: SOSI_id SOSI_int32, LANDKODE SOSI_char(2), GYLDIG_FRA SOSI_char(255), LINK SOSI_char(255), DATAFANGSTDATO SOSI_datetime, NOYAKTIGHET SOSI_number(6,0), STATUS SOSI_char(2), LOVREF SOSI_char(255), MALEMETODE SOSI_int16, SOSI_guid SOSI_char(36), NAVN SOSI_char(60), KYSTTYP SOSI_int16, OPPHAV SOSI_char(255), INFORMASJON SOSI_char(255), OBJTYPE SOSI_char(32), OPPDATERINGSDATO SOSI_datetime, KYSTREF SOSI_char(5)
    -> SpatialFilter [input 1]
    -> SpatialFilter_2 [input 1]
Grunnlinjepunkt (reader SOSI_1)
    attributes: SOSI_id SOSI_int32, GRUNNLINJEPUNKTNUMMER SOSI_char(255), INFORMASJON SOSI_char(255), OBJTYPE SOSI_char(32), GRUNNLINJEPUNKTNAVN SOSI_char(255), PUNKTNAVN SOSI_char(255), SOSI_guid SOSI_char(36), GR_TYPE SOSI_int16, PUNKTNUMMER SOSI_char(255)
    -> SpatialFilter [input 1]
GrensepunktSjo (reader SOSI_1)
    attributes: SOSI_id SOSI_int32, INFORMASJON SOSI_char(255), OBJTYPE SOSI_char(32), PUNKTNAVN SOSI_char(255), SOSI_guid SOSI_char(36), GR_TYPE SOSI_int16, PUNKTNUMMER SOSI_char(255)
    -> SpatialFilter [input 1]
Fiskerisone (reader SOSI_1)
    attributes: SOSI_id SOSI_int32, LANDKODE SOSI_char(2), GYLDIG_FRA SOSI_char(255), LINK SOSI_char(255), DATAFANGSTDATO SOSI_datetime, STATUS SOSI_char(2), LOVREF SOSI_char(255), SOSI_guid SOSI_char(36), NAVN SOSI_char(60), INFORMASJON SOSI_char(255), OBJTYPE SOSI_char(32), AREAL_KM2 SOSI_char(255), OPPDATERINGSDATO SOSI_datetime
    -> SpatialFilter [input 1]
Territorialfarvann (reader SOSI_1)
    attributes: SOSI_id SOSI_int32, LANDKODE SOSI_char(2), GYLDIG_FRA SOSI_char(255), LINK SOSI_char(255), DATAFANGSTDATO SOSI_datetime, STATUS SOSI_char(2), LOVREF SOSI_char(255), SOSI_guid SOSI_char(36), NAVN SOSI_char(60), INFORMASJON SOSI_char(255), OBJTYPE SOSI_char(32), AREAL_KM2 SOSI_char(255), OPPDATERINGSDATO SOSI_datetime
    -> SpatialFilter [input 1]
TilstotendeSone (reader SOSI_1)
    attributes: SOSI_id SOSI_int32, OPPDATERINGSDATO SOSI_datetime, NAVN SOSI_char(60), GYLDIG_FRA SOSI_char(255), INFORMASJON SOSI_char(255), LINK SOSI_char(255), LANDKODE SOSI_char(2), DATAFANGSTDATO SOSI_datetime, LOVREF SOSI_char(255), OBJTYPE SOSI_char(32), STATUS SOSI_char(2)
    -> SpatialFilter [input 1]
IndreFarvann (reader SOSI_1)
    attributes: SOSI_id SOSI_int32, LANDKODE SOSI_char(2), GYLDIG_FRA SOSI_char(255), LINK SOSI_char(255), DATAFANGSTDATO SOSI_datetime, STATUS SOSI_char(2), LOVREF SOSI_char(255), SOSI_guid SOSI_char(36), NAVN SOSI_char(60), INFORMASJON SOSI_char(255), OBJTYPE SOSI_char(32), AREAL_KM2 SOSI_char(255), OPPDATERINGSDATO SOSI_datetime
    -> SpatialFilter [input 1]
Grunnlinje (reader SOSI_1)
    attributes: SOSI_id SOSI_int32, LANDKODE SOSI_char(2), GYLDIG_FRA SOSI_char(255), LINK SOSI_char(255), DATAFANGSTDATO SOSI_datetime, NOYAKTIGHET SOSI_number(6,0), STATUS SOSI_char(2), LOVREF SOSI_char(255), MALEMETODE SOSI_int16, SOSI_guid SOSI_char(36), NAVN SOSI_char(60), INFORMASJON SOSI_char(255), OBJTYPE SOSI_char(32), OPPDATERINGSDATO SOSI_datetime
    -> SpatialFilter [input 1]
Fiskerigrense (reader SOSI_1)
    attributes: SOSI_id SOSI_int32, LANDKODE SOSI_char(2), LINK SOSI_char(255), NOYAKTIGHET SOSI_number(6,0), STATUS SOSI_char(2), LOVREF SOSI_char(255), MALEMETODE SOSI_int16, SOSI_guid SOSI_char(36), NAVN SOSI_char(60), INFORMASJON SOSI_char(255), SONENAUT SOSI_int16, OBJTYPE SOSI_char(32), OPPDATERINGSDATO SOSI_datetime
    -> SpatialFilter [input 1]
Kontinentalsokkel (reader SOSI_1)
    attributes: SOSI_id SOSI_int32, LANDKODE SOSI_char(2), GYLDIG_FRA SOSI_char(255), LINK SOSI_char(255), DATAFANGSTDATO SOSI_datetime, STATUS SOSI_char(2), LOVREF SOSI_char(255), SOSI_guid SOSI_char(36), NAVN SOSI_char(60), INFORMASJON SOSI_char(255), OBJTYPE SOSI_char(32), AREAL_KM2 SOSI_char(255), OPPDATERINGSDATO SOSI_datetime
    -> SpatialFilter [input 1]
GrenseSjo (reader SOSI_1)
    attributes: SOSI_id SOSI_int32, LANDKODE SOSI_char(2), GYLDIG_FRA SOSI_char(255), GR_TYPE SOSI_int16, LINK SOSI_char(255), DATAFANGSTDATO SOSI_datetime, NOYAKTIGHET SOSI_number(6,0), STATUS SOSI_char(2), LOVREF SOSI_char(255), MALEMETODE SOSI_int16, SOSI_guid SOSI_char(36), NAVN SOSI_char(60), INFORMASJON SOSI_char(255), OBJTYPE SOSI_char(32), OPPDATERINGSDATO SOSI_datetime
    -> SpatialFilter [input 1]

Bookmark: Norges maritime grenser
SpatialFilter
    CURVE_BOUNDARY_RULE_PARAM = Default Rule
    PASS_CRITERIA = Pass Against One Filter
    USE_BOUNDING_BOX = No
    PREDICATE_VALUE = Intersects
    PREDATTR = _predicate
    BASE_TYPE = Multiple Filters
    MERGE_ATTRS = Yes
    PASSED -> AttributeCreator_4
    FAILED -> AttributeCreator_5
AttributeCreator_4
    ATTR_LIST = sk_norgesmargrenser,1
    -> dekningsoversikt.dekningsoversikt (writer POSTGIS_2)
AttributeCreator_5
    ATTR_LIST = sk_norgesmargrenser,0
    -> dekningsoversikt.dekningsoversikt (writer POSTGIS_2)

Bookmark: Sjøkartraster
SpatialFilter_2
    CURVE_BOUNDARY_RULE_PARAM = Default Rule
    PASS_CRITERIA = Pass Against One Filter
    USE_BOUNDING_BOX = No
    PREDICATE_VALUE = Intersects
    PREDATTR = _predicate
    BASE_TYPE = Multiple Filters
    MERGE_ATTRS = Yes
    PASSED -> AttributeCreator_6
    FAILED -> AttributeCreator_7
AttributeCreator_6
    ATTR_LIST = sk_sjokartraster,1
    -> dekningsoversikt.dekningsoversikt (writer POSTGIS_2)
AttributeCreator_7
    ATTR_LIST = sk_sjokartraster,0
    -> dekningsoversikt.dekningsoversikt (writer POSTGIS_2)
