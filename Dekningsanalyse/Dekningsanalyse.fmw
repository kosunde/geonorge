FME workspace Dekningsanalyse.fmw

Parameters:
- DestDataset_POSTGIS = geonortst@nnridb504:5432/geonor01tst   # Connection
- SourceDataset_CSV = $(FME_MF_DIR)Temp_data\EksplosivAnlegg.txt   # Source CSV (CommaSeparatedValue) File(s)
- SourceDataset_CSV_5 = $(FME_MF_DIR)Temp_data\FarligStoffAnlegg.txt   # Source CSV (CommaSeparatedValue) File(s)
- SourceDataset_CSV_7 = $(FME_MF_DIR)Temp_data\Anlegg pr kommune Storulykkeanlegg.txt   # Source CSV (CommaSeparatedValue) File(s)
- SourceDataset_CSV_6 = $(FME_MF_DIR)Temp_data\kommunermedjordkvalitet.txt   # Source CSV (CommaSeparatedValue) File(s)
- SourceDataset_POSTGIS = geonortst@nnridb504:5432/geonor01tst   # Connection
- SourceDataset_WFS_5 = http://kart.fiskeridir.no/wfs.aspx?SERVICE=WFS&amp;VERSION=1.0.0&amp;REQUEST=capabilities   # Source WFS (Web Feature Service) URL
- SourceDataset_WFS_6 = http://maps.imr.no/geoserver/ows?service=wfs   # Source WFS (Web Feature Service) URL
- SourceDataset_WFS_7 = http://kart.dsb.no/wfs.aspx?service=wfs&request=getcapabilities   # Source WFS (Web Feature Service) URL
- SourceDataset_ESRIJSON = http://askeladden_wms.ra.no/arcgis/rest/services/WMS/RA_Brannvern/MapServer/3/query?where=1%3D1&text=&objectIds=&time=&geometry=&geometryType=esriGeometryEnvelope&inSR=&spatialRel=esriSpatialRelIntersects&relationParam=&outFields=KommuneNummer&returnGeometry=false&maxAllowableOffset=&geometryPrecision=&outSR=&returnIdsOnly=false&returnCountOnly=false&orderByFields=&groupByFieldsForStatistics=&outStatistics=&returnZ=false&returnM=false&gdbVersion=&returnDistinctValues=true&f=pjson   # Source Esri-JSON File or URL
- SourceDataset_ESRIJSON_9 = http://askeladden_wms.ra.no/arcgis/rest/services/WMS/RA_Brannvern/MapServer/2/query?where=1%3D1&text=&objectIds=&time=&geometry=&geometryType=esriGeometryEnvelope&inSR=&spatialRel=esriSpatialRelIntersects&relationParam=&outFields=KommuneNummer&returnGeometry=false&maxAllowableOffset=&geometryPrecision=&outSR=&returnIdsOnly=false&returnCountOnly=false&orderByFields=&groupByFieldsForStatistics=&outStatistics=&returnZ=false&returnM=false&gdbVersion=&returnDistinctValues=true&f=pjson   # Source Esri-JSON File or URL
- SourceDataset_ESRIJSON_13 = http://askeladden_wms.ra.no/arcgis/rest/services/WMS/RA_Askeladden/MapServer/0/query?where=1%3D1&text=&objectIds=&time=&geometry=&geometryType=esriGeometryEnvelope&inSR=&spatialRel=esriSpatialRelIntersects&relationParam=&outFields=KOMM&returnGeometry=false&maxAllowableOffset=&geometryPrecision=&outSR=&returnIdsOnly=false&returnCountOnly=false&orderByFields=&groupByFieldsForStatistics=&outStatistics=&returnZ=false&returnM=false&gdbVersion=&returnDistinctValues=true&f=pjson   # Source Esri-JSON File or URL
- SourceDataset_ESRIJSON_11 = http://askeladden_wms.ra.no/arcgis/rest/services/WMS/RA_Askeladden/MapServer/4/query?where=1%3D1&text=&objectIds=&time=&geometry=&geometryType=esriGeometryEnvelope&inSR=&spatialRel=esriSpatialRelIntersects&relationParam=&outFields=KOMM&returnGeometry=false&maxAllowableOffset=&geometryPrecision=&outSR=&returnIdsOnly=false&returnCountOnly=false&orderByFields=&groupByFieldsForStatistics=&outStatistics=&returnZ=false&returnM=false&gdbVersion=&returnDistinctValues=true&f=pjson   # Source Esri-JSON File or URL
- SourceDataset_ESRIJSON_8 = http://askeladden_wms.ra.no/arcgis/rest/services/WMS/RA_Askeladden/MapServer/7/query?where=1%3D1&text=&objectIds=&time=&geometry=&geometryType=esriGeometryEnvelope&inSR=&spatialRel=esriSpatialRelIntersects&relationParam=&outFields=KOMM&returnGeometry=false&maxAllowableOffset=&geometryPrecision=&outSR=&returnIdsOnly=false&returnCountOnly=false&orderByFields=&groupByFieldsForStatistics=&outStatistics=&returnZ=false&returnM=false&gdbVersion=&returnDistinctValues=true&f=pjson   # Source Esri-JSON File or URL
- SourceDataset_ESRIJSON_10 = http://askeladden_wms.ra.no/arcgis/rest/services/WMS/RA_Askeladden/MapServer/5/query?where=1%3D1&text=&objectIds=&time=&geometry=&geometryType=esriGeometryEnvelope&inSR=&spatialRel=esriSpatialRelIntersects&relationParam=&outFields=KOMM&returnGeometry=false&maxAllowableOffset=&geometryPrecision=&outSR=&returnIdsOnly=false&returnCountOnly=false&orderByFields=&groupByFieldsForStatistics=&outStatistics=&returnZ=false&returnM=false&gdbVersion=&returnDistinctValues=true&f=pjson   # Source Esri-JSON File or URL
- SourceDataset_ESRIJSON_12 = http://askeladden_wms.ra.no/arcgis/rest/services/WMS/RA_Askeladden/MapServer/6/query?where=1%3D1&text=&objectIds=&time=&geometry=&geometryType=esriGeometryEnvelope&inSR=&spatialRel=esriSpatialRelIntersects&relationParam=&outFields=KOMM&returnGeometry=false&maxAllowableOffset=&geometryPrecision=&outSR=&returnIdsOnly=false&returnCountOnly=false&orderByFields=&groupByFieldsForStatistics=&outStatistics=&returnZ=false&returnM=false&gdbVersion=&returnDistinctValues=true&f=pjson   # Source Esri-JSON File or URL
- SourceDataset_WFS = http://153.44.6.24/a3_mapserver/wfs.ashx   # Source WFS (Web Feature Service) URL

Readers:
- POSTGIS_1: POSTGIS from $(SourceDataset_POSTGIS)
- WFS_1: WFS from $(SourceDataset_WFS_5)
- WFS_2: WFS from $(SourceDataset_WFS_6)
- WFS_3: WFS from $(SourceDataset_WFS_7)
- ESRIJSON_1: ESRIJSON from $(SourceDataset_ESRIJSON)
- ESRIJSON_2: ESRIJSON from $(SourceDataset_ESRIJSON_9)
- ESRIJSON_3: ESRIJSON from $(SourceDataset_ESRIJSON_13)
- ESRIJSON_4: ESRIJSON from $(SourceDataset_ESRIJSON_11)
- ESRIJSON_5: ESRIJSON from $(SourceDataset_ESRIJSON_8)
- ESRIJSON_6: ESRIJSON from $(SourceDataset_ESRIJSON_10)
- ESRIJSON_7: ESRIJSON from $(SourceDataset_ESRIJSON_12)
- WFS_4: WFS from $(SourceDataset_WFS)
- CSV_1: CSV from $(SourceDataset_CSV)
- CSV_2: CSV from $(SourceDataset_CSV_5)
- CSV_3: CSV from $(SourceDataset_CSV_7)
- CSV_4: CSV from $(SourceDataset_CSV_6)

Writers:
- POSTGIS_2: POSTGIS to $(DestDataset_POSTGIS)

admingrense.kommuneflate (reader POSTGIS_1)
    attributes: kommuneid int4
    -> Reprojector
Reprojector
    RASTER_CELL_SIZE = Preserve Cells
    SOURCE = Read from feature
    INTERPOLATION_TYPE_NAME = Nearest Neighbor
    DEST = EPSG:32633
    REPROJECTED -> Deaggregator
Deaggregator
    LIST_ATTR_MODE_LOOKUP = LEAN
    ID_SELECTION = ID and Parent ID
    MODE = Flatten One Level
    PART_NUMBER_FIELD = _part_number
    COPY_ATTR = Every Node
    ID_ATTR = _hierarchy_id
    GEOM_NAME_FIELD = _geometry_name
    SPLIT_COMPOSITES = No
    PARENT_ID_ATTR = _hierarchy_parent_id
    EXPLODE_INSTANCES = No
    CHILD_ID_ATTR = _hierarchy_child_id_list
    DEAGGREGATED -> GeometryCoercer
GeometryCoercer
    GQUERY:
      for $geom in //geometry
      where $geom/count(parent::geometry) = 0
      return number($geom/@fme_id)
    KIND = fme_polygon
    COERCED -> SpatialFilter [input 2]
    COERCED -> SpatialFilter_2 [input 2]
    UNTOUCHED -> SpatialFilter_2 [input 2]
    COERCED -> SpatialFilter_3 [input 2]
    COERCED -> SpatialFilter_4 [input 2]
    UNTOUCHED -> SpatialFilter_4 [input 2]
    COERCED -> SpatialFilter_5 [input 2]
    UNTOUCHED -> SpatialFilter_5 [input 2]
    COERCED -> SpatialFilter_6 [input 2]
    UNTOUCHED -> SpatialFilter_6 [input 2]
    UNTOUCHED -> SpatialFilter [input 2]
    UNTOUCHED -> SpatialFilter_3 [input 2]
    COERCED -> GeometryRemover
    UNTOUCHED -> GeometryRemover
    UNTOUCHED -> SpatialFilter_7 [input 2]
    COERCED -> SpatialFilter_7 [input 2]
    COERCED -> SpatialFilter_8 [input 2]
    UNTOUCHED -> SpatialFilter_8 [input 2]
    COERCED -> SpatialFilter_9 [input 2]
    UNTOUCHED -> SpatialFilter_9 [input 2]
    COERCED -> SpatialFilter_10 [input 2]
    UNTOUCHED -> SpatialFilter_10 [input 2]
Note: Jordkvalitet NIBIO
CSV (reader CSV_4)
    attributes: col0 number(5,0)
    -> FeatureMerger_11 [input 2]
FeatureMerger_11 [off]
    IGNORE_NULLS = No
    MERGE_TYPE = Attributes Only
    SUPPLIERS_FIRST = No
    ATTR_CONFLICT_RES = Use Requestor
    PROCESS_DUPS = No
    ATTR_ACCUM_MODE = Merge Supplier
    JOIN_KEYS = @Value(kommuneid) @Value(col0) AUTO
    MERGED -> AttributeCreator_41 [off]
    NOT_MERGED -> AttributeCreator_42 [off]
AttributeCreator_41 [off]
    ATTR_LIST = nibio_jordkvalitet,1
    -> Reprojector_3
AttributeCreator_42 [off]
    ATTR_LIST = nibio_jordkvalitet,0
    -> Reprojector_3
Reprojector_3
    RASTER_CELL_SIZE = Preserve Cells
    SOURCE = Read from feature
    INTERPOLATION_TYPE_NAME = Nearest Neighbor
    DEST = EPSG:4258
    REPROJECTED -> dekningsoversikt.dekningsoversikt (writer POSTGIS_2)
dekningsoversikt.dekningsoversikt (writer POSTGIS_2)
    attributes: kommuneid int4,PRIKEY, akvakultur bool, dsb_sivforsvdistr bool, korallrev bool, dsb_brannstasjon bool, dsb_110sentral bool, dsb_distrkont_siv bool, ra_brannsmitteomr bool, ra_tettetrehusm bool, ra_frededebygg bool, ra_enkeltminner bool, ra_kulturmiljo bool, ra_lokaliteter bool, ra_sikringssoner bool, kv_hovedbiled bool, kv_ispshavneanlegg bool, kv_losbordingsfelt bool, kv_losstasjoner bool, nve_flomsoner10 bool, nve_flomsoner20 bool, nve_flomsoner50 bool, nve_flomsoner100 bool, nve_flomsoner200 bool, nve_flomsoner500 bool, nve_flomsoner1000 bool, nve_flomsoner200_i_aar2100 bool, nve_flomsonekartplan bool, nve_elvis_hovedelv bool, nve_elvis_elvenett bool, nve_innsjodata bool,
      nve_dybdekart bool, nve_nedborfelt_regine bool, nve_vassdragsomrade bool, nve_totnedbfelt_mstasjon bool, nve_vannkraftverk bool, nve_vindparkomrader bool, nve_vindturbin bool, nve_kraftlinjer bool, nve_sjokabler bool, nve_transformatorstasjoner bool, nve_omradekonsesjoner bool, nve_sikringstiltak bool, nve_verneplan_vassdrag bool, nve_kvikkleire bool, nve_aktsomhet_snoskred bool, nve_aktsomhet_steinsprang bool, nve_aktsomhet_snosteinsprang bool, nve_aktsomhet_jordflomskred bool, nve_skredhendelser bool, nve_kraftverk_alle_kst bool, nve_magasin bool, nve_dam bool, nve_vanninntak bool, nve_vannvei bool, nve_delfelt_vannkraft bool, nve_vindkraftverk bool, nve_skredsoner bool, dsb_anleggfarligstoff bool, dsb_storulykkeanlegg bool, dsb_eksplosivanlegg bool,
      nibio_jordkvalitet bool, md_forurensetgrunn bool, md_frilstatligsikra bool, md_frilkartlverds bool, md_verdif_kulturlandsk bool, md_viktige_naturt bool, md_villreinomr bool, md_naturvernomr bool, md_naturvernomr_foresl bool, md_arter_nasjon_forv bool, md_naturt_landskap bool, md_naturt_utv bool, fkb_ar5 bool, fkb_adresse bool, fkb_arealbruk bool, fkb_bane bool, fkb_bygnanlegg bool, fkb_bygning bool, fkb_bygningspunkt bool, fkb_hoydekurve-5m bool, fkb_hoydekurve bool, fkb_ledning bool, fkb_ledningva bool, fkb_lufthavn bool, fkb_matrikkelkartdekteig bool, fkb_naturinfo bool, fkb_pbltiltak bool, fkb_servitutt bool, fkb_tekst1000 bool, fkb_tekst5000 bool,
      fkb_traktorvegsti bool, fkb_vann bool, fkb_vbase bool, fkb_veg bool, ldir_reinbeitedistrikt bool, ldir_reinbeiteomrade bool, ldir_reindriftsanlegg bool, ldir_beitehage bool, ldir_flyttlei bool, ldir_trekklei bool, ldir_oppsamlingsomrade bool, ldir_varbeite bool, ldir_sommerbeite bool, ldir_hostbeite bool, ldir_hostvinterbeite bool, ldir_vinterbeite bool, ldir_siidagrense bool, ldir_konvensjonsomrade bool, ldir_konsesjonsomrader bool, ldir_restriksjonsomrader bool, ldir_tamreinlag bool, ldir_restriksjonsgrense bool, ldir_rendal bool, ldir_trollheimen bool, ldir_avtaleomrader bool, ldir_ekspropriasjonsomrader bool, avinor_stoysoner bool, forsvaret_stoysoner bool, matrikkel_vegadresser bool, nibio_ar50 bool,
      sk_vbase bool, sk_n50 bool, sk_n250 bool, sk_n500 bool, sk_n1000 bool, sk_n5000 bool, sk_ssr bool, sk_abas bool, matrikkel_bygningspunkt bool, matrikkel_eiendom bool, ngu_losmasser bool

Bookmark: Riksantikvaren
GeometryRemover
    -> FeatureMerger [input 1]
    -> FeatureMerger_7 [input 1]
    -> FeatureMerger_2 [input 1]
    -> FeatureMerger_3 [input 1]
    -> FeatureMerger_4 [input 1]
    -> FeatureMerger_5 [input 1]
    -> FeatureMerger_6 [input 1]
    -> FeatureMerger_8 [input 1]
    -> FeatureMerger_9 [input 1]
    -> FeatureMerger_10 [input 1]
    -> FeatureMerger_11 [input 1]
Note: Brannsmitteområder RA
ESRIJSON (reader ESRIJSON_2)
    attributes: Kommunenummer string
    -> FeatureMerger [input 2]
FeatureMerger
    IGNORE_NULLS = No
    MERGE_TYPE = Attributes Only
    SUPPLIERS_FIRST = No
    ATTR_CONFLICT_RES = Use Requestor
    PROCESS_DUPS = No
    ATTR_ACCUM_MODE = Merge Supplier
    JOIN_KEYS = @Value(kommuneid) @Value(Kommunenummer) AUTO
    MERGED -> AttributeCreator_13
    NOT_MERGED -> AttributeCreator_14
AttributeCreator_13
    ATTR_LIST = ra_brannsmitteomr,1
    -> Reprojector_3
AttributeCreator_14
    ATTR_LIST = ra_brannsmitteomr,0
    -> Reprojector_3
Note: Tette Trehusmiljø RA
ESRIJSON (reader ESRIJSON_1)
    attributes: Kommunenummer string
    -> FeatureMerger_2 [input 2]
FeatureMerger_2
    IGNORE_NULLS = No
    MERGE_TYPE = Attributes Only
    SUPPLIERS_FIRST = No
    ATTR_CONFLICT_RES = Use Requestor
    PROCESS_DUPS = No
    ATTR_ACCUM_MODE = Merge Supplier
    JOIN_KEYS = @Value(kommuneid) @Value(Kommunenummer) AUTO
    NOT_MERGED -> AttributeCreator_16
    MERGED -> AttributeCreator_15
AttributeCreator_15
    ATTR_LIST = ra_tettetrehusm,1
    -> Reprojector_3
AttributeCreator_16
    ATTR_LIST = ra_tettetrehusm,0
    -> Reprojector_3
Note: Fredede bygninger RA
ESRIJSON (reader ESRIJSON_3)
    attributes: KOMM int
    -> FeatureMerger_3 [input 2]
FeatureMerger_3
    IGNORE_NULLS = No
    MERGE_TYPE = Attributes Only
    SUPPLIERS_FIRST = No
    ATTR_CONFLICT_RES = Use Requestor
    PROCESS_DUPS = No
    ATTR_ACCUM_MODE = Merge Supplier
    JOIN_KEYS = @Value(kommuneid) @Value(KOMM) AUTO
    NOT_MERGED -> AttributeCreator_18
    MERGED -> AttributeCreator_17
AttributeCreator_17
    ATTR_LIST = ra_frededebygg,1
    -> Reprojector_3
AttributeCreator_18
    ATTR_LIST = ra_frededebygg,0
    -> Reprojector_3
Note: Enkeltminner RA
ESRIJSON (reader ESRIJSON_4)
    attributes: KOMM string
    -> FeatureMerger_4 [input 2]
FeatureMerger_4
    IGNORE_NULLS = No
    MERGE_TYPE = Attributes Only
    SUPPLIERS_FIRST = No
    ATTR_CONFLICT_RES = Use Requestor
    PROCESS_DUPS = No
    ATTR_ACCUM_MODE = Merge Supplier
    JOIN_KEYS = @Value(kommuneid) @Value(KOMM) AUTO
    NOT_MERGED -> AttributeCreator_20
    MERGED -> AttributeCreator_19
AttributeCreator_19
    ATTR_LIST = ra_enkeltminner,1
    -> Reprojector_3
AttributeCreator_20
    ATTR_LIST = ra_enkeltminner,0
    -> Reprojector_3
Note: Kulturmiljø RA
ESRIJSON (reader ESRIJSON_5)
    attributes: KOMM int
    -> FeatureMerger_5 [input 2]
FeatureMerger_5
    IGNORE_NULLS = No
    MERGE_TYPE = Attributes Only
    SUPPLIERS_FIRST = No
    ATTR_CONFLICT_RES = Use Requestor
    PROCESS_DUPS = No
    ATTR_ACCUM_MODE = Merge Supplier
    JOIN_KEYS = @Value(kommuneid) @Value(KOMM) AUTO
    NOT_MERGED -> AttributeCreator_22
    MERGED -> AttributeCreator_21
AttributeCreator_21
    ATTR_LIST = ra_kulturmiljo,1
    -> Reprojector_3
AttributeCreator_22
    ATTR_LIST = ra_kulturmiljo,0
    -> Reprojector_3
Note: Lokaliteter RA
ESRIJSON (reader ESRIJSON_6)
    attributes: KOMM int
    -> FeatureMerger_6 [input 2]
FeatureMerger_6
    IGNORE_NULLS = No
    MERGE_TYPE = Attributes Only
    SUPPLIERS_FIRST = No
    ATTR_CONFLICT_RES = Use Requestor
    PROCESS_DUPS = No
    ATTR_ACCUM_MODE = Merge Supplier
    JOIN_KEYS = @Value(kommuneid) @Value(KOMM) AUTO
    NOT_MERGED -> AttributeCreator_24
    MERGED -> AttributeCreator_23
AttributeCreator_23
    ATTR_LIST = ra_lokaliteter,1
    -> Reprojector_3
AttributeCreator_24
    ATTR_LIST = ra_lokaliteter,0
    -> Reprojector_3
Note: Sikringssoner RA
ESRIJSON (reader ESRIJSON_7)
    attributes: KOMM int
    -> FeatureMerger_7 [input 2]
FeatureMerger_7
    IGNORE_NULLS = No
    MERGE_TYPE = Attributes Only
    SUPPLIERS_FIRST = No
    ATTR_CONFLICT_RES = Use Requestor
    PROCESS_DUPS = No
    ATTR_ACCUM_MODE = Merge Supplier
    JOIN_KEYS = @Value(kommuneid) @Value(KOMM) AUTO
    MERGED -> AttributeCreator_25
    NOT_MERGED -> AttributeCreator_26
AttributeCreator_25
    ATTR_LIST = ra_sikringssoner,1
    -> Reprojector_3
AttributeCreator_26
    ATTR_LIST = ra_sikringssoner,0
    -> Reprojector_3

Bookmark: WFS-data
layer_92 (reader WFS_1)
    attributes: gml_parent_id xml_buffer, gml_parent_property xml_buffer, gml_id xml_buffer, msGeometry xml_geometry, id xml_buffer, navn xml_buffer, areal_m2 xml_buffer
    -> SpatialFilter [input 1]
layer_553 (reader WFS_1)
    attributes: gml_parent_id xml_buffer, gml_parent_property xml_buffer, gml_id xml_buffer, msGeometry xml_geometry, objectid xml_buffer, loknr xml_buffer, lokalitet xml_buffer, innehaver xml_buffer, organisasjonsnummer xml_buffer, firma_adresse xml_buffer, firma_poststed xml_buffer, post_adresse xml_buffer, post_poststed xml_buffer, tillatelsesnr xml_buffer, kapasitet xml_buffer, art xml_buffer, produksjon xml_buffer, formaal xml_buffer, plassering xml_buffer, vannmiljo xml_buffer, geom xml_buffer, av_class xml_buffer, tillatelse_html xml_buffer, geom_25833 xml_buffer
    -> SpatialFilter [input 1]
layer_245 (reader WFS_1)
    attributes: gml_parent_id xml_buffer, gml_parent_property xml_buffer, gml_id xml_buffer, msGeometry xml_geometry, loknr xml_buffer, lokalitet xml_buffer, tillatelsesnr xml_buffer, art xml_buffer, kapasitet xml_buffer, navn xml_buffer, produksjon xml_buffer, formaal xml_buffer, loktilstand xml_buffer, mudato xml_buffer, uri xml_buffer, plassering xml_buffer, prodorgnavn xml_buffer, miljoundersokelse_type xml_buffer, av_class xml_buffer
    -> SpatialFilter [input 1]
layer_460 (reader WFS_1)
    attributes: gml_parent_id xml_buffer, gml_parent_property xml_buffer, gml_id xml_buffer, msGeometry xml_geometry, loknr xml_buffer, lokalitet xml_buffer, tillatelsesnr xml_buffer, art xml_buffer, kapasitet xml_buffer, navn xml_buffer, produksjon xml_buffer, formaal xml_buffer, mudato xml_buffer, uri xml_buffer, plassering xml_buffer, prodorgnavn xml_buffer, miljoundersokelse_type xml_buffer, av_class xml_buffer
    -> SpatialFilter [input 1]

Bookmark: Akvakultur
SpatialFilter
    PREDICATE_VALUE = Intersects
    MERGE_ATTRS = Yes
    BASE_TYPE = Multiple Filters
    PASS_CRITERIA = Pass Against One Filter
    CURVE_BOUNDARY_RULE_PARAM = Default Rule
    PREDATTR = _predicate
    USE_BOUNDING_BOX = No
    PASSED -> AttributeCreator
    FAILED -> AttributeCreator_2
AttributeCreator
    ATTR_LIST = akvakultur,1
    -> Reprojector_3
AttributeCreator_2
    ATTR_LIST = akvakultur,0
    -> Reprojector_3

Bookmark: Kystverket
Note: Hoved - og biled
layer_37 (reader WFS_4)
    attributes: gml_parent_id xml_buffer, gml_parent_property xml_buffer, gml_id xml_buffer, msGeometry xml_geometry, navn xml_buffer, uuid xml_buffer, farlednummer xml_buffer, delstreknavn xml_buffer, farledpaabud xml_buffer, farledtype xml_buffer, farledstatus xml_buffer, kyv_region xml_buffer, lengde xml_buffer, datafangstdato xml_buffer, oppdateringsdato xml_buffer, gyldig_fra xml_buffer, gyldig_til xml_buffer, informasjon xml_buffer, maalemetode xml_buffer, noyaktighet xml_buffer, orginaldatavert xml_buffer, opphav xml_buffer, kopidato xml_buffer, id xml_buffer
    -> Deaggregator_2
Deaggregator_2
    LIST_ATTR_MODE_LOOKUP = LEAN
    MODE = Flatten All Levels
    GEOM_NAME_FIELD = _geometry_name
    SPLIT_COMPOSITES = No
    EXPLODE_INSTANCES = No
    DEAGGREGATED -> SpatialFilter_7 [input 1]
SpatialFilter_7
    PREDICATE_VALUE = Intersects
    MERGE_ATTRS = Yes
    BASE_TYPE = Multiple Filters
    PASS_CRITERIA = Pass Against One Filter
    CURVE_BOUNDARY_RULE_PARAM = Default Rule
    PREDATTR = _predicate
    USE_BOUNDING_BOX = No
    PASSED -> AttributeCreator_27
    FAILED -> AttributeCreator_28
AttributeCreator_27
    ATTR_LIST = kv_hovedbiled,1
    -> Reprojector_3
AttributeCreator_28
    ATTR_LIST = kv_hovedbiled,0
    -> Reprojector_3
Note: ISPS havneanlegg
layer_28 (reader WFS_4)
    attributes: gml_parent_id xml_buffer, gml_parent_property xml_buffer, gml_id xml_buffer, msGeometry xml_geometry, Cluster:FeatureCount xml_buffer, Cluster:Group xml_buffer
    -> SpatialFilter_8 [input 1]
SpatialFilter_8
    PREDICATE_VALUE = Intersects
    MERGE_ATTRS = Yes
    BASE_TYPE = Multiple Filters
    PASS_CRITERIA = Pass Against One Filter
    CURVE_BOUNDARY_RULE_PARAM = Default Rule
    PREDATTR = _predicate
    USE_BOUNDING_BOX = No
    PASSED -> AttributeCreator_29
    FAILED -> AttributeCreator_30
AttributeCreator_29
    ATTR_LIST = kv_ispshavneanlegg,1
    -> Reprojector_3
AttributeCreator_30
    ATTR_LIST = kv_ispshavneanlegg,0
    -> Reprojector_3
Note: Losbordingsfelt
layer_29 (reader WFS_4)
    attributes: gml_parent_id xml_buffer, gml_parent_property xml_buffer, gml_id xml_buffer, msGeometry xml_geometry, losbordingsfelt xml_buffer, nord xml_buffer, ost xml_buffer, kommune xml_buffer, merknad_begrensning xml_buffer, merknad2 xml_buffer, sjotrafikkomraade xml_buffer, uuid xml_buffer, datafangstdato xml_buffer, oppdateringsdato xml_buffer, gyldig_fra xml_buffer, gyldig_til xml_buffer, informasjon xml_buffer, maalemetode xml_buffer, noyaktighet xml_buffer, originaldatavert xml_buffer, opphav xml_buffer, kopidato xml_buffer, id xml_buffer
    -> SpatialFilter_9 [input 1]
SpatialFilter_9
    PREDICATE_VALUE = Intersects
    MERGE_ATTRS = Yes
    BASE_TYPE = Multiple Filters
    PASS_CRITERIA = Pass Against One Filter
    CURVE_BOUNDARY_RULE_PARAM = Default Rule
    PREDATTR = _predicate
    USE_BOUNDING_BOX = No
    PASSED -> AttributeCreator_31
    FAILED -> AttributeCreator_32
AttributeCreator_31
    ATTR_LIST = kv_losbordingsfelt,1
    -> Reprojector_3
AttributeCreator_32
    ATTR_LIST = kv_losbordingsfelt,0
    -> Reprojector_3
Note: Losstasjoner
layer_59 (reader WFS_4)
    attributes: gml_parent_id xml_buffer, gml_parent_property xml_buffer, gml_id xml_buffer, msGeometry xml_geometry, gid xml_buffer, navn xml_buffer, dato xml_buffer, funksjon xml_buffer, distrikt xml_buffer, los1 xml_buffer, los2 xml_buffer
    -> SpatialFilter_10 [input 1]
SpatialFilter_10
    PREDICATE_VALUE = Intersects
    MERGE_ATTRS = Yes
    BASE_TYPE = Multiple Filters
    PASS_CRITERIA = Pass Against One Filter
    CURVE_BOUNDARY_RULE_PARAM = Default Rule
    PREDATTR = _predicate
    USE_BOUNDING_BOX = No
    PASSED -> AttributeCreator_33
    FAILED -> AttributeCreator_34
AttributeCreator_33
    ATTR_LIST = kv_losstasjoner,1
    -> Reprojector_3
AttributeCreator_34
    ATTR_LIST = kv_losstasjoner,0
    -> Reprojector_3

Bookmark: WFS-data
Note: Sivilforsvarsdistrikt
layer_307 (reader WFS_3)
    attributes: gml_parent_id xml_buffer, gml_parent_property xml_buffer, gml_id xml_buffer, msGeometry xml_geometry, SIVDISTRIK xml_buffer, URL xml_buffer, NAVN xml_buffer
    -> SpatialFilter_2 [input 1]
Note: Distriktskontor sivilforsvaret
layer_309 (reader WFS_3)
    attributes: gml_parent_id xml_buffer, gml_parent_property xml_buffer, gml_id xml_buffer, msGeometry xml_geometry, TYPE xml_buffer, KOMMUNE xml_buffer, URL xml_buffer, NAVN xml_buffer, DATO xml_buffer
    -> SpatialFilter_4 [input 1]
Note: Brannstasjoner
layer_511 (reader WFS_3)
    attributes: gml_parent_id xml_buffer, gml_parent_property xml_buffer, gml_id xml_buffer, msGeometry xml_geometry, BRANNSTASJ xml_buffer, KASERNERT xml_buffer, BRANNVESEN xml_buffer, ANLEGGID xml_buffer, AJOURDATO xml_buffer, INFORMASJ xml_buffer, OPPHAV xml_buffer, STASJONSTY xml_buffer, OBJTYPE xml_buffer, DATO xml_buffer, BRANNSTA_ xml_buffer
    -> SpatialFilter_5 [input 1]
Note: 110-sentraldistrikter
layer_562 (reader WFS_3)
    attributes: gml_parent_id xml_buffer, gml_parent_property xml_buffer, gml_id xml_buffer, msGeometry xml_geometry, POLY_ xml_buffer, POLY_ID xml_buffer, AREA xml_buffer, PERIMETER xml_buffer, OPPR xml_buffer, X xml_buffer, Y xml_buffer, KOORDH xml_buffer, SENTRAL xml_buffer, LOKALISERI xml_buffer, OPPHAV xml_buffer, MALEMETODE xml_buffer, NOYAKTIGHE xml_buffer, SYNBARHET xml_buffer, H_MALEMETO xml_buffer, H_NOYAKTIG xml_buffer, MAX_AVVIK xml_buffer, OBJTYPE xml_buffer, NAVN xml_buffer, DATO xml_buffer
    -> SpatialFilter_6 [input 1]

Bookmark: DSB
SpatialFilter_2
    PREDICATE_VALUE = Intersects
    MERGE_ATTRS = Yes
    BASE_TYPE = Multiple Filters
    PASS_CRITERIA = Pass Against One Filter
    CURVE_BOUNDARY_RULE_PARAM = Default Rule
    PREDATTR = _predicate
    USE_BOUNDING_BOX = No
    PASSED -> AttributeCreator_3
    FAILED -> AttributeCreator_4
AttributeCreator_3
    ATTR_LIST = dsb_sivforsvdistr,1
    -> Reprojector_3
AttributeCreator_4
    ATTR_LIST = dsb_sivforsvdistr,0
    -> Reprojector_3
SpatialFilter_4
    PREDICATE_VALUE = Intersects
    MERGE_ATTRS = Yes
    BASE_TYPE = Multiple Filters
    PASS_CRITERIA = Pass Against One Filter
    CURVE_BOUNDARY_RULE_PARAM = Default Rule
    PREDATTR = _predicate
    USE_BOUNDING_BOX = No
    PASSED -> AttributeCreator_7
    FAILED -> AttributeCreator_8
AttributeCreator_7
    ATTR_LIST = dsb_distrkont_siv,1
    -> Reprojector_3
AttributeCreator_8
    ATTR_LIST = dsb_distrkont_siv,0
    -> Reprojector_3
SpatialFilter_5
    PREDICATE_VALUE = Intersects
    MERGE_ATTRS = Yes
    BASE_TYPE = Multiple Filters
    PASS_CRITERIA = Pass Against One Filter
    CURVE_BOUNDARY_RULE_PARAM = Default Rule
    PREDATTR = _predicate
    USE_BOUNDING_BOX = No
    PASSED -> AttributeCreator_9
    FAILED -> AttributeCreator_10
AttributeCreator_9
    ATTR_LIST = dsb_brannstasjon,1
    -> Reprojector_3
AttributeCreator_10
    ATTR_LIST = dsb_brannstasjon,0
    -> Reprojector_3
SpatialFilter_6
    PREDICATE_VALUE = Intersects
    MERGE_ATTRS = Yes
    BASE_TYPE = Multiple Filters
    PASS_CRITERIA = Pass Against One Filter
    CURVE_BOUNDARY_RULE_PARAM = Default Rule
    PREDATTR = _predicate
    USE_BOUNDING_BOX = No
    PASSED -> AttributeCreator_11
    FAILED -> AttributeCreator_12
AttributeCreator_11
    ATTR_LIST = dsb_110sentral,1
    -> Reprojector_3
AttributeCreator_12
    ATTR_LIST = dsb_110sentral,0
    -> Reprojector_3

Bookmark: WFS-data
coralreefs (reader WFS_2)
    attributes: gml_parent_id xml_buffer, gml_parent_property xml_buffer, gml_id xml_buffer, the_geom xml_geometry, Nummer_uni xml_real64, Nummer_uni.xsi_nil xml_boolean, Habitat_Ty xml_buffer, Habitat_Ty.xsi_nil xml_boolean, Verifisert xml_buffer, Verifisert.xsi_nil xml_boolean, Verifise_1 xml_buffer, Verifise_1.xsi_nil xml_boolean, Observasjo xml_buffer, Observasjo.xsi_nil xml_boolean, Observas_1 xml_buffer, Observas_1.xsi_nil xml_boolean, Observas_2 xml_buffer, Observas_2.xsi_nil xml_boolean, Steds_Navn xml_buffer, Steds_Navn.xsi_nil xml_boolean, Breddegrad xml_real64, Breddegrad.xsi_nil xml_boolean, Lengdegrad xml_real64, Lengdegrad.xsi_nil xml_boolean, Posisjon_T xml_buffer, Posisjon_T.xsi_nil xml_boolean, Nøyaktigh xml_real64, Nøyaktigh.xsi_nil xml_boolean, Referanse xml_buffer, Referanse.xsi_nil xml_boolean,
      Metode xml_buffer, Metode.xsi_nil xml_boolean, Dybde_Øvr xml_real64, Dybde_Øvr.xsi_nil xml_boolean, Dybde_Nedr xml_real64, Dybde_Nedr.xsi_nil xml_boolean, Kilde xml_buffer, Kilde.xsi_nil xml_boolean
    -> Reprojector_2

Bookmark: Havforskningsinstituttet
Reprojector_2
    RASTER_CELL_SIZE = Preserve Cells
    SOURCE = Read from feature
    INTERPOLATION_TYPE_NAME = Nearest Neighbor
    DEST = EPSG:32633
    REPROJECTED -> SpatialFilter_3 [input 1]
SpatialFilter_3
    PREDICATE_VALUE = Intersects
    MERGE_ATTRS = Yes
    BASE_TYPE = Multiple Filters
    PASS_CRITERIA = Pass Against One Filter
    CURVE_BOUNDARY_RULE_PARAM = Default Rule
    PREDATTR = _predicate
    USE_BOUNDING_BOX = No
    PASSED -> AttributeCreator_5
    FAILED -> AttributeCreator_6
AttributeCreator_5
    ATTR_LIST = korallrev,1
    -> Reprojector_3
AttributeCreator_6
    ATTR_LIST = korallrev,0
    -> Reprojector_3

Bookmark: DSB_
Note: Eksplosivanlegg
CSV (reader CSV_1)
    attributes: col0 number(3,0), col1 char(7), col2 number(5,0)
    -> Tester
Tester
    BOOL_OP = OR
    TEST_MODE = Automatic
    TEST_CLAUSE = TEST @Value(col2) BEGINS_WITH 0
    TEST_DESCRIPTION = ""
    PASSED -> SubstringExtractor
    FAILED -> FeatureMerger_8 [input 2]
SubstringExtractor
    END = -1
    SRC_STRING = @Value(col2)
    RESULT_ATTR = col2
    START = 1
    -> FeatureMerger_8 [input 2]
FeatureMerger_8
    IGNORE_NULLS = No
    MERGE_TYPE = Attributes Only
    SUPPLIERS_FIRST = No
    ATTR_CONFLICT_RES = Use Requestor
    PROCESS_DUPS = No
    ATTR_ACCUM_MODE = Merge Supplier
    JOIN_KEYS = @Value(kommuneid) @Value(col2) AUTO
    MERGED -> AttributeCreator_35
    NOT_MERGED -> AttributeCreator_36
AttributeCreator_35
    ATTR_LIST = dsb_eksplosivanlegg,1
    -> Reprojector_3
AttributeCreator_36
    ATTR_LIST = dsb_eksplosivanlegg,0
    -> Reprojector_3
Note: Storulykkeanlegg
CSV (reader CSV_3)
    attributes: col0 number(3,0), col1 char(7), col2 number(5,0)
    -> Tester_3
Tester_3 [off]
    BOOL_OP = OR
    TEST_MODE = Automatic
    TEST_CLAUSE = TEST @Value(col2) BEGINS_WITH 0
    TEST_DESCRIPTION = ""
    PASSED -> SubstringExtractor_3 [off]
    FAILED -> FeatureMerger_10 [input 2] [off]
SubstringExtractor_3 [off]
    END = -1
    SRC_STRING = @Value(col2)
    RESULT_ATTR = col2
    START = 1
    -> FeatureMerger_10 [input 2] [off]
FeatureMerger_10 [off]
    IGNORE_NULLS = No
    MERGE_TYPE = Attributes Only
    SUPPLIERS_FIRST = No
    ATTR_CONFLICT_RES = Use Requestor
    PROCESS_DUPS = No
    ATTR_ACCUM_MODE = Merge Supplier
    JOIN_KEYS = @Value(kommuneid) @Value(col2) AUTO
    MERGED -> AttributeCreator_37
    NOT_MERGED -> AttributeCreator_38
AttributeCreator_37 [off]
    ATTR_LIST = dsb_storulykkeanlegg,1
    -> Reprojector_3
AttributeCreator_38 [off]
    ATTR_LIST = dsb_storulykkeanlegg,0
    -> Reprojector_3
Note: Farlig stoff
CSV (reader CSV_2)
    attributes: col0 number(3,0), col1 char(7), col2 number(5,0)
    -> Tester_2
Tester_2
    BOOL_OP = OR
    TEST_MODE = Automatic
    TEST_CLAUSE = TEST @Value(col2) BEGINS_WITH 0
    TEST_DESCRIPTION = ""
    PASSED -> SubstringExtractor_2
    FAILED -> FeatureMerger_9 [input 2]
SubstringExtractor_2
    END = -1
    SRC_STRING = @Value(col2)
    RESULT_ATTR = col2
    START = 1
    -> FeatureMerger_9 [input 2]
FeatureMerger_9
    IGNORE_NULLS = No
    MERGE_TYPE = Attributes Only
    SUPPLIERS_FIRST = No
    ATTR_CONFLICT_RES = Use Requestor
    PROCESS_DUPS = No
    ATTR_ACCUM_MODE = Merge Supplier
    JOIN_KEYS = @Value(kommuneid) @Value(col2) AUTO
    MERGED -> AttributeCreator_39
    NOT_MERGED -> AttributeCreator_40
AttributeCreator_39
    ATTR_LIST = dsb_anleggfarligstoff,1
    -> Reprojector_3
AttributeCreator_40
    ATTR_LIST = dsb_anleggfarligstoff,0
    -> Reprojector_3
