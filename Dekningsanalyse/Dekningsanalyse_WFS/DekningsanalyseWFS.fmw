FME workspace DekningsanalyseWFS.fmw

Parameters:
- READER_FORMAT = POSTGIS   # Input Format
- READER_DATASET = geonor01tst   # Reader Dataset
- GML_OUT_TARGET_NS_PREFIX_GML = app   # Target Namespace Prefix
- GML_OUT_TARGET_NS_URI_GML = http://skjema.geonorge.no/SOSI/produktspesifikasjon/   # Target Namespace URI
- SourceDataset_POSTGIS_3 = geonor01tst   # Database
- MAX_FEATURES = 3000   # Max features returned

Readers:
- XML_1: XML from C:\Users\xmaland\Documents\GitHub\geonorge\DSB\useparameters.xml
- POSTGIS_1: POSTGIS from $(SourceDataset_POSTGIS_3)

Writers:
- GML2_1: GML2 to C:\Users\bpont\Downloads\return.gml
- GML_1: GML to C:\Users\bpont\Downloads\return.gml
- GML_2: GML to C:\Users\bpont\Downloads\return.gml
- TEXTLINE_1: TEXTLINE to return.xml

Note: WFS Service Template / To modify this workspace to serve your desired dataset, please follow the steps below: / 1. Open the Transformers in the Navigation Window. / 2. Click on the first transformer (_FeatureReader_Source) to navigate to it. / 3. Open the transformer Properties and modify the reader settings to read your desired source data. / 4. Modify the Private Parameters in the Navigation Window / Input Format: Choose the same format as you used in the FeatureReader / Reader Dataset: Copy the contents of the Dataset field in the FeatureReader / Target Namespace Prefix: Default of 'mywfs' will work, but you can specify your own namespace ('fme' is reserved and will cause the workspace to fail). / Target Namespace URI: Your namespace schema, if you change from the default. / 5. Right-click on Workspace Resources in the Navigator and choose Add a Reader as a Resource. / Add a reader with the same settings you used in the Feature Reader. / This resource will provide the output schema information for the results. / 6. Open the Properties of the three GML feature types in the lower right section of the workspace. / Check the Dynamic Properties box. / Modify the Schema Sources to point only to the reader you added as a resource. / Leave Schema Definition set to Default / 7. Publish workspace to FME Server Data Streaming Service. Check the service properties to ensure that / The Output Datasets include the Textline and all three GML writers / The Source Dataset to Override is set to useParameters[XML]
Note: Route Features
AttributeFilter_6
    ATTR_NAME = REQUEST
    ATTR_VALUES = <EMPTY>,<MISSING>,<NULL>,<UNFILTERED>,GetCapabilities,DescribeFeatureType,GetFeature
    DescribeFeatureType -> FeatureReader_Schema_2
    GetFeature -> StringReplacer_2
    GetCapabilities -> AttributeFilter_2
    <NULL> -> AttributeFilter_2
    <MISSING> -> AttributeFilter_2
    <EMPTY> -> AttributeFilter_2
    <UNFILTERED> -> XMLTemplater_2
text_line (writer TEXTLINE_1)
    attributes: text_line_data buffer

Bookmark: Read POST if sent, otherwise create feature to use GET parameters
GetCapabilities (reader XML_1)
    attributes: xml_fragment xml_xml, xml_id xml_char(21), xml_matched_element xml_char(16), xml_parent_child_pos xml_char(1), xml_parent_id xml_char(1)
    -> AttributeCreator
DescribeFeatureType (reader XML_1)
    attributes: xml_fragment xml_xml, xml_id xml_char(25), xml_matched_element xml_char(20), xml_parent_child_pos xml_char(1), xml_parent_id xml_char(1)
    -> AttributeCreator
GetFeature (reader XML_1)
    attributes: xml_fragment xml_xml, xml_id xml_char(16), xml_matched_element xml_char(11), xml_parent_child_pos xml_char(1), xml_parent_id xml_char(1)
    -> AttributeCreator
Note: Copy Feature Type to attribute
AttributeCreator
    ATTR_LIST = _id,0
    -> FeatureTypeExtractor_2
    -> AttributeCreator_Output
AttributeCreator_Output: Logger
    MAXCOORDS = 20
    MAXFEATS = 20
    MESSAGE = Feature is:
FeatureTypeExtractor_2
    DEST_ATTR = REQUEST
    -> DuplicateRemover
Note: Create feature after all / input features read
Creator
    GEOMTYPE = Geometry Object
    NUM = 1
    CREATED -> DuplicateRemover
Note: Block GET feature if POST is read
DuplicateRemover
    KEYATTR = _id
    UNIQUE -> AttributeRenamer_5
AttributeRenamer_5
    ATTR_LIST = xml_fragment,xml_request,
    -> AttributeFilter
Note: Route Features
AttributeFilter
    ATTR_NAME = REQUEST
    ATTR_VALUES = <EMPTY>,<MISSING>,<NULL>,<UNFILTERED>,GetCapabilities,DescribeFeatureType,GetFeature
    GetCapabilities -> XMLFlattener_2
    DescribeFeatureType -> XMLFlattener
    <MISSING> -> ParameterFetcher_2
    GetFeature -> XMLFlattener_3

Bookmark: Process GET Request
Note: Get URI of workspace / Map null for testing in desktop
ParameterFetcher_2
    ATTR_LIST = _FME_SERVER_REQUEST_URI {$(FME_SERVER_REQUEST_URI)}
    -> NullAttributeMapper_2
NullAttributeMapper_2
    NULL_TREATMENT = New Value
    SOURCE_ATTR_VAL = Empty "Missing (Selected Attributes Only)" Null
    NEW_VALUE = " "
    ATTRCHOICE = Selected Attributes
    ATTRLIST = _FME_SERVER_REQUEST_URI
    -> TextDecoder
Note: Decode URL string
TextDecoder
    DEST_ATTR = _FME_SERVER_REQUEST_URI
    ENCODING_TYPE = URL (Percent Encoding)
    STRING_TO_DECODE = @Value(_FME_SERVER_REQUEST_URI)
    -> FMEServerURLSplitter
Note: Split calling URI to get parameters
Note: FMEServerURLSplitter [FMEServerURLSplitter] / [Embedded] / Request URI: @Value(_FME_SERVER_REQUEST_URI) / URL Parameter Name Case: UPPERCASE / Decode URL Parameters: Decode
FMEServerURLSplitter
    URL_PARAM_NAME_CASE = UPPERCASE
    _FME_SERVER_REQUEST_URI = @Value(_FME_SERVER_REQUEST_URI)
    DECODE_URL_TEXT = Decode
    -> AttributeExposer_4
Note: Expose parameter attributes
AttributeExposer_4
    ATTR_LIST = SERVICE,REQUEST,VERSION,TYPENAME,TYPENAMES,FILTER,BBOX,ACCEPTVERSIONS,SRSNAME,COUNT,MAXFEATURES
    -> AttributeFilter_6

Bookmark: GetCapabilities POST Request
Note: Flatten POST XML
XMLFlattener_2
    ATTRIBUTE_XML = xml_request
    NEW_ATTRIBUTES = GetCapabilities.version TypeName TypeNames
    EMBEDDED_EXPRESSIONS = GetCapabilities
    XML_SOURCE_TYPE = Attribute with XML document
    FLATTEN_OPTIONS = <structure separator="." map-empty-elements="yes" matched-prefix="attributes" matched-attributes="yes" cardinality="+{?}" structure-prefix="" child-position-attribute="" except-expression="" ui-mode="basic" matched-ancestor-attributes=""/>
    -> AttributeRenamer_2
Note: Copy Version
AttributeRenamer_2
    ATTR_LIST = GetCapabilities.version,VERSION,
    -> AttributeFilter_6

Bookmark: DescribeFeatureType POST request
Note: Flatten POST XML
XMLFlattener
    ATTRIBUTE_XML = xml_request
    NEW_ATTRIBUTES = DescribeFeatureType.version TypeName TypeNames TypeName{} TypeNames{}
    EMBEDDED_EXPRESSIONS = DescribeFeatureType
    XML_SOURCE_TYPE = Attribute with XML document
    FLATTEN_OPTIONS = <structure separator="." map-empty-elements="yes" matched-prefix="attributes" matched-attributes="yes" cardinality="+{?}" structure-prefix="" child-position-attribute="" except-expression="" ui-mode="basic" matched-ancestor-attributes=""/>
    -> ListConcatenator
Note: Create Type lists
ListConcatenator
    DROP_EMPTY_PARTS = Yes
    VAL_ATTR = _typename
    SEP = ,
    LIST_ATTR = TypeName{}
    -> ListConcatenator_2
ListConcatenator_2
    DROP_EMPTY_PARTS = Yes
    VAL_ATTR = _typenames
    SEP = ,
    LIST_ATTR = TypeNames{}
    -> AttributeCreator_6
Note: Copy Version and Type Names
AttributeCreator_6
    ATTR_LIST = TYPENAME,"FME_CONDITIONAL:DEFAULT_VALUE'@Value(_typename)'BOOL_OP;OR;COMPOSITE_TEST;<Unused>;TEST _typename ATTRIBUTE_VALUE_NULL _FME_BLANK_STRING_;TEST _typename ATTRIBUTE_IS_EMPTY _FME_BLANK_STRING_;TEST _typename ATTRIBUTE_IS_MISSING _FME_BLANK_STRING_'@Value(TypeName)'FME_NUM_CONDITIONS2___",TYPENAMES,"FME_CONDITIONAL:DEFAULT_VALUE'@Value(_typenames)'BOOL_OP;OR;COMPOSITE_TEST;<Unused>;TEST _typenames ATTRIBUTE_VALUE_NULL _FME_BLANK_STRING_;TEST _typenames ATTRIBUTE_IS_EMPTY _FME_BLANK_STRING_;TEST _typenames ATTRIBUTE_IS_MISSING _FME_BLANK_STRING_'@Value(TypeNames)'FME_NUM_CONDITIONS2___",VERSION,@Value(DescribeFeatureType.version)
    -> AttributeFilter_6

Bookmark: GetFeature POST
Note: Flatten POST XML
XMLFlattener_3
    ATTRIBUTE_XML = xml_request
    NEW_ATTRIBUTES = GetFeature.version Query.typeName Query.typeNames Query{}.typeName Query{}.typeNames Query{}.srsName Query{}.COUNT Query.COUNT Query.MAXFEATURES Query{}.MAXFEATURES
    EMBEDDED_EXPRESSIONS = GetFeature
    XML_SOURCE_TYPE = Attribute with XML document
    FLATTEN_OPTIONS:
      <structure
      separator="."
      open-list-brace="{"
      close-list-brace="}"
      map-empty-elements="yes"
      matched-prefix="attributes"
      matched-attributes="yes"
      matched-ancestor-attributes=""
      cardinality="+{?}"
      except=""
      structure-prefix=""
      child-position-attribute=""
      attribute-identifier=""/>

      <!--
      The options here allows customization of the attributes and attribute lists of the matched XML subtree
      that will be added to FME Features.

      Here are the following options that can be specified:

      1. separator
      This value of this option is used as the separator in the naming of the attributes of the children of the matched elements.

      Default value: .
      Possible values: any string

      2. open-list-brace
      Specifies the open list index delimiter brace for the flattened attributes.

      Default value: {
      Possible values: any string

      3. close-list-brace
      Specifies the close list index delimiter brace for the flattened attributes.

      Default value: }
      Possible values: any string

      4. map-empty-elements
      If set to yes, then any empty elements will be added as attributes with empty values onto the features.
      Otherwise, the attributes will not be added onto the features.

      Default value if not specified: yes
      Possible values: yes|no

      Default value:
      Possible values: any string

      5. matched-prefix
      This option controls whether FME feature attributes produced will be prefixed with matched element's name.
      If the value is 'yes', then both the matched element's attributes and all its children are prefixed
      If the value is 'no', then none of the feature attributes are prefixed with matched element's name
      If the value is 'children', then only the children of the matched element are prefixed
      If the value is 'attributes', then only the attributes of the matched element are prefixed

      Default value if not specified: yes
      Possible values: yes|no|children|attributes

      6. matched-attributes
      If this option is set to 'yes' then the attributes of the matched element are mapped as FME feature attributes.
      Otherwise, the attributes of the matched element are ignored.

      matched-prefix option can also be set to 'attributes' or 'yes' to allow the attributes to be prefixed with
      the name of the matched element.

      Default value if not specified: yes
      Possible values: yes|no

      7. matched-ancestor-attributes
      The option controls whether XML attributes from ancestor of the matched element should be included as FME feature attributes.

      The valid values for this option are:
      - 'parent' or '1'         : XML attributes of the parent of the matched element are added
      - 'grandparent' or '2'    : XML attributes of the grandparent of the matched element are added
      - 'root' or '-1'          : XML attributes of the root of the document are added
      - any non-negative number : XML attributes of the ancestor by going up x levels from the matched element are added.
                                  0 is the matched element.

      To include more than one ancestor, multiple values can be separated by a space.
      For example: To get the attributes from root, parent and grand parent, we can specify
      matched-ancestor-attributes="parent grandparent root"

      Default value:
      Possible values: parent|grandparent|root

      8. cardinality
      This option can be specified as a space separated list of cardinality directives.

      Default value: +{?} (Treat child elements as a list if there are more than one with the same name)
      Possible values: Refer to the documentation of XFMap section in XML Reader documentation

      9. structure-prefix
      This option can be set to non-empty string that serves as a prefix to every attribute that is generated for a matched element.

      Default value:
      Possible values: any string

      10. except
      The except attribute accepts the same types of expressions as the match or except attribute of a mapping rule.
      For example, the expression except=”parent/child{2}” could be used to exclude the second <child> element
      contained in a <parent> element from the output of the structure subrule.

      Default value:
      Possible values: any path expression

      11. child-position-attribute
      When this option is set to non-empty string, each child element will generate an additional feature attribute
      whose value will be the position of the child element witihin its parent.

      Default value:
      Possible values: any string

      12. attribute-identifier (Any string)
      XML attributes can be differentiated from leaf elements. By setting this option to non-empty string, XML reader
      will append a prefix to the attributes in the leaf elements.

      All the options have more elaborated examples and descriptions in the XML reader documentation.
      -->
    -> XMLFragmenter
    -> FeatureMerger [input 1]
Note: Extract Filter XML
XMLFragmenter
    MERGE_ATTRS = Yes
    ATTRIBUTE_XML = xml_request
    EMBEDDED_EXPRESSIONS = Filter
    XML_SOURCE_TYPE = Attribute with XML document
    FRAGMENTS -> FeatureMerger [input 2]
Note: Merge Filter onto request
FeatureMerger
    ATTR_CONFLICT_RES = Use Supplier
    IGNORE_NULLS = No
    SUPPLIERS_FIRST = No
    JOIN_KEYS = 1 1 AUTO
    ATTR_ACCUM_MODE = Merge Supplier
    MERGE_TYPE = Attributes Only
    PROCESS_DUPS = No
    MERGED -> ListExploder_4
    NOT_MERGED -> ListExploder_4
Note: Explode query list
ListExploder_4
    INDEX_ATTR = _element_index
    ATTR_CONFLICT_RES = Use Original
    ATTR_ACCUM_MODE = Merge Incoming List
    LIST_ATTR = Query{}
    NOT_FOUND -> AttributeRenamer_4
    LIST_FOUND -> AttributeRenamer_3
Note: Copy Version and Type Names
AttributeRenamer_3
    ATTR_LIST = GetFeature.version,VERSION,,typeName,TYPENAME,,typeNames,TYPENAMES,,xml_fragment,FILTER,,srsName,SRSNAME,,COUNT,Teller,,MAXFEATURES,Teller,
    -> AttributeFilter_6
Note: Copy Version and Type Names
AttributeRenamer_4
    ATTR_LIST = GetFeature.version,VERSION,,Query.typeName,TYPENAME,,Query.typeNames,TYPENAMES,,xml_fragment,FILTER,,Query.srsName,SRSNAME,,COUNT,Teller,,MAXFEATURES,Teller,
    -> AttributeFilter_6

Bookmark: GetCapabilities
AttributeFilter_2
    ATTR_NAME = VERSION
    ATTR_VALUES = <EMPTY>,<MISSING>,<NULL>,<UNFILTERED>,1.0.0,1.1.0,2.0.0
    1.0.0 -> AttributeFileReader_2
    1.1.0 -> AttributeFileReader_3
    2.0.0 -> AttributeFileReader
    <UNFILTERED> -> AttributeFileReader
    <NULL> -> AttributeFileReader
    <EMPTY> -> AttributeFileReader
    <MISSING> -> AttributeFileReader
AttributeFileReader_2
    DEST_ATTR = text_line_data
    CHAR_ENCODING = utf-8
    FILE_NAME = GetCapabilities10.xml
    -> text_line (writer TEXTLINE_1)
AttributeFileReader_3
    DEST_ATTR = text_line_data
    CHAR_ENCODING = utf-8
    FILE_NAME = GetCapabilities11.xml
    -> text_line (writer TEXTLINE_1)
AttributeFileReader
    DEST_ATTR = text_line_data
    CHAR_ENCODING = utf-8
    FILE_NAME = GetCapabilities20.xml
    -> text_line (writer TEXTLINE_1)

Bookmark: Request som ikke er støttet ennå
XMLTemplater_2
    VISIBLE_QUERY_VALIDATE = Yes
    ROOT_QUERY_EXPR:
      <ows:ExceptionReport xmlns:ows="http://www.opengis.net/ows/1.1" xmlns:xsi="http://www.w3.org/2001/XMLSchema-instance" xsi:schemaLocation="http://www.opengis.net/ows/1.1 http://schemas.opengis.net/ows/1.1.0/owsExceptionReport.xsd" version="2.0.0">
        <ows:Exception exceptionCode="InvalidParameterValue" locator="request">
          <ows:ExceptionText>No service for request type {fme:get-attribute("REQUEST")} is configured / active.</ows:ExceptionText>
        </ows:Exception>
      </ows:ExceptionReport>
    OUTPUT_XML_HEADER = Yes
    RESULT_ATTRIBUTE = text_line_data
    -> text_line (writer TEXTLINE_1)

Bookmark: DescribeFeatureType
Note: Read Source data schema
FeatureReader_Schema_2
    ATTR_CONFLICT_RES = Use Result
    CACHE_TIMEOUT_HRS = 24
    COMBINE_GEOM = Use Result
    FEATURETYPES_RADIO = FEATURETYPES
    DATASET = $(READER_DATASET)
    FEATURETYPES = schema
    SCHEMA_REAL_FORMAT = $(READER_FORMAT)
    FORMAT = SCHEMA
    SCHEMA_SCHEMA_READER = yes
    SUPPORTED_SPATIAL_INTERACTIONS = ENVELOPE_INTERSECT%INTERSECTS%CONTAINS%CROSSES%DISJOINT%EQUALS%OVERLAPS%TOUCHES%WITHIN
    ATTR_ACCUM_MODE = Merge Initiator and Result
    <OTHER> -> DescribeFeatureType
DescribeFeatureType
    GML_OUT_TARGET_NS_PREFIX_GML = app
    GML_OUT_TARGET_NS_URI_GML = http://skjema.geonorge.no/SOSI/produktspesifikasjon/
    TYPENAMES = @Value(TYPENAMES)
    TYPENAME = @Value(TYPENAME)
    VERSION = @Value(VERSION)
    XMLFormatter_2_Passed -> text_line (writer TEXTLINE_1)

Bookmark: GetFeatures
Note: Remove NameSpace from TypeNames
StringReplacer_2
    FIND_TEXT = $(GML_OUT_TARGET_NS_PREFIX_GML):
    REGEXP = no
    NO_MATCH = _FME_NO_OP_
    CASE = no
    SRC_ATTRS = TYPENAME,TYPENAMES
    -> StringReplacer
StringReplacer
    FIND_TEXT = ,
    REGEXP = no
    REPLACE_TEXT = " "
    NO_MATCH = _FME_NO_OP_
    CASE = no
    SRC_ATTRS = TYPENAME,TYPENAMES
    -> Tester_4
Note: Different WFS versions have / different type name attributes
Tester_4
    BOOL_OP = OR
    TEST_CLAUSE = TEST @Value(VERSION) = 2.0.0
    TEST_MODE = Automatic
    TEST_DESCRIPTION = ""
    PASSED -> AttributeCopier
    FAILED -> AttributeCopier_2
Note: WFS 2.0.0
AttributeCopier
    ATTR_LIST = TYPENAMES,_types,"",COUNT,Teller,""
    -> WFS_BBOX_CREATOR
AttributeCopier_2
    ATTR_LIST = TYPENAME,_types,"",MAXFEATURES,Teller,""
    -> WFS_BBOX_CREATOR
Note: Read objects from the database
WFS_BBOX_CREATOR
    FILTER = @Value(FILTER)
    BBOX = @Value(BBOX)
    SRSNAME = @Value(SRSNAME)
    WFS20_FilterBBOX -> WFS_FILTER_CREATOR
    Standard_bbox -> WFS_FILTER_CREATOR
    Reprojected_BBOX -> WFS_FILTER_CREATOR
    Default_BBOX -> WFS_FILTER_CREATOR
WFS_Reprojector
    SRSNAME = @Value(SRSNAME)
    Reprojector_3_Reprojected -> AttributeFilter_4
    Reprojector_2_Reprojected -> AttributeFilter_4
Note: Ulike GML-writere for ulike WFS-versjoner
AttributeFilter_4
    ATTR_NAME = VERSION
    ATTR_VALUES = <EMPTY>,<MISSING>,<NULL>,<UNFILTERED>,1.0.0,1.1.0,2.0.0
    1.1.0 -> GML3.1 (writer GML_1)
    2.0.0 -> GML3.2 (writer GML_2)
    1.0.0 -> GML2 (writer GML2_1)
Note: WFS 1.0.0
GML2 (writer GML2_1)
Note: WFS 1.1.0
GML3.1 (writer GML_1)
Note: WFS 2.0.0
GML3.2 (writer GML_2)

Bookmark: Filter as SQL
WFS_FILTER_CREATOR
    FILTER = @Value(FILTER)
    FeatureMerger_2_Merged -> _FeatureReader_Source
    FeatureMerger_2_NotMerged -> _FeatureReader_Source

Bookmark: Need to replace this with SQLCreator
_FeatureReader_Source: FeatureReader
    DATASET = geonor01tst
    POSTGIS_USE_SEARCH_ENVELOPE = NO
    POSTGIS_QUERY_FEATURE_TYPES_FOR_MERGE_FILTERS = Yes
    POSTGIS_CLIP_TO_ENVELOPE = NO
    POSTGIS_USER_NAME = geonortst
    POSTGIS_USE_TRUE_POSTGIS_TYPES = yes
    POSTGIS_PORT = 5432
    COMBINE_GEOM = Use Result
    FEATURETYPES_RADIO = ATTR_NAME
    POSTGIS_DISABLE_COLLECTION_SPLITTING = yes
    FORMAT = POSTGIS
    POSTGIS_HOST = Nnridb504
    WHERE = @Value(_where)
    ATTR_CONFLICT_RES = Use Result
    POSTGIS_PASSWORD =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
    INTERACT = Envelope Intersect
    ATTR_ACCUM_MODE = Merge Initiator and Result
    POSTGIS_SCHEMALIST = dekningsoversikt
    ATTR_NAME = _types
    <OTHER> -> Tester_9
    <OTHER> -> Counter_2
    INITIATOR -> Counter_2
Counter_2
    DOMAIN = counter
    SCOPE = Global
    START = 0
    CNT_ATTR = _count
    -> StatisticsCalculator_2
XMLTemplater
    VISIBLE_QUERY_VALIDATE = Yes
    ROOT_QUERY_EXPR:
      <ows:ExceptionReport xmlns:ows="http://www.opengis.net/ows/1.1" xmlns:xsi="http://www.w3.org/2001/XMLSchema-instance" xsi:schemaLocation="http://www.opengis.net/ows/1.1 http://schemas.opengis.net/ows/1.1.0/owsExceptionReport.xsd" version="2.0.0">
        <ows:Exception exceptionCode="NotFound" locator="request">
          <ows:ExceptionText>No features returned.</ows:ExceptionText>
        </ows:Exception>
      </ows:ExceptionReport>
    OUTPUT_XML_HEADER = Yes
    RESULT_ATTRIBUTE = text_line_data
    -> text_line (writer TEXTLINE_1)

Bookmark: Limit number of features returned
Tester_9
    BOOL_OP = OR
    TEST_CLAUSE:
      TEST Teller ATTRIBUTE_IS_EMPTY ""
      TEST Teller ATTRIBUTE_IS_MISSING ""
      TEST Teller ATTRIBUTE_VALUE_NULL ""
    TEST_MODE = Automatic
    TEST_DESCRIPTION = ""
    FAILED -> Counter
    PASSED -> Sampler
Sampler
    SAMPLE_TYPE_LONG = First N Features
    RATE = $(MAX_FEATURES)
    SAMPLED -> WFS_Reprojector
Counter
    DOMAIN = counter
    SCOPE = Global
    START = 0
    CNT_ATTR = _count
    -> Tester_8
Tester_8
    BOOL_OP = OR
    TEST_CLAUSE = TEST @Value(_count) < @Value(Teller)
    TEST_MODE = Automatic
    TEST_DESCRIPTION = ""
    PASSED -> WFS_Reprojector
Note: Counts features received
StatisticsCalculator_2
    PASS_THROUGH = No
    COUNT_ATTR = FeatureCount
    STATS_ATTR = _count
    STATISTICS -> Tester
Tester
    BOOL_OP = OR
    TEST_CLAUSE = TEST @Value(FeatureCount) = 1
    TEST_MODE = Automatic
    TEST_DESCRIPTION = ""
    PASSED -> XMLTemplater

FME custom transformer WFS_Reprojector

Parameters:
- SRSNAME = @Value(SRSNAME)

Tester_7_Input (input)
    -> Tester_7
Note: Is SRSNAME provided?
Tester_7
    BOOL_OP = OR
    TEST_CLAUSE = TEST SRSNAME ATTRIBUTE_IS_EMPTY ""
    TEST_MODE = Automatic
    TEST_DESCRIPTION = ""
    PASSED -> Reprojector_3
    FAILED -> AttributeValueMapper_5
Note: Reprojects to default coordinate system
Reprojector_3
    DEST = EPSG:4258
    RASTER_CELL_SIZE = Preserve Cells
    SOURCE = EPSG:4258
    INTERPOLATION_TYPE_NAME = Nearest Neighbor
    REPROJECTED -> Reprojector_3_Reprojected (output)
Reprojector_3_Reprojected (output)
Note: If urn-notation is provided, map to standard EPSG
AttributeValueMapper_5
    LUT = urn:ogc:def:crs:EPSG::4258,EPSG:4258,urn:ogc:def:crs:EPSG::4326,EPSG:4326,urn:ogc:def:crs:EPSG::25830,EPSG:25830,urn:ogc:def:crs:EPSG::25831,EPSG:25831,urn:ogc:def:crs:EPSG::25832,EPSG:25832,urn:ogc:def:crs:EPSG::25833,EPSG:25833,urn:ogc:def:crs:EPSG::25834,EPSG:25834,urn:ogc:def:crs:EPSG::25835,EPSG:25835,urn:ogc:def:crs:EPSG::25836,EPSG:25836,urn:ogc:def:crs:EPSG::3044,EPSG:3044,urn:ogc:def:crs:EPSG::3045,EPSG:3045
    VAL_ATTR = SRSNAME
    SRC = SRSNAME
    DEFAULT_VALUE = @Value(SRSNAME)
    DIRECTION = Forward (Source To Destination)
    -> Reprojector_2
Note: Reprojects to destination coordinate system
Reprojector_2
    DEST = @Value(SRSNAME)
    RASTER_CELL_SIZE = Preserve Cells
    SOURCE = EPSG:4258
    INTERPOLATION_TYPE_NAME = Nearest Neighbor
    REPROJECTED -> Reprojector_2_Reprojected (output)
Reprojector_2_Reprojected (output)

FME custom transformer FMEServerURLSplitter
This transformer is useful for breaking up the full URI request that is sent to FME Server. The transformer actually takes any URL and breaks it up into pieces, so it could be applied elsewhere.
With FME Server the entire request URL is passed to the workspace in the FME_SERVER_REQUEST_URI parameter so that it can be used within the workspace. This is useful in cases where extra parameters are tacked onto a URL or the URL path doesn't end with .fmw.
This capability makes it possible for FME Server to be used to satisfy new types of requests where the full request cannot be known until runtime.
Input:
Request URI: the full URI request made to FME Server, in string or attribute form
URL Parameter Name Case: Will case of the URL Parameter Names to the case specified. This is useful to make your service "case insensitve".  Specify Upper or lower case and then your service is not case sensitive with Parameter Names. Parameter Values are left untouched.
Decode URL Parameters: If set to "Decode" then both url parameter attribute names and attribute values will be decoded. 
Output
base_url - This is the entire URL up to the starts of URL parameters. 
fme_server_base_url - The FME Server base url. Is the same as above if the base_url ends at .fmw. This is only present if the url has .fmw in it. 
fme_server_extra_url_path - the additional components of the path if it is from FME Server. This is present if the base_url is different from the fme_server_base_url.
fme_server_extra_url{} list - fme_server_extra_url_path broken up into a list for convenience
url_raw_parameters - These are all the url parameters as one string.
num_parms - The number of URL parameters after they have been parsed out. 
decoded parameters - The parameters themselves are also parsed out and turned into FME attributes.  These must be explicitly exposed after this transformer. 
Example
Given the url 
http://dondemo/fmejobsubmitter/webdump/PublishParameterDump.fmw/another/value?DestDataset_TEXTLINE=output.txt&opt_showresult=false&opt_servicemode=sync&anotherparm=here
base_url has value `http://dondemo/fmejobsubmitter/webdump/PublishParameterDump.fmw/another/value'
fme_server_base_url has value `http://dondemo/fmejobsubmitter/webdump/PublishParameterDump.fmw/'
fme_server_extra_url_path' has value `another/value'
fme_server_extra_url{0}' has value 'another'
fme_server_extra_url{1}' has value 'value'
url_raw_parameters' has value 'DestDataset_TEXTLINE=output.txt&opt_showresult=false&opt_servicemode=sync&anotherparm=here'
num_parms' has value '4'
DestDataset_TEXTLINE has value 'output.txt'
anotherparm has value 'here'
opt_servicemode has value 'sync'
opt_showresult has value 'false'
Copyright (c) 2014 Safe Software Inc.
Permission is granted to anyone, free of charge, to use, modify and distribute the object code form of this transformer for any purpose, subject to the following restrictions:
1) The origin of this transformer and associated FME(R) software must not be misrepresented.
2) This transformer may only be used in conjunction with a validly licensed copy of FME software.
THIS SOFTWARE IS PROVIDED BY SAFE SOFTWARE INC. "AS IS" AND ANY EXPRESS OR IMPLIED WARRANTIES, INCLUDING, BUT NOT LIMITED TO, THE IMPLIED WARRANTIES OF MERCHANTABILITY, NONINFRINGEMENT AND FITNESS FOR A PARTICULAR PURPOSE ARE DISCLAIMED. IN NO EVENT SHALL SAFE SOFTWARE INC. BE LIABLE FOR ANY DIRECT, INDIRECT, INCIDENTAL, SPECIAL, EXEMPLARY, OR CONSEQUENTIAL DAMAGES (INCLUDING, BUT NOT LIMITED TO, PROCUREMENT OF SUBSTITUTE GOODS OR SERVICES; LOSS OF USE, DATA, OR PROFITS; OR BUSINESS INTERRUPTION) HOWEVER CAUSED AND ON ANY THEORY OF LIABILITY, WHETHER IN CONTRACT, STRICT LIABILITY, OR TORT (INCLUDING NEGLIGENCE OR OTHERWISE) ARISING IN ANY WAY OUT OF THE USE OF THIS SOFTWARE, EVEN IF ADVISED OF THE POSSIBILITY OF SUCH DAMAGE.

Parameters:
- _FME_SERVER_REQUEST_URI =   # Request URI
- URL_PARAM_NAME_CASE = Untouched   # case"%"Full Title Case"%Untouched URL Parameter Name Case
- DECODE_URL_TEXT = Don't Decode   # Decode" Decode URL Parameters

Input (input)
    -> AttributeSplitter
Output (output)

Bookmark: First split url up into two peices ("base url" and "parm string")
AttributeSplitter
    DROP_EMPTY_PARTS = No
    ATTR_NAME = _FME_SERVER_REQUEST_URI
    DELIMITER = ?
    LIST_NAME = _list
    TRIM_OPTION = Both
    -> AttributeRenamer
AttributeRenamer
    ATTR_LIST = _list{0},base_url,"",_list{1},url_raw_parameters,""
    -> AttributeSplitter_2

Bookmark: Check if Parms and build list
Note: Now we split the parm string into a list.
AttributeSplitter_2
    DROP_EMPTY_PARTS = No
    ATTR_NAME = url_raw_parameters
    DELIMITER = &
    LIST_NAME = _paramList
    TRIM_OPTION = Both
    -> TestFilter
TestFilter
    TEST_LIST = BOOL_OP,OR,COMPOSITE_TEST,<Unused>,TEST_CLAUSE,"TEST _paramList{0} NOT_ATTRIBUTE_IS_EMPTY """"",Parameters
    DEFAULT_VALUE = NoParameters
    Parameters -> ListElementCounter
    NoParameters -> Remove_Empty_Argument
Note: No Parms so remove attribute
Remove_Empty_Argument: AttributeRemover
    REMOVE_ATTRS = url_raw_parameters
    -> StringSearcher

Bookmark: Loop Initialization
ListElementCounter
    CNT_ATTR = num_parms
    LIST_NAME = _paramList{}
    -> InitializeCounter
InitializeCounter: Counter
    DOMAIN = AttributeCount
    SCOPE = Global
    START = 0
    CNT_ATTR = currentListPos
    -> AttributeCreator_2

Bookmark: Iterate over all the parameters that were set
AttributeLooper (input)
    -> AttributeCreator_2

Bookmark: Extract a value and build attribute
AttributeCreator_2
    ATTR_LIST = curListEntry,@Value(_paramList{@Value(currentListPos)})
    -> AttributeSplitter_3
AttributeSplitter_3
    DROP_EMPTY_PARTS = No
    ATTR_NAME = curListEntry
    DELIMITER = =
    LIST_NAME = paramEntry
    TRIM_OPTION = Both
    -> AreWeChangingCase
AreWeDecodingURLText: TestFilter
    TEST_LIST = BOOL_OP,OR,COMPOSITE_TEST,<Unused>,TEST_CLAUSE,"TEST $(DECODE_URL_TEXT) = Decode",Decode
    DEFAULT_VALUE = Don't Decode
    Don't Decode -> AttributeCreator
    Decode -> DecodeParamName
DecodeParamName: TextDecoder
    DEST_ATTR = paramEntry{0}
    ENCODING_TYPE = URL (Percent Encoding)
    STRING_TO_DECODE = @Value(paramEntry{0})
    -> DecodeParamValue
DecodeParamValue: TextDecoder
    DEST_ATTR = paramEntry{1}
    ENCODING_TYPE = URL (Percent Encoding)
    STRING_TO_DECODE = @Value(paramEntry{1})
    -> AttributeCreator
AttributeCreator
    ATTR_LIST = @Value(paramEntry{0}),@Value(paramEntry{1})
    -> IncrementCounter
IncrementCounter: Counter
    DOMAIN = AttributeCount
    SCOPE = Global
    START = 0
    CNT_ATTR = currentListPos
    -> TestForMoreParms

Bookmark: Change Case
AreWeChangingCase: TestFilter
    TEST_LIST = BOOL_OP,OR,COMPOSITE_TEST,<Unused>,TEST_CLAUSE,"TEST $(URL_PARAM_NAME_CASE) = Untouched",No case change
    DEFAULT_VALUE = change case
    change case -> StringCaseChanger
    No case change -> AreWeDecodingURLText
StringCaseChanger
    CHANGE_TYPE = $(URL_PARAM_NAME_CASE)
    ATTRCHOICE = Selected Attributes
    ATTRLIST = paramEntry{0}
    -> AreWeDecodingURLText

Bookmark: Another Iteration?
TestForMoreParms: TestFilter
    TEST_LIST = BOOL_OP,OR,COMPOSITE_TEST,<Unused>,TEST_CLAUSE,"TEST @Value(currentListPos) < @Value(num_parms)",More Params
    DEFAULT_VALUE = All Done
    More Params -> AttributeLooper (output)
    All Done -> StringSearcher
AttributeLooper (output)

Bookmark: Extract URL Path after the *.fmw.
StringSearcher
    REGEXP = ^(.*[.]fmw/)(.*)$
    MATCHED_PARTS_ATTR = _matched_parts
    STRING_TO_SEARCH = @Value(base_url)
    CASE = no
    MATCHED_RESULT_ATTR = _matched_characters
    MATCHED -> AttributeRenamer_2
    NOT_MATCHED -> AttributeRemover
AttributeRenamer_2
    ATTR_LIST = _matched_parts{0},fme_server_base_url,"",_matched_parts{1},fme_server_extra_url_path,""
    -> AttributeSplitter_4
AttributeSplitter_4
    DROP_EMPTY_PARTS = No
    ATTR_NAME = fme_server_extra_url_path
    DELIMITER = /
    LIST_NAME = fme_server_extra_url
    TRIM_OPTION = Both
    -> AreWeDecodingURLText_2
AreWeDecodingURLText_2: TestFilter
    TEST_LIST = BOOL_OP,OR,COMPOSITE_TEST,<Unused>,TEST_CLAUSE,"TEST $(DECODE_URL_TEXT) = Decode",Decode
    DEFAULT_VALUE = Don't Decode
    Don't Decode -> AttributeRemover
    Decode -> DecodeExxtraURL
DecodeExxtraURL: TextDecoder
    DEST_ATTR = fme_server_extra_url_path
    ENCODING_TYPE = URL (Percent Encoding)
    STRING_TO_DECODE = @Value(fme_server_extra_url_path)
    -> AttributeRemover
AttributeRemover
    REMOVE_ATTRS = currentListPos,curListEntry,_matched_characters
    LIST_ATTRS = _paramList{} _matched_parts{} paramEntry{} _list{}
    -> Output (output)
