FME workspace Dekningsanalyse_Forsvaret.fmw

Parameters:
- SourceDataset_FILEGDB = D:\Data\Stoy_skytefelt_og_baner_FB.gdb   # Source Geodatabase
- SourceDataset_POSTGIS = geonortst@nnridb504:5432/geonor01tst   # Connection
- DestDataset_POSTGIS = geonortst@nnridb504:5432/geonor01tst   # Connection

Readers:
- FILEGDB_1: FILEGDB from $(SourceDataset_FILEGDB)
- POSTGIS_1: POSTGIS from $(SourceDataset_POSTGIS)

Writers:
- POSTGIS_2: POSTGIS to $(DestDataset_POSTGIS)

STOY_FLYPLASSER_LINJE_FRA_AVINOR_2014 (reader FILEGDB_1)
    attributes: OBJECTID objectid, LENGTH double, OPPR smallint, KOORDH double, ICAO text(24), ENDRETAV text(24), PERIMETER text(100), AVINORKODE double, LUKKET text(100), MALEMETODE smallint, NOYAKTIGHE int, SYNBARHET smallint, H_MALEMETODE smallint, H_NOYAKTIGHET int, MAX_AVVIK int, HOEYDE double, AREAL double, OBJTYPE text(32), LTEMA smallint, PRODUKT text(15), VERSJON text(20), DATFGSTDATDATO text(20), DATO date, STOYSONEKATEGORI text(1), SHAPE_Length double
    -> Reprojector
Reprojector
    RASTER_CELL_SIZE = Preserve Cells
    DEST = EPSG:4258
    SOURCE = Read from feature
    INTERPOLATION_TYPE_NAME = Nearest Neighbor
    REPROJECTED -> SpatialFilter [input 1]
STOY_FLYPLASSER_FLATE_FRA_AVINOR_2014 (reader FILEGDB_1)
    attributes: OBJECTID objectid, PERIMETER double, OPPR smallint, X double, Y double, KOORDH double, ICAO text(24), LHSTOY int, ENDRETAV text(24), LUKKET text(100), STOYSONEKATEGORI text(1), FTEMA smallint, MALEMETODE smallint, NOYAKTIGHE int, SYNBARHET smallint, H_MALEMETODE smallint, H_NOYAKTIGHET int, MAX_AVVIK int, OBJTYPE text(32), STOYKILDENAVN text(50), PRODUKT text(15), VERSJON text(20), DATFGSTDATO text(20), STOEYKILDE text(2), DATO date, SHAPE_Length double, SHAPE_Area double
    -> Reprojector_2
Reprojector_2
    RASTER_CELL_SIZE = Preserve Cells
    DEST = EPSG:4258
    SOURCE = Read from feature
    INTERPOLATION_TYPE_NAME = Nearest Neighbor
    REPROJECTED -> SpatialFilter [input 1]
STOY_FELT_BANER_LINJE (reader FILEGDB_1)
    attributes: OBJECTID objectid, OBJTYPE text(32), STOYSONEKATEGORI text(1), STOYKILDE text(2), STOYNIVA smallint, STOYINTERVALL smallint, STOYENHET text(50), STOYKILDENAVN text(50), STOYMETODE text(50), BEREGNETAAR text(10), MALEMETODE smallint, NOYAKTIGHET int, SYNBARHET smallint, MAX_AVVIK int, REFERANSE text(100), SHAPE_Length double
    -> Reprojector_3
Reprojector_3
    RASTER_CELL_SIZE = Preserve Cells
    DEST = EPSG:4258
    SOURCE = Read from feature
    INTERPOLATION_TYPE_NAME = Nearest Neighbor
    REPROJECTED -> SpatialFilter_2 [input 1]
STOY_FELT_BANER_FLATE (reader FILEGDB_1)
    attributes: OBJECTID objectid, MALEMETODE smallint, STOYMETODE text(50), STOYKILDENAVN text(50), OBJTYPE text(32), STOYENHET text(50), STOYKILDE text(2), STOYSONEKATEGORI text(1), INDIKATOR text(50), STOYINTERVALL smallint, BEREGNETAAR text(10), KOMM text(4), OPPHAV text(20), STEDKVAL smallint, REFERANSE text(100), STOYKILDEIDENTIFIKASJON text(50), DATAFANGSTDATO date, SHAPE_Length double, SHAPE_Area double
    -> Reprojector_4
Reprojector_4
    RASTER_CELL_SIZE = Preserve Cells
    DEST = EPSG:4258
    SOURCE = Read from feature
    INTERPOLATION_TYPE_NAME = Nearest Neighbor
    REPROJECTED -> Deaggregator_2
Deaggregator_2
    EXPLODE_INSTANCES = No
    COPY_ATTR = Every Node
    CHILD_ID_ATTR = _hierarchy_child_id_list
    ID_SELECTION = ID and Parent ID
    MODE = Flatten One Level
    PART_NUMBER_FIELD = _part_number
    ID_ATTR = _hierarchy_id
    PARENT_ID_ATTR = _hierarchy_parent_id
    LIST_ATTR_MODE_LOOKUP = LEAN
    GEOM_NAME_FIELD = _geometry_name
    SPLIT_COMPOSITES = No
    DEAGGREGATED -> SpatialFilter_2 [input 1]
admingrense.kommuneflate (reader POSTGIS_1)
    attributes: kommuneid int4, navn varchar(80)
    -> Deaggregator
Deaggregator
    EXPLODE_INSTANCES = No
    COPY_ATTR = Every Node
    CHILD_ID_ATTR = _hierarchy_child_id_list
    ID_SELECTION = ID and Parent ID
    MODE = Flatten One Level
    PART_NUMBER_FIELD = _part_number
    ID_ATTR = _hierarchy_id
    PARENT_ID_ATTR = _hierarchy_parent_id
    LIST_ATTR_MODE_LOOKUP = LEAN
    GEOM_NAME_FIELD = _geometry_name
    SPLIT_COMPOSITES = No
    DEAGGREGATED -> SpatialFilter [input 2]
    DEAGGREGATED -> SpatialFilter_2 [input 2]
SpatialFilter
    USE_BOUNDING_BOX = No
    BASE_TYPE = Multiple Filters
    PREDICATE_VALUE = Intersects
    CURVE_BOUNDARY_RULE_PARAM = Default Rule
    PASS_CRITERIA = Pass Against One Filter
    PREDATTR = _predicate
    MERGE_ATTRS = Yes
    PASSED -> AttributeCreator
    FAILED -> AttributeCreator_2
AttributeCreator
    ATTR_LIST = avinor_stoysoner,1
    -> dekningsoversikt.dekningsoversikt (writer POSTGIS_2)
AttributeCreator_2
    ATTR_LIST = avinor_stoysoner,0
    -> dekningsoversikt.dekningsoversikt (writer POSTGIS_2)
SpatialFilter_2
    USE_BOUNDING_BOX = No
    BASE_TYPE = Multiple Filters
    PREDICATE_VALUE = Intersects
    CURVE_BOUNDARY_RULE_PARAM = Default Rule
    PASS_CRITERIA = Pass Against One Filter
    PREDATTR = _predicate
    MERGE_ATTRS = Yes
    PASSED -> AttributeCreator_3
    FAILED -> AttributeCreator_4
AttributeCreator_3
    ATTR_LIST = forsvaret_stoysoner,1
    -> dekningsoversikt.dekningsoversikt (writer POSTGIS_2)
AttributeCreator_4
    ATTR_LIST = forsvaret_stoysoner,0
    -> dekningsoversikt.dekningsoversikt (writer POSTGIS_2)
dekningsoversikt.dekningsoversikt (writer POSTGIS_2)
    attributes: kommuneid int4,PRIKEY, akvakultur bool, korallrev bool, dsb_110sentral bool, dsb_brannstasjon bool, dsb_distrkont_siv bool, dsb_sivforsvdistr bool, ra_brannsmitteomr bool, ra_tettetrehusm bool, ra_frededebygg bool, ra_enkeltminner bool, ra_kulturmiljo bool, ra_lokaliteter bool, ra_sikringssoner bool, kv_hovedbiled bool, kv_ispshavneanlegg bool, kv_losbordingsfelt bool, kv_losstasjoner bool, nve_flomsoner10 bool, nve_flomsoner20 bool, nve_flomsoner50 bool, nve_flomsoner100 bool, nve_flomsoner200 bool, nve_flomsoner500 bool, nve_flomsoner1000 bool, nve_flomsoner200_i_aar2100 bool, nve_flomsonekartplan bool, nve_elvis_hovedelv bool, nve_elvis_elvenett bool, nve_innsjodata bool,
      nve_dybdekart bool, nve_nedborfelt_regine bool, nve_vassdragsomrade bool, nve_totnedbfelt_mstasjon bool, nve_vannkraftverk bool, nve_vindparkomrader bool, nve_vindturbin bool, nve_kraftlinjer bool, nve_sjokabler bool, nve_transformatorstasjoner bool, nve_omradekonsesjoner bool, nve_sikringstiltak bool, nve_verneplan_vassdrag bool, nve_kvikkleire bool, nve_aktsomhet_snoskred bool, nve_aktsomhet_steinsprang bool, nve_aktsomhet_snosteinsprang bool, nve_aktsomhet_jordflomskred bool, nve_skredhendelser bool, nve_kraftverk_alle_kst bool, nve_magasin bool, nve_dam bool, nve_vanninntak bool, nve_vannvei bool, nve_delfelt_vannkraft bool, nve_vindkraftverk bool, nve_skredsoner bool, dsb_anleggfarligstoff bool, dsb_storulykkeanlegg bool, dsb_eksplosivanlegg bool,
      nibio_jordkvalitet bool, md_forurensetgrunn bool, md_frilstatligsikra bool, md_frilkartlverds bool, md_verdif_kulturlandsk bool, md_viktige_naturt bool, md_villreinomr bool, md_naturvernomr bool, md_naturvernomr_foresl bool, md_arter_nasjon_forv bool, md_naturt_landskap bool, md_naturt_utv bool, fkb_ar5 bool, fkb_adresse bool, fkb_arealbruk bool, fkb_bane bool, fkb_bygnanlegg bool, fkb_bygning bool, fkb_bygningspunkt bool, fkb_hoydekurve-5m bool, fkb_hoydekurve bool, fkb_ledning bool, fkb_ledningva bool, fkb_lufthavn bool, fkb_matrikkelkartdekteig bool, fkb_naturinfo bool, fkb_pbltiltak bool, fkb_servitutt bool, fkb_tekst1000 bool, fkb_tekst5000 bool,
      fkb_traktorvegsti bool, fkb_vann bool, fkb_vbase bool, fkb_veg bool, ldir_reinbeitedistrikt bool, ldir_reinbeiteomrade bool, ldir_reindriftsanlegg bool, ldir_beitehage bool, ldir_flyttlei bool, ldir_trekklei bool, ldir_oppsamlingsomrade bool, ldir_varbeite bool, ldir_sommerbeite bool, ldir_hostbeite bool, ldir_hostvinterbeite bool, ldir_vinterbeite bool, ldir_siidagrense bool, ldir_konvensjonsomrade bool, ldir_konsesjonsomrader bool, ldir_restriksjonsomrader bool, ldir_tamreinlag bool, ldir_restriksjonsgrense bool, ldir_rendal bool, ldir_trollheimen bool, ldir_avtaleomrader bool, ldir_ekspropriasjonsomrader bool, avinor_stoysoner bool, forsvaret_stoysoner bool
