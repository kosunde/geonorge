FME workspace Dekningsanalyse_Fiskeridir_RA_DSB_IMR_KV.fmw

Parameters:
- DestDataset_POSTGIS = geonortst@nnridb504:5432/geonor01tst   # Connection
- SourceDataset_POSTGIS = geonortst@nnridb504:5432/geonor01tst   # Connection
- SourceDataset_WFS_5 = http://kart.fiskeridir.no/wfs.aspx?SERVICE=WFS&amp;VERSION=1.0.0&amp;REQUEST=capabilities   # Source WFS (Web Feature Service) URL
- SourceDataset_WFS_6 = http://maps.imr.no/geoserver/ows?service=wfs   # Source WFS (Web Feature Service) URL
- SourceDataset_WFS_7 = http://kart.dsb.no/wfs.aspx?service=wfs&request=getcapabilities   # Source WFS (Web Feature Service) URL
- SourceDataset_ESRIJSON = http://askeladden_wms.ra.no/arcgis/rest/services/WMS/RA_Brannvern/MapServer/3/query?where=1%3D1&text=&objectIds=&time=&geometry=&geometryType=esriGeometryEnvelope&inSR=&spatialRel=esriSpatialRelIntersects&relationParam=&outFields=KommuneNummer&returnGeometry=false&maxAllowableOffset=&geometryPrecision=&outSR=&returnIdsOnly=false&returnCountOnly=false&orderByFields=&groupByFieldsForStatistics=&outStatistics=&returnZ=false&returnM=false&gdbVersion=&returnDistinctValues=true&f=pjson   # Source Esri-JSON File or URL
- SourceDataset_ESRIJSON_9 = http://askeladden_wms.ra.no/arcgis/rest/services/WMS/RA_Brannvern/MapServer/2/query?where=1%3D1&text=&objectIds=&time=&geometry=&geometryType=esriGeometryEnvelope&inSR=&spatialRel=esriSpatialRelIntersects&relationParam=&outFields=KommuneNummer&returnGeometry=false&maxAllowableOffset=&geometryPrecision=&outSR=&returnIdsOnly=false&returnCountOnly=false&orderByFields=&groupByFieldsForStatistics=&outStatistics=&returnZ=false&returnM=false&gdbVersion=&returnDistinctValues=true&f=pjson   # Source Esri-JSON File or URL
- SourceDataset_ESRIJSON_13 = http://askeladden_wms.ra.no/arcgis/rest/services/WMS/RA_Askeladden/MapServer/0/query?where=1%3D1&text=&objectIds=&time=&geometry=&geometryType=esriGeometryEnvelope&inSR=&spatialRel=esriSpatialRelIntersects&relationParam=&outFields=KOMM&returnGeometry=false&maxAllowableOffset=&geometryPrecision=&outSR=&returnIdsOnly=false&returnCountOnly=false&orderByFields=&groupByFieldsForStatistics=&outStatistics=&returnZ=false&returnM=false&gdbVersion=&returnDistinctValues=true&f=pjson   # Source Esri-JSON File or URL
- SourceDataset_ESRIJSON_11 = http://askeladden_wms.ra.no/arcgis/rest/services/WMS/RA_Askeladden/MapServer/4/query?where=1%3D1&text=&objectIds=&time=&geometry=&geometryType=esriGeometryEnvelope&inSR=&spatialRel=esriSpatialRelIntersects&relationParam=&outFields=KOMM&returnGeometry=false&maxAllowableOffset=&geometryPrecision=&outSR=&returnIdsOnly=false&returnCountOnly=false&orderByFields=&groupByFieldsForStatistics=&outStatistics=&returnZ=false&returnM=false&gdbVersion=&returnDistinctValues=true&f=pjson   # Source Esri-JSON File or URL
- SourceDataset_ESRIJSON_8 = http://askeladden_wms.ra.no/arcgis/rest/services/WMS/RA_Askeladden/MapServer/7/query?where=1%3D1&text=&objectIds=&time=&geometry=&geometryType=esriGeometryEnvelope&inSR=&spatialRel=esriSpatialRelIntersects&relationParam=&outFields=KOMM&returnGeometry=false&maxAllowableOffset=&geometryPrecision=&outSR=&returnIdsOnly=false&returnCountOnly=false&orderByFields=&groupByFieldsForStatistics=&outStatistics=&returnZ=false&returnM=false&gdbVersion=&returnDistinctValues=true&f=pjson   # Source Esri-JSON File or URL
- SourceDataset_ESRIJSON_10 = http://askeladden_wms.ra.no/arcgis/rest/services/WMS/RA_Askeladden/MapServer/5/query?where=1%3D1&text=&objectIds=&time=&geometry=&geometryType=esriGeometryEnvelope&inSR=&spatialRel=esriSpatialRelIntersects&relationParam=&outFields=KOMM&returnGeometry=false&maxAllowableOffset=&geometryPrecision=&outSR=&returnIdsOnly=false&returnCountOnly=false&orderByFields=&groupByFieldsForStatistics=&outStatistics=&returnZ=false&returnM=false&gdbVersion=&returnDistinctValues=true&f=pjson   # Source Esri-JSON File or URL
- SourceDataset_ESRIJSON_12 = http://askeladden_wms.ra.no/arcgis/rest/services/WMS/RA_Askeladden/MapServer/6/query?where=1%3D1&text=&objectIds=&time=&geometry=&geometryType=esriGeometryEnvelope&inSR=&spatialRel=esriSpatialRelIntersects&relationParam=&outFields=KOMM&returnGeometry=false&maxAllowableOffset=&geometryPrecision=&outSR=&returnIdsOnly=false&returnCountOnly=false&orderByFields=&groupByFieldsForStatistics=&outStatistics=&returnZ=false&returnM=false&gdbVersion=&returnDistinctValues=true&f=pjson   # Source Esri-JSON File or URL
- SourceDataset_WFS = http://153.44.6.24/a3_mapserver/wfs.ashx   # Source WFS (Web Feature Service) URL
- DestDataset_POSTGIS_4 = geonor01tst   # Database

Readers:
- POSTGIS_1: POSTGIS from $(SourceDataset_POSTGIS)
- WFS_1: WFS from $(SourceDataset_WFS_5)
- WFS_2: WFS from $(SourceDataset_WFS_6)
- WFS_3: WFS from $(SourceDataset_WFS_7)
- ESRIJSON_1: ESRIJSON from $(SourceDataset_ESRIJSON)
- ESRIJSON_2: ESRIJSON from $(SourceDataset_ESRIJSON_9)
- ESRIJSON_3: ESRIJSON from $(SourceDataset_ESRIJSON_13)
- ESRIJSON_4: ESRIJSON from $(SourceDataset_ESRIJSON_11)
- ESRIJSON_5: ESRIJSON from $(SourceDataset_ESRIJSON_8)
- ESRIJSON_6: ESRIJSON from $(SourceDataset_ESRIJSON_10)
- ESRIJSON_7: ESRIJSON from $(SourceDataset_ESRIJSON_12)
- WFS_4: WFS from $(SourceDataset_WFS)

Writers:
- POSTGIS_2: POSTGIS to $(DestDataset_POSTGIS_4)
- POSTGIS_3: POSTGIS to $(DestDataset_POSTGIS)

admingrense.kommuneflate (reader POSTGIS_1)
    attributes: kommuneid int4
    -> Reprojector
Reprojector
    INTERPOLATION_TYPE_NAME = Nearest Neighbor
    SOURCE = Read from feature
    RASTER_CELL_SIZE = Preserve Cells
    DEST = EPSG:32633
    REPROJECTED -> Deaggregator
Deaggregator
    COPY_ATTR = Every Node
    GEOM_NAME_FIELD = _geometry_name
    SPLIT_COMPOSITES = No
    EXPLODE_INSTANCES = No
    ID_SELECTION = ID and Parent ID
    CHILD_ID_ATTR = _hierarchy_child_id_list
    PARENT_ID_ATTR = _hierarchy_parent_id
    ID_ATTR = _hierarchy_id
    MODE = Flatten One Level
    PART_NUMBER_FIELD = _part_number
    LIST_ATTR_MODE_LOOKUP = LEAN
    DEAGGREGATED -> GeometryCoercer
GeometryCoercer
    GQUERY:
      for $geom in //geometry
      where $geom/count(parent::geometry) = 0
      return number($geom/@fme_id)
    KIND = fme_polygon
    COERCED -> SpatialFilter [input 2]
    COERCED -> SpatialFilter_2 [input 2]
    UNTOUCHED -> SpatialFilter_2 [input 2]
    COERCED -> SpatialFilter_3 [input 2]
    COERCED -> SpatialFilter_4 [input 2]
    UNTOUCHED -> SpatialFilter_4 [input 2]
    COERCED -> SpatialFilter_5 [input 2]
    UNTOUCHED -> SpatialFilter_5 [input 2]
    COERCED -> SpatialFilter_6 [input 2]
    UNTOUCHED -> SpatialFilter_6 [input 2]
    UNTOUCHED -> SpatialFilter [input 2]
    UNTOUCHED -> SpatialFilter_3 [input 2]
    COERCED -> GeometryRemover
    UNTOUCHED -> GeometryRemover
    UNTOUCHED -> SpatialFilter_7 [input 2]
    COERCED -> SpatialFilter_7 [input 2]
    COERCED -> SpatialFilter_8 [input 2]
    UNTOUCHED -> SpatialFilter_8 [input 2]
    COERCED -> SpatialFilter_9 [input 2]
    UNTOUCHED -> SpatialFilter_9 [input 2]
    COERCED -> SpatialFilter_10 [input 2]
    UNTOUCHED -> SpatialFilter_10 [input 2]
dekningsoversikt.dekningsoversikt (writer POSTGIS_3)
    attributes: kommuneid int4, akvakultur bool, dsb_sivforsvdistr bool, korallrev bool, dsb_brannstasjon bool, dsb_110sentral bool, dsb_distrkont_siv bool, ra_brannsmitteomr bool, ra_tettetrehusm bool, ra_frededebygg bool, ra_enkeltminner bool, ra_kulturmiljo bool, ra_lokaliteter bool, ra_sikringssoner bool, kv_hovedbiled bool, kv_ispshavneanlegg bool, kv_losbordingsfelt bool, kv_losstasjoner bool

Bookmark: Riksantikvaren
GeometryRemover
    -> FeatureMerger [input 1]
    -> FeatureMerger_7 [input 1]
    -> FeatureMerger_2 [input 1]
    -> FeatureMerger_3 [input 1]
    -> FeatureMerger_4 [input 1]
    -> FeatureMerger_5 [input 1]
    -> FeatureMerger_6 [input 1]
Note: Brannsmitteområder RA
ESRIJSON (reader ESRIJSON_2)
    attributes: Kommunenummer string
    -> FeatureMerger [input 2]
FeatureMerger
    SUPPLIERS_FIRST = No
    MERGE_TYPE = Attributes Only
    PROCESS_DUPS = No
    ATTR_ACCUM_MODE = Merge Supplier
    ATTR_CONFLICT_RES = Use Requestor
    IGNORE_NULLS = No
    JOIN_KEYS = @Value(kommuneid) @Value(Kommunenummer) AUTO
    MERGED -> AttributeCreator_13
    NOT_MERGED -> AttributeCreator_14
AttributeCreator_13
    ATTR_LIST = ra_brannsmitteomr,1
    -> dekningsoversikt.dekningsoversikt (writer POSTGIS_3)
AttributeCreator_14
    ATTR_LIST = ra_brannsmitteomr,0
    -> dekningsoversikt.dekningsoversikt (writer POSTGIS_3)
Note: Tette Trehusmiljø RA
ESRIJSON (reader ESRIJSON_1)
    attributes: Kommunenummer string
    -> FeatureMerger_2 [input 2]
FeatureMerger_2
    SUPPLIERS_FIRST = No
    MERGE_TYPE = Attributes Only
    PROCESS_DUPS = No
    ATTR_ACCUM_MODE = Merge Supplier
    ATTR_CONFLICT_RES = Use Requestor
    IGNORE_NULLS = No
    JOIN_KEYS = @Value(kommuneid) @Value(Kommunenummer) AUTO
    NOT_MERGED -> AttributeCreator_16
    MERGED -> AttributeCreator_15
AttributeCreator_15
    ATTR_LIST = ra_tettetrehusm,1
    -> dekningsoversikt.dekningsoversikt (writer POSTGIS_3)
AttributeCreator_16
    ATTR_LIST = ra_tettetrehusm,0
    -> dekningsoversikt.dekningsoversikt (writer POSTGIS_3)
Note: Fredede bygninger RA
ESRIJSON (reader ESRIJSON_3)
    attributes: KOMM int
    -> FeatureMerger_3 [input 2]
FeatureMerger_3
    SUPPLIERS_FIRST = No
    MERGE_TYPE = Attributes Only
    PROCESS_DUPS = No
    ATTR_ACCUM_MODE = Merge Supplier
    ATTR_CONFLICT_RES = Use Requestor
    IGNORE_NULLS = No
    JOIN_KEYS = @Value(kommuneid) @Value(KOMM) AUTO
    NOT_MERGED -> AttributeCreator_18
    MERGED -> AttributeCreator_17
AttributeCreator_17
    ATTR_LIST = ra_frededebygg,1
    -> dekningsoversikt.dekningsoversikt (writer POSTGIS_3)
AttributeCreator_18
    ATTR_LIST = ra_frededebygg,0
    -> dekningsoversikt.dekningsoversikt (writer POSTGIS_3)
Note: Enkeltminner RA
ESRIJSON (reader ESRIJSON_4)
    attributes: KOMM string
    -> FeatureMerger_4 [input 2]
FeatureMerger_4
    SUPPLIERS_FIRST = No
    MERGE_TYPE = Attributes Only
    PROCESS_DUPS = No
    ATTR_ACCUM_MODE = Merge Supplier
    ATTR_CONFLICT_RES = Use Requestor
    IGNORE_NULLS = No
    JOIN_KEYS = @Value(kommuneid) @Value(KOMM) AUTO
    NOT_MERGED -> AttributeCreator_20
    MERGED -> AttributeCreator_19
AttributeCreator_19
    ATTR_LIST = ra_enkeltminner,1
    -> dekningsoversikt.dekningsoversikt (writer POSTGIS_3)
AttributeCreator_20
    ATTR_LIST = ra_enkeltminner,0
    -> dekningsoversikt.dekningsoversikt (writer POSTGIS_3)
Note: Kulturmiljø RA
ESRIJSON (reader ESRIJSON_5)
    attributes: KOMM int
    -> FeatureMerger_5 [input 2]
FeatureMerger_5
    SUPPLIERS_FIRST = No
    MERGE_TYPE = Attributes Only
    PROCESS_DUPS = No
    ATTR_ACCUM_MODE = Merge Supplier
    ATTR_CONFLICT_RES = Use Requestor
    IGNORE_NULLS = No
    JOIN_KEYS = @Value(kommuneid) @Value(KOMM) AUTO
    NOT_MERGED -> AttributeCreator_22
    MERGED -> AttributeCreator_21
AttributeCreator_21
    ATTR_LIST = ra_kulturmiljo,1
    -> dekningsoversikt.dekningsoversikt (writer POSTGIS_3)
AttributeCreator_22
    ATTR_LIST = ra_kulturmiljo,0
    -> dekningsoversikt.dekningsoversikt (writer POSTGIS_3)
Note: Lokaliteter RA
ESRIJSON (reader ESRIJSON_6)
    attributes: KOMM int
    -> FeatureMerger_6 [input 2]
FeatureMerger_6
    SUPPLIERS_FIRST = No
    MERGE_TYPE = Attributes Only
    PROCESS_DUPS = No
    ATTR_ACCUM_MODE = Merge Supplier
    ATTR_CONFLICT_RES = Use Requestor
    IGNORE_NULLS = No
    JOIN_KEYS = @Value(kommuneid) @Value(KOMM) AUTO
    NOT_MERGED -> AttributeCreator_24
    MERGED -> AttributeCreator_23
AttributeCreator_23
    ATTR_LIST = ra_lokaliteter,1
    -> dekningsoversikt.dekningsoversikt (writer POSTGIS_3)
AttributeCreator_24
    ATTR_LIST = ra_lokaliteter,0
    -> dekningsoversikt.dekningsoversikt (writer POSTGIS_3)
Note: Sikringssoner RA
ESRIJSON (reader ESRIJSON_7)
    attributes: KOMM int
    -> FeatureMerger_7 [input 2]
FeatureMerger_7
    SUPPLIERS_FIRST = No
    MERGE_TYPE = Attributes Only
    PROCESS_DUPS = No
    ATTR_ACCUM_MODE = Merge Supplier
    ATTR_CONFLICT_RES = Use Requestor
    IGNORE_NULLS = No
    JOIN_KEYS = @Value(kommuneid) @Value(KOMM) AUTO
    MERGED -> AttributeCreator_25
    NOT_MERGED -> AttributeCreator_26
AttributeCreator_25
    ATTR_LIST = ra_sikringssoner,1
    -> dekningsoversikt.dekningsoversikt (writer POSTGIS_3)
AttributeCreator_26
    ATTR_LIST = ra_sikringssoner,0
    -> dekningsoversikt.dekningsoversikt (writer POSTGIS_3)

Bookmark: WFS-data
layer_92 (reader WFS_1)
    attributes: gml_parent_id xml_buffer, gml_parent_property xml_buffer, gml_id xml_buffer, msGeometry xml_geometry, id xml_buffer, navn xml_buffer, areal_m2 xml_buffer
    -> SpatialFilter [input 1]
layer_553 (reader WFS_1)
    attributes: gml_parent_id xml_buffer, gml_parent_property xml_buffer, gml_id xml_buffer, msGeometry xml_geometry, objectid xml_buffer, loknr xml_buffer, lokalitet xml_buffer, innehaver xml_buffer, organisasjonsnummer xml_buffer, firma_adresse xml_buffer, firma_poststed xml_buffer, post_adresse xml_buffer, post_poststed xml_buffer, tillatelsesnr xml_buffer, kapasitet xml_buffer, art xml_buffer, produksjon xml_buffer, formaal xml_buffer, plassering xml_buffer, vannmiljo xml_buffer, geom xml_buffer, av_class xml_buffer, tillatelse_html xml_buffer, geom_25833 xml_buffer
    -> SpatialFilter [input 1]
layer_245 (reader WFS_1)
    attributes: gml_parent_id xml_buffer, gml_parent_property xml_buffer, gml_id xml_buffer, msGeometry xml_geometry, loknr xml_buffer, lokalitet xml_buffer, tillatelsesnr xml_buffer, art xml_buffer, kapasitet xml_buffer, navn xml_buffer, produksjon xml_buffer, formaal xml_buffer, loktilstand xml_buffer, mudato xml_buffer, uri xml_buffer, plassering xml_buffer, prodorgnavn xml_buffer, miljoundersokelse_type xml_buffer, av_class xml_buffer
    -> SpatialFilter [input 1]
layer_460 (reader WFS_1)
    attributes: gml_parent_id xml_buffer, gml_parent_property xml_buffer, gml_id xml_buffer, msGeometry xml_geometry, loknr xml_buffer, lokalitet xml_buffer, tillatelsesnr xml_buffer, art xml_buffer, kapasitet xml_buffer, navn xml_buffer, produksjon xml_buffer, formaal xml_buffer, mudato xml_buffer, uri xml_buffer, plassering xml_buffer, prodorgnavn xml_buffer, miljoundersokelse_type xml_buffer, av_class xml_buffer
    -> SpatialFilter [input 1]

Bookmark: Akvakultur
SpatialFilter
    MERGE_ATTRS = Yes
    BASE_TYPE = Multiple Filters
    CURVE_BOUNDARY_RULE_PARAM = Default Rule
    USE_BOUNDING_BOX = No
    PREDICATE_VALUE = Intersects
    PREDATTR = _predicate
    PASS_CRITERIA = Pass Against One Filter
    PASSED -> AttributeCreator
    FAILED -> AttributeCreator_2
AttributeCreator
    ATTR_LIST = akvakultur,1
    -> dekningsoversikt.dekningsoversikt (writer POSTGIS_3)
AttributeCreator_2
    ATTR_LIST = akvakultur,0
    -> dekningsoversikt.dekningsoversikt (writer POSTGIS_3)

Bookmark: Kystverket
Note: Hoved - og biled
layer_37 (reader WFS_4)
    attributes: gml_parent_id xml_buffer, gml_parent_property xml_buffer, gml_id xml_buffer, msGeometry xml_geometry, navn xml_buffer, uuid xml_buffer, farlednummer xml_buffer, delstreknavn xml_buffer, farledpaabud xml_buffer, farledtype xml_buffer, farledstatus xml_buffer, kyv_region xml_buffer, lengde xml_buffer, datafangstdato xml_buffer, oppdateringsdato xml_buffer, gyldig_fra xml_buffer, gyldig_til xml_buffer, informasjon xml_buffer, maalemetode xml_buffer, noyaktighet xml_buffer, orginaldatavert xml_buffer, opphav xml_buffer, kopidato xml_buffer, id xml_buffer
    -> Deaggregator_2
Deaggregator_2
    GEOM_NAME_FIELD = _geometry_name
    SPLIT_COMPOSITES = No
    EXPLODE_INSTANCES = No
    MODE = Flatten All Levels
    LIST_ATTR_MODE_LOOKUP = LEAN
    DEAGGREGATED -> SpatialFilter_7 [input 1]
SpatialFilter_7
    MERGE_ATTRS = Yes
    BASE_TYPE = Multiple Filters
    CURVE_BOUNDARY_RULE_PARAM = Default Rule
    USE_BOUNDING_BOX = No
    PREDICATE_VALUE = Intersects
    PREDATTR = _predicate
    PASS_CRITERIA = Pass Against One Filter
    PASSED -> AttributeCreator_27
    FAILED -> AttributeCreator_28
AttributeCreator_27
    ATTR_LIST = kv_hovedbiled,1
    -> dekningsoversikt.dekningsoversikt (writer POSTGIS_3)
AttributeCreator_28
    ATTR_LIST = kv_hovedbiled,0
    -> dekningsoversikt.dekningsoversikt (writer POSTGIS_3)
Note: ISPS havneanlegg
layer_28 (reader WFS_4)
    attributes: gml_parent_id xml_buffer, gml_parent_property xml_buffer, gml_id xml_buffer, msGeometry xml_geometry, Cluster:FeatureCount xml_buffer, Cluster:Group xml_buffer
    -> SpatialFilter_8 [input 1]
SpatialFilter_8
    MERGE_ATTRS = Yes
    BASE_TYPE = Multiple Filters
    CURVE_BOUNDARY_RULE_PARAM = Default Rule
    USE_BOUNDING_BOX = No
    PREDICATE_VALUE = Intersects
    PREDATTR = _predicate
    PASS_CRITERIA = Pass Against One Filter
    PASSED -> AttributeCreator_29
    FAILED -> AttributeCreator_30
AttributeCreator_29
    ATTR_LIST = kv_ispshavneanlegg,1
    -> dekningsoversikt.dekningsoversikt (writer POSTGIS_3)
AttributeCreator_30
    ATTR_LIST = kv_ispshavneanlegg,0
    -> dekningsoversikt.dekningsoversikt (writer POSTGIS_3)
Note: Losbordingsfelt
layer_29 (reader WFS_4)
    attributes: gml_parent_id xml_buffer, gml_parent_property xml_buffer, gml_id xml_buffer, msGeometry xml_geometry, losbordingsfelt xml_buffer, nord xml_buffer, ost xml_buffer, kommune xml_buffer, merknad_begrensning xml_buffer, merknad2 xml_buffer, sjotrafikkomraade xml_buffer, uuid xml_buffer, datafangstdato xml_buffer, oppdateringsdato xml_buffer, gyldig_fra xml_buffer, gyldig_til xml_buffer, informasjon xml_buffer, maalemetode xml_buffer, noyaktighet xml_buffer, originaldatavert xml_buffer, opphav xml_buffer, kopidato xml_buffer, id xml_buffer
    -> SpatialFilter_9 [input 1]
SpatialFilter_9
    MERGE_ATTRS = Yes
    BASE_TYPE = Multiple Filters
    CURVE_BOUNDARY_RULE_PARAM = Default Rule
    USE_BOUNDING_BOX = No
    PREDICATE_VALUE = Intersects
    PREDATTR = _predicate
    PASS_CRITERIA = Pass Against One Filter
    PASSED -> AttributeCreator_31
    FAILED -> AttributeCreator_32
AttributeCreator_31
    ATTR_LIST = kv_losbordingsfelt,1
    -> dekningsoversikt.dekningsoversikt (writer POSTGIS_3)
AttributeCreator_32
    ATTR_LIST = kv_losbordingsfelt,0
    -> dekningsoversikt.dekningsoversikt (writer POSTGIS_3)
Note: Losstasjoner
layer_59 (reader WFS_4)
    attributes: gml_parent_id xml_buffer, gml_parent_property xml_buffer, gml_id xml_buffer, msGeometry xml_geometry, gid xml_buffer, navn xml_buffer, dato xml_buffer, funksjon xml_buffer, distrikt xml_buffer, los1 xml_buffer, los2 xml_buffer
    -> SpatialFilter_10 [input 1]
SpatialFilter_10
    MERGE_ATTRS = Yes
    BASE_TYPE = Multiple Filters
    CURVE_BOUNDARY_RULE_PARAM = Default Rule
    USE_BOUNDING_BOX = No
    PREDICATE_VALUE = Intersects
    PREDATTR = _predicate
    PASS_CRITERIA = Pass Against One Filter
    PASSED -> AttributeCreator_33
    FAILED -> AttributeCreator_34
AttributeCreator_33
    ATTR_LIST = kv_losstasjoner,1
    -> dekningsoversikt.dekningsoversikt (writer POSTGIS_3)
AttributeCreator_34
    ATTR_LIST = kv_losstasjoner,0
    -> dekningsoversikt.dekningsoversikt (writer POSTGIS_3)

Bookmark: WFS-data
Note: Sivilforsvarsdistrikt
layer_307 (reader WFS_3)
    attributes: gml_parent_id xml_buffer, gml_parent_property xml_buffer, gml_id xml_buffer, msGeometry xml_geometry, SIVDISTRIK xml_buffer, URL xml_buffer, NAVN xml_buffer
    -> SpatialFilter_2 [input 1]
Note: Distriktskontor sivilforsvaret
layer_309 (reader WFS_3)
    attributes: gml_parent_id xml_buffer, gml_parent_property xml_buffer, gml_id xml_buffer, msGeometry xml_geometry, TYPE xml_buffer, KOMMUNE xml_buffer, URL xml_buffer, NAVN xml_buffer, DATO xml_buffer
    -> SpatialFilter_4 [input 1]
Note: Brannstasjoner
layer_511 (reader WFS_3)
    attributes: gml_parent_id xml_buffer, gml_parent_property xml_buffer, gml_id xml_buffer, msGeometry xml_geometry, BRANNSTASJ xml_buffer, KASERNERT xml_buffer, BRANNVESEN xml_buffer, ANLEGGID xml_buffer, AJOURDATO xml_buffer, INFORMASJ xml_buffer, OPPHAV xml_buffer, STASJONSTY xml_buffer, OBJTYPE xml_buffer, DATO xml_buffer, BRANNSTA_ xml_buffer
    -> SpatialFilter_5 [input 1]
Note: 110-sentraldistrikter
layer_562 (reader WFS_3)
    attributes: gml_parent_id xml_buffer, gml_parent_property xml_buffer, gml_id xml_buffer, msGeometry xml_geometry, POLY_ xml_buffer, POLY_ID xml_buffer, AREA xml_buffer, PERIMETER xml_buffer, OPPR xml_buffer, X xml_buffer, Y xml_buffer, KOORDH xml_buffer, SENTRAL xml_buffer, LOKALISERI xml_buffer, OPPHAV xml_buffer, MALEMETODE xml_buffer, NOYAKTIGHE xml_buffer, SYNBARHET xml_buffer, H_MALEMETO xml_buffer, H_NOYAKTIG xml_buffer, MAX_AVVIK xml_buffer, OBJTYPE xml_buffer, NAVN xml_buffer, DATO xml_buffer
    -> SpatialFilter_6 [input 1]

Bookmark: DSB
SpatialFilter_2
    MERGE_ATTRS = Yes
    BASE_TYPE = Multiple Filters
    CURVE_BOUNDARY_RULE_PARAM = Default Rule
    USE_BOUNDING_BOX = No
    PREDICATE_VALUE = Intersects
    PREDATTR = _predicate
    PASS_CRITERIA = Pass Against One Filter
    PASSED -> AttributeCreator_3
    FAILED -> AttributeCreator_4
AttributeCreator_3
    ATTR_LIST = dsb_sivforsvdistr,1
    -> dekningsoversikt.dekningsoversikt (writer POSTGIS_3)
AttributeCreator_4
    ATTR_LIST = dsb_sivforsvdistr,0
    -> dekningsoversikt.dekningsoversikt (writer POSTGIS_3)
SpatialFilter_4
    MERGE_ATTRS = Yes
    BASE_TYPE = Multiple Filters
    CURVE_BOUNDARY_RULE_PARAM = Default Rule
    USE_BOUNDING_BOX = No
    PREDICATE_VALUE = Intersects
    PREDATTR = _predicate
    PASS_CRITERIA = Pass Against One Filter
    PASSED -> AttributeCreator_7
    FAILED -> AttributeCreator_8
AttributeCreator_7
    ATTR_LIST = dsb_distrkont_siv,1
    -> dekningsoversikt.dekningsoversikt (writer POSTGIS_3)
AttributeCreator_8
    ATTR_LIST = dsb_distrkont_siv,0
    -> dekningsoversikt.dekningsoversikt (writer POSTGIS_3)
SpatialFilter_5
    MERGE_ATTRS = Yes
    BASE_TYPE = Multiple Filters
    CURVE_BOUNDARY_RULE_PARAM = Default Rule
    USE_BOUNDING_BOX = No
    PREDICATE_VALUE = Intersects
    PREDATTR = _predicate
    PASS_CRITERIA = Pass Against One Filter
    PASSED -> AttributeCreator_9
    FAILED -> AttributeCreator_10
AttributeCreator_9
    ATTR_LIST = dsb_brannstasjon,1
    -> dekningsoversikt.dekningsoversikt (writer POSTGIS_3)
AttributeCreator_10
    ATTR_LIST = dsb_brannstasjon,0
    -> dekningsoversikt.dekningsoversikt (writer POSTGIS_3)
SpatialFilter_6
    MERGE_ATTRS = Yes
    BASE_TYPE = Multiple Filters
    CURVE_BOUNDARY_RULE_PARAM = Default Rule
    USE_BOUNDING_BOX = No
    PREDICATE_VALUE = Intersects
    PREDATTR = _predicate
    PASS_CRITERIA = Pass Against One Filter
    PASSED -> AttributeCreator_11
    FAILED -> AttributeCreator_12
AttributeCreator_11
    ATTR_LIST = dsb_110sentral,1
    -> dekningsoversikt.dekningsoversikt (writer POSTGIS_3)
AttributeCreator_12
    ATTR_LIST = dsb_110sentral,0
    -> dekningsoversikt.dekningsoversikt (writer POSTGIS_3)

Bookmark: WFS-data
coralreefs (reader WFS_2)
    attributes: gml_parent_id xml_buffer, gml_parent_property xml_buffer, gml_id xml_buffer, the_geom xml_geometry, Nummer_uni xml_real64, Nummer_uni.xsi_nil xml_boolean, Habitat_Ty xml_buffer, Habitat_Ty.xsi_nil xml_boolean, Verifisert xml_buffer, Verifisert.xsi_nil xml_boolean, Verifise_1 xml_buffer, Verifise_1.xsi_nil xml_boolean, Observasjo xml_buffer, Observasjo.xsi_nil xml_boolean, Observas_1 xml_buffer, Observas_1.xsi_nil xml_boolean, Observas_2 xml_buffer, Observas_2.xsi_nil xml_boolean, Steds_Navn xml_buffer, Steds_Navn.xsi_nil xml_boolean, Breddegrad xml_real64, Breddegrad.xsi_nil xml_boolean, Lengdegrad xml_real64, Lengdegrad.xsi_nil xml_boolean, Posisjon_T xml_buffer, Posisjon_T.xsi_nil xml_boolean, Nøyaktigh xml_real64, Nøyaktigh.xsi_nil xml_boolean, Referanse xml_buffer, Referanse.xsi_nil xml_boolean,
      Metode xml_buffer, Metode.xsi_nil xml_boolean, Dybde_Øvr xml_real64, Dybde_Øvr.xsi_nil xml_boolean, Dybde_Nedr xml_real64, Dybde_Nedr.xsi_nil xml_boolean, Kilde xml_buffer, Kilde.xsi_nil xml_boolean
    -> Reprojector_2

Bookmark: Havforskningsinstituttet
Reprojector_2
    INTERPOLATION_TYPE_NAME = Nearest Neighbor
    SOURCE = Read from feature
    RASTER_CELL_SIZE = Preserve Cells
    DEST = EPSG:32633
    REPROJECTED -> SpatialFilter_3 [input 1]
SpatialFilter_3
    MERGE_ATTRS = Yes
    BASE_TYPE = Multiple Filters
    CURVE_BOUNDARY_RULE_PARAM = Default Rule
    USE_BOUNDING_BOX = No
    PREDICATE_VALUE = Intersects
    PREDATTR = _predicate
    PASS_CRITERIA = Pass Against One Filter
    PASSED -> AttributeCreator_5
    FAILED -> AttributeCreator_6
AttributeCreator_5
    ATTR_LIST = korallrev,1
    -> dekningsoversikt.dekningsoversikt (writer POSTGIS_3)
AttributeCreator_6
    ATTR_LIST = korallrev,0
    -> dekningsoversikt.dekningsoversikt (writer POSTGIS_3)
