FME workspace Dekningsanalyse_MD_dataimport.fmw

Parameters:
- MINX = -76110   # Minimum X
- MINY = 6448054   # Minimum Y
- MAXX = 1103469   # Maximum X
- MAXY = 8686472   # Maximum Y
- SourceDataset_GEOJSON = http://gis3.nve.no/map/rest/services/Elvenett/MapServer/1/query?where=&text=&objectIds=&time=&geometry=&geometryType=esriGeometryEnvelope&inSR=&spatialRel=esriSpatialRelIntersects&relationParam=&outFields=&returnGeometry=true&maxAllowableOffset=&geometryPrecision=&outSR=&returnIdsOnly=false&returnCountOnly=false&orderByFields=&groupByFieldsForStatistics=&outStatistics=&returnZ=false&returnM=false&gdbVersion=&returnDistinctValues=false&returnTrueCurves=false&resultOffset=&resultRecordCount=&f=pjson   # Source GeoJSON File or URL
- DestDataset_SHAPE = $(FME_MF_DIR)Temp_data\MD   # Destination Esri Shape Folder

Readers:
- GEOJSON_1: GEOJSON from $(SourceDataset_GEOJSON)

Writers:
- SHAPE_1: SHAPE to $(DestDataset_SHAPE)

Note: Lager polygon av / envelope
Creator_11 [off]
    COORDS = $(MINX) $(MINY) $(MAXX) $(MINY) $(MAXX) $(MAXY)  $(MINX) $(MAXY)  $(MINX) $(MINY)
    GEOMTYPE = 2D Coordinate List
    COORDSYS = EPSG:25833
    NUM = 1
    CREATED -> Reprojector_11 [off]
Note: Projiserer envelopen til 25833
Reprojector_11 [off]
    INTERPOLATION_TYPE_NAME = Nearest Neighbor
    DEST = EPSG:25833
    SOURCE = Read from feature
    RASTER_CELL_SIZE = Preserve Cells
    STROKE_ARCS = Yes
    REPROJECTED -> Tiler_10 [off]
Note: Tiler opp envelopen i mindre / områder
Tiler_10 [off]
    TILING_TYPE = Tile Size
    COL_ATTR = _column
    XINC = 100000
    ROW_ATTR = _row
    YINC = 100000
    TILED -> BoundsExtractor_10 [off]
BoundsExtractor_10 [off]
    ZMIN = _zmin
    ZMAX = _zmax
    XMIN = _xmin
    XMAX = _xmax
    YMIN = _ymin
    YMAX = _ymax
    -> AttributeCreator_10 [off]
AttributeCreator_10 [off]
    ATTR_LIST = Query,http://kart.miljodirektoratet.no/arcgis/rest/services/grunnforurensning/MapServer/0/query?where=1%3D1&text=&objectIds=&time=&geometry=@Value(_xmin),@Value(_ymin),@Value(_xmax),@Value(_ymax)&geometryType=esriGeometryEnvelope&inSR=&spatialRel=esriSpatialRelIntersects&relationParam=&outFields=&returnGeometry=true&maxAllowableOffset=&geometryPrecision=&outSR=&returnIdsOnly=false&returnCountOnly=false&orderByFields=&groupByFieldsForStatistics=&outStatistics=&returnZ=false&returnM=false&gdbVersion=&returnDistinctValues=false&returnTrueCurves=false&resultOffset=&resultRecordCount=&f=pjson
    -> FeatureReader_10 [off]
FeatureReader_10 [off]
    OUTPUT_FEATURES_DISPLAY = Only Data Features
    COMBINE_GEOM = Use Result
    ATTR_ACCUM_MODE = Only Use Result
    FEATURETYPES_RADIO = FEATURETYPES
    ESRIJSON_SIMPLIFY_MULTIS = Yes
    INTERACT = <No Spatial Filter>
    ESRIJSON_USE_SEARCH_ENVELOPE = NO
    DATASET = @Value(Query)
    FORMAT = ESRIJSON
    ESRIJSON_MAKE_DONUTS = No
    ESRIJSON_USE_BASENAME_AS_DEFAULT_FEATURE_TYPE = No
    ESRIJSON_MAKE_PATHS = No
    ESRIJSON_DELETE_DOWNLOAD_FILE = Yes
    ESRIJSON_CLIP_TO_ENVELOPE = NO
    <OTHER> -> Matcher_10 [off]
Matcher_10 [off]
    MATCH = 2D
    MATCH_STRATEGY = Match Selected Attributes
    CNT_ATTR = _match_id
    BLANK_AND_MISSING_DIFFER = No
    LENIENT_MATCH = No
    SINGLE_MATCHED -> GF_lokalitet (writer SHAPE_1) [off]
    NOT_MATCHED -> GF_lokalitet (writer SHAPE_1) [off]
GF_lokalitet (writer SHAPE_1) [off]
    attributes: _match_id char(200)
Note: Lager polygon av / envelope
Creator_2 [off]
    COORDS = $(MINX) $(MINY) $(MAXX) $(MINY) $(MAXX) $(MAXY)  $(MINX) $(MAXY)  $(MINX) $(MINY)
    GEOMTYPE = 2D Coordinate List
    COORDSYS = EPSG:25833
    NUM = 1
    CREATED -> Reprojector_2 [off]
Note: Projiserer envelopen til 25833
Reprojector_2 [off]
    INTERPOLATION_TYPE_NAME = Nearest Neighbor
    DEST = EPSG:25833
    SOURCE = Read from feature
    RASTER_CELL_SIZE = Preserve Cells
    STROKE_ARCS = Yes
    REPROJECTED -> Tiler_2 [off]
Note: Tiler opp envelopen i mindre / områder
Tiler_2 [off]
    TILING_TYPE = Tile Size
    COL_ATTR = _column
    XINC = 100000
    ROW_ATTR = _row
    YINC = 100000
    TILED -> BoundsExtractor_2 [off]
BoundsExtractor_2 [off]
    ZMIN = _zmin
    ZMAX = _zmax
    XMIN = _xmin
    XMAX = _xmax
    YMIN = _ymin
    YMAX = _ymax
    -> AttributeCreator_2 [off]
AttributeCreator_2 [off]
    ATTR_LIST = Query,http://wms.miljodirektoratet.no/arcgis/rest/services/friluftsliv_statlig_sikra/MapServer/0/query?where=1%3D1&text=&objectIds=&time=&geometry=@Value(_xmin),@Value(_ymin),@Value(_xmax),@Value(_ymax)&geometryType=esriGeometryEnvelope&inSR=&spatialRel=esriSpatialRelIntersects&relationParam=&outFields=&returnGeometry=true&maxAllowableOffset=&geometryPrecision=&outSR=&returnIdsOnly=false&returnCountOnly=false&orderByFields=&groupByFieldsForStatistics=&outStatistics=&returnZ=false&returnM=false&gdbVersion=&returnDistinctValues=false&returnTrueCurves=false&resultOffset=&resultRecordCount=&f=pjson
    -> FeatureReader_2 [off]
FeatureReader_2 [off]
    OUTPUT_FEATURES_DISPLAY = Only Data Features
    COMBINE_GEOM = Use Result
    ATTR_ACCUM_MODE = Only Use Result
    FEATURETYPES_RADIO = FEATURETYPES
    ESRIJSON_SIMPLIFY_MULTIS = Yes
    INTERACT = <No Spatial Filter>
    ESRIJSON_USE_SEARCH_ENVELOPE = NO
    DATASET = @Value(Query)
    FORMAT = ESRIJSON
    ESRIJSON_MAKE_DONUTS = No
    ESRIJSON_USE_BASENAME_AS_DEFAULT_FEATURE_TYPE = No
    ESRIJSON_MAKE_PATHS = No
    ESRIJSON_DELETE_DOWNLOAD_FILE = Yes
    ESRIJSON_CLIP_TO_ENVELOPE = NO
    <OTHER> -> Matcher_2 [off]
Matcher_2 [off]
    MATCH = 2D
    MATCH_STRATEGY = Match Selected Attributes
    CNT_ATTR = _match_id
    BLANK_AND_MISSING_DIFFER = No
    LENIENT_MATCH = No
    SINGLE_MATCHED -> Fril_statligsikra (writer SHAPE_1) [off]
    NOT_MATCHED -> Fril_statligsikra (writer SHAPE_1) [off]
Fril_statligsikra (writer SHAPE_1) [off]
    attributes: _match_id char(200)
Note: Lager polygon av / envelope
Creator_3 [off]
    COORDS = $(MINX) $(MINY) $(MAXX) $(MINY) $(MAXX) $(MAXY)  $(MINX) $(MAXY)  $(MINX) $(MINY)
    GEOMTYPE = 2D Coordinate List
    COORDSYS = EPSG:25833
    NUM = 1
    CREATED -> Reprojector_3 [off]
Note: Projiserer envelopen til 25833
Reprojector_3 [off]
    INTERPOLATION_TYPE_NAME = Nearest Neighbor
    DEST = EPSG:25833
    SOURCE = Read from feature
    RASTER_CELL_SIZE = Preserve Cells
    STROKE_ARCS = Yes
    REPROJECTED -> Tiler_3 [off]
Note: Tiler opp envelopen i mindre / områder
Tiler_3 [off]
    TILING_TYPE = Tile Size
    COL_ATTR = _column
    XINC = 100000
    ROW_ATTR = _row
    YINC = 100000
    TILED -> BoundsExtractor_3 [off]
BoundsExtractor_3 [off]
    ZMIN = _zmin
    ZMAX = _zmax
    XMIN = _xmin
    XMAX = _xmax
    YMIN = _ymin
    YMAX = _ymax
    -> AttributeCreator_3 [off]
AttributeCreator_3 [off]
    ATTR_LIST = Query,http://wms.miljodirektoratet.no/arcgis/rest/services/friluftsliv_kartlagt/MapServer/0/query?where=1%3D1&text=&objectIds=&time=&geometry=@Value(_xmin),@Value(_ymin),@Value(_xmax),@Value(_ymax)&geometryType=esriGeometryEnvelope&inSR=&spatialRel=esriSpatialRelIntersects&relationParam=&outFields=&returnGeometry=true&maxAllowableOffset=&geometryPrecision=&outSR=&returnIdsOnly=false&returnCountOnly=false&orderByFields=&groupByFieldsForStatistics=&outStatistics=&returnZ=false&returnM=false&gdbVersion=&returnDistinctValues=false&returnTrueCurves=false&resultOffset=&resultRecordCount=&f=pjson
    -> FeatureReader_3 [off]
FeatureReader_3 [off]
    OUTPUT_FEATURES_DISPLAY = Only Data Features
    COMBINE_GEOM = Use Result
    ATTR_ACCUM_MODE = Only Use Result
    FEATURETYPES_RADIO = FEATURETYPES
    ESRIJSON_SIMPLIFY_MULTIS = Yes
    INTERACT = <No Spatial Filter>
    ESRIJSON_USE_SEARCH_ENVELOPE = NO
    DATASET = @Value(Query)
    FORMAT = ESRIJSON
    ESRIJSON_MAKE_DONUTS = No
    ESRIJSON_USE_BASENAME_AS_DEFAULT_FEATURE_TYPE = No
    ESRIJSON_MAKE_PATHS = No
    ESRIJSON_DELETE_DOWNLOAD_FILE = Yes
    ESRIJSON_CLIP_TO_ENVELOPE = NO
    <OTHER> -> Reprojector [off]
Reprojector [off]
    INTERPOLATION_TYPE_NAME = Nearest Neighbor
    DEST = EPSG:32633
    SOURCE = Read from feature
    RASTER_CELL_SIZE = Preserve Cells
    REPROJECTED -> Matcher_3 [off]
Matcher_3 [off]
    MATCH = 2D
    MATCH_STRATEGY = Match Selected Attributes
    CNT_ATTR = _match_id
    BLANK_AND_MISSING_DIFFER = No
    LENIENT_MATCH = No
    SINGLE_MATCHED -> Fril_kartlverd (writer SHAPE_1) [off]
    NOT_MATCHED -> Fril_kartlverd (writer SHAPE_1) [off]
Fril_kartlverd (writer SHAPE_1) [off]
    attributes: _match_id char(200)
Note: Lager polygon av / envelope
Creator_4 [off]
    COORDS = $(MINX) $(MINY) $(MAXX) $(MINY) $(MAXX) $(MAXY)  $(MINX) $(MAXY)  $(MINX) $(MINY)
    GEOMTYPE = 2D Coordinate List
    COORDSYS = EPSG:25833
    NUM = 1
    CREATED -> Reprojector_4 [off]
Note: Projiserer envelopen til 25833
Reprojector_4 [off]
    INTERPOLATION_TYPE_NAME = Nearest Neighbor
    DEST = EPSG:25833
    SOURCE = Read from feature
    RASTER_CELL_SIZE = Preserve Cells
    STROKE_ARCS = Yes
    REPROJECTED -> Tiler_4 [off]
Note: Tiler opp envelopen i mindre / områder
Tiler_4 [off]
    TILING_TYPE = Tile Size
    COL_ATTR = _column
    XINC = 100000
    ROW_ATTR = _row
    YINC = 100000
    TILED -> BoundsExtractor_4 [off]
BoundsExtractor_4 [off]
    ZMIN = _zmin
    ZMAX = _zmax
    XMIN = _xmin
    XMAX = _xmax
    YMIN = _ymin
    YMAX = _ymax
    -> AttributeCreator_4 [off]
AttributeCreator_4 [off]
    ATTR_LIST = Query,http://wms.miljodirektoratet.no/arcgis/rest/services/helhetlige_kulturlandskap/MapServer/0/query?where=1%3D1&text=&objectIds=&time=&geometry=@Value(_xmin),@Value(_ymin),@Value(_xmax),@Value(_ymax)&geometryType=esriGeometryEnvelope&inSR=&spatialRel=esriSpatialRelIntersects&relationParam=&outFields=&returnGeometry=true&maxAllowableOffset=&geometryPrecision=&outSR=&returnIdsOnly=false&returnCountOnly=false&orderByFields=&groupByFieldsForStatistics=&outStatistics=&returnZ=false&returnM=false&gdbVersion=&returnDistinctValues=false&returnTrueCurves=false&resultOffset=&resultRecordCount=&f=pjson
    -> FeatureReader_4 [off]
FeatureReader_4 [off]
    OUTPUT_FEATURES_DISPLAY = Only Data Features
    COMBINE_GEOM = Use Result
    ATTR_ACCUM_MODE = Only Use Result
    FEATURETYPES_RADIO = FEATURETYPES
    ESRIJSON_SIMPLIFY_MULTIS = Yes
    INTERACT = <No Spatial Filter>
    ESRIJSON_USE_SEARCH_ENVELOPE = NO
    DATASET = @Value(Query)
    FORMAT = ESRIJSON
    ESRIJSON_MAKE_DONUTS = No
    ESRIJSON_USE_BASENAME_AS_DEFAULT_FEATURE_TYPE = No
    ESRIJSON_MAKE_PATHS = No
    ESRIJSON_DELETE_DOWNLOAD_FILE = Yes
    ESRIJSON_CLIP_TO_ENVELOPE = NO
    <OTHER> -> Reprojector_5 [off]
Reprojector_5 [off]
    INTERPOLATION_TYPE_NAME = Nearest Neighbor
    DEST = EPSG:32633
    SOURCE = Read from feature
    RASTER_CELL_SIZE = Preserve Cells
    REPROJECTED -> Matcher_4 [off]
Matcher_4 [off]
    MATCH = 2D
    MATCH_STRATEGY = Match Selected Attributes
    CNT_ATTR = _match_id
    BLANK_AND_MISSING_DIFFER = No
    LENIENT_MATCH = No
    SINGLE_MATCHED -> Verdifulle_kulturlandskap (writer SHAPE_1) [off]
    NOT_MATCHED -> Verdifulle_kulturlandskap (writer SHAPE_1) [off]
Verdifulle_kulturlandskap (writer SHAPE_1) [off]
    attributes: _match_id char(200)
Note: Lager polygon av / envelope
Creator_5 [off]
    COORDS = $(MINX) $(MINY) $(MAXX) $(MINY) $(MAXX) $(MAXY)  $(MINX) $(MAXY)  $(MINX) $(MINY)
    GEOMTYPE = 2D Coordinate List
    COORDSYS = EPSG:25833
    NUM = 1
    CREATED -> Reprojector_6 [off]
Note: Projiserer envelopen til 25833
Reprojector_6 [off]
    INTERPOLATION_TYPE_NAME = Nearest Neighbor
    DEST = EPSG:25833
    SOURCE = Read from feature
    RASTER_CELL_SIZE = Preserve Cells
    STROKE_ARCS = Yes
    REPROJECTED -> Tiler_5 [off]
Note: Tiler opp envelopen i mindre / områder
Tiler_5 [off]
    TILING_TYPE = Tile Size
    COL_ATTR = _column
    XINC = 100000
    ROW_ATTR = _row
    YINC = 100000
    TILED -> BoundsExtractor_5 [off]
BoundsExtractor_5 [off]
    ZMIN = _zmin
    ZMAX = _zmax
    XMIN = _xmin
    XMAX = _xmax
    YMIN = _ymin
    YMAX = _ymax
    -> AttributeCreator_5 [off]
AttributeCreator_5 [off]
    ATTR_LIST = Query,http://wms.miljodirektoratet.no/arcgis/rest/services/naturtyper_naturbase/MapServer/1/query?where=1%3D1&text=&objectIds=&time=&geometry=@Value(_xmin),@Value(_ymin),@Value(_xmax),@Value(_ymax)&geometryType=esriGeometryEnvelope&inSR=&spatialRel=esriSpatialRelIntersects&relationParam=&outFields=&returnGeometry=true&maxAllowableOffset=&geometryPrecision=&outSR=&returnIdsOnly=false&returnCountOnly=false&orderByFields=&groupByFieldsForStatistics=&outStatistics=&returnZ=false&returnM=false&gdbVersion=&returnDistinctValues=false&returnTrueCurves=false&resultOffset=&resultRecordCount=&f=pjson
    -> FeatureReader_5 [off]
FeatureReader_5 [off]
    OUTPUT_FEATURES_DISPLAY = Only Data Features
    COMBINE_GEOM = Use Result
    ATTR_ACCUM_MODE = Only Use Result
    FEATURETYPES_RADIO = FEATURETYPES
    ESRIJSON_SIMPLIFY_MULTIS = Yes
    INTERACT = <No Spatial Filter>
    ESRIJSON_USE_SEARCH_ENVELOPE = NO
    DATASET = @Value(Query)
    FORMAT = ESRIJSON
    ESRIJSON_MAKE_DONUTS = No
    ESRIJSON_USE_BASENAME_AS_DEFAULT_FEATURE_TYPE = No
    ESRIJSON_MAKE_PATHS = No
    ESRIJSON_DELETE_DOWNLOAD_FILE = Yes
    ESRIJSON_CLIP_TO_ENVELOPE = NO
    <OTHER> -> Reprojector_7 [off]
Reprojector_7 [off]
    INTERPOLATION_TYPE_NAME = Nearest Neighbor
    DEST = EPSG:32633
    SOURCE = Read from feature
    RASTER_CELL_SIZE = Preserve Cells
    REPROJECTED -> Matcher_5 [off]
Matcher_5 [off]
    MATCH = 2D
    MATCH_STRATEGY = Match Selected Attributes
    CNT_ATTR = _match_id
    BLANK_AND_MISSING_DIFFER = No
    LENIENT_MATCH = No
    SINGLE_MATCHED -> Viktige_naturtyper (writer SHAPE_1) [off]
    NOT_MATCHED -> Viktige_naturtyper (writer SHAPE_1) [off]
Viktige_naturtyper (writer SHAPE_1) [off]
    attributes: _match_id char(200)
Note: Lager polygon av / envelope
Creator_6 [off]
    COORDS = $(MINX) $(MINY) $(MAXX) $(MINY) $(MAXX) $(MAXY)  $(MINX) $(MAXY)  $(MINX) $(MINY)
    GEOMTYPE = 2D Coordinate List
    COORDSYS = EPSG:25833
    NUM = 1
    CREATED -> Reprojector_8 [off]
Note: Projiserer envelopen til 25833
Reprojector_8 [off]
    INTERPOLATION_TYPE_NAME = Nearest Neighbor
    DEST = EPSG:25833
    SOURCE = Read from feature
    RASTER_CELL_SIZE = Preserve Cells
    STROKE_ARCS = Yes
    REPROJECTED -> Tiler_6 [off]
Note: Tiler opp envelopen i mindre / områder
Tiler_6 [off]
    TILING_TYPE = Tile Size
    COL_ATTR = _column
    XINC = 100000
    ROW_ATTR = _row
    YINC = 100000
    TILED -> BoundsExtractor_6 [off]
BoundsExtractor_6 [off]
    ZMIN = _zmin
    ZMAX = _zmax
    XMIN = _xmin
    XMAX = _xmax
    YMIN = _ymin
    YMAX = _ymax
    -> AttributeCreator_6 [off]
AttributeCreator_6 [off]
    ATTR_LIST = Query,http://wms.miljodirektoratet.no/arcgis/rest/services/villreinomrader/MapServer/4/query?where=1%3D1&text=&objectIds=&time=&geometry=@Value(_xmin),@Value(_ymin),@Value(_xmax),@Value(_ymax)&geometryType=esriGeometryEnvelope&inSR=&spatialRel=esriSpatialRelIntersects&relationParam=&outFields=&returnGeometry=true&maxAllowableOffset=&geometryPrecision=&outSR=&returnIdsOnly=false&returnCountOnly=false&orderByFields=&groupByFieldsForStatistics=&outStatistics=&returnZ=false&returnM=false&gdbVersion=&returnDistinctValues=false&returnTrueCurves=false&resultOffset=&resultRecordCount=&f=pjson
    -> FeatureReader_6 [off]
FeatureReader_6 [off]
    OUTPUT_FEATURES_DISPLAY = Only Data Features
    COMBINE_GEOM = Use Result
    ATTR_ACCUM_MODE = Only Use Result
    FEATURETYPES_RADIO = FEATURETYPES
    ESRIJSON_SIMPLIFY_MULTIS = Yes
    INTERACT = <No Spatial Filter>
    ESRIJSON_USE_SEARCH_ENVELOPE = NO
    DATASET = @Value(Query)
    FORMAT = ESRIJSON
    ESRIJSON_MAKE_DONUTS = No
    ESRIJSON_USE_BASENAME_AS_DEFAULT_FEATURE_TYPE = No
    ESRIJSON_MAKE_PATHS = No
    ESRIJSON_DELETE_DOWNLOAD_FILE = Yes
    ESRIJSON_CLIP_TO_ENVELOPE = NO
    <OTHER> -> Reprojector_9 [off]
Reprojector_9 [off]
    INTERPOLATION_TYPE_NAME = Nearest Neighbor
    DEST = EPSG:32633
    SOURCE = Read from feature
    RASTER_CELL_SIZE = Preserve Cells
    REPROJECTED -> Matcher_6 [off]
Matcher_6 [off]
    MATCH = 2D
    MATCH_STRATEGY = Match Selected Attributes
    CNT_ATTR = _match_id
    BLANK_AND_MISSING_DIFFER = No
    LENIENT_MATCH = No
    SINGLE_MATCHED -> Villreinomrader (writer SHAPE_1) [off]
    NOT_MATCHED -> Villreinomrader (writer SHAPE_1) [off]
Villreinomrader (writer SHAPE_1) [off]
    attributes: _match_id char(200)
Note: NB:32633
Creator_7 [off]
    COORDS = $(MINX) $(MINY) $(MAXX) $(MINY) $(MAXX) $(MAXY)  $(MINX) $(MAXY)  $(MINX) $(MINY)
    GEOMTYPE = 2D Coordinate List
    COORDSYS = EPSG:25833
    NUM = 1
    CREATED -> Reprojector_10 [off]
Note: Projiserer envelopen til 25833
Reprojector_10 [off]
    INTERPOLATION_TYPE_NAME = Nearest Neighbor
    DEST = EPSG:25833
    SOURCE = Read from feature
    RASTER_CELL_SIZE = Preserve Cells
    STROKE_ARCS = Yes
    REPROJECTED -> Tiler_7 [off]
Note: Tiler opp envelopen i mindre / områder
Tiler_7 [off]
    TILING_TYPE = Tile Size
    COL_ATTR = _column
    XINC = 100000
    ROW_ATTR = _row
    YINC = 100000
    TILED -> BoundsExtractor_7 [off]
BoundsExtractor_7 [off]
    ZMIN = _zmin
    ZMAX = _zmax
    XMIN = _xmin
    XMAX = _xmax
    YMIN = _ymin
    YMAX = _ymax
    -> AttributeCreator_7 [off]
AttributeCreator_7 [off]
    ATTR_LIST = Query,http://wms.miljodirektoratet.no/arcgis/rest/services/vern/MapServer/1/query?where=1%3D1&text=&objectIds=&time=&geometry=@Value(_xmin),@Value(_ymin),@Value(_xmax),@Value(_ymax)&geometryType=esriGeometryEnvelope&inSR=&spatialRel=esriSpatialRelIntersects&relationParam=&outFields=&returnGeometry=true&maxAllowableOffset=&geometryPrecision=&outSR=&returnIdsOnly=false&returnCountOnly=false&orderByFields=&groupByFieldsForStatistics=&outStatistics=&returnZ=false&returnM=false&gdbVersion=&returnDistinctValues=false&returnTrueCurves=false&resultOffset=&resultRecordCount=&f=pjson
    -> FeatureReader_7 [off]
FeatureReader_7 [off]
    OUTPUT_FEATURES_DISPLAY = Only Data Features
    COMBINE_GEOM = Use Result
    ATTR_ACCUM_MODE = Only Use Result
    FEATURETYPES_RADIO = FEATURETYPES
    ESRIJSON_SIMPLIFY_MULTIS = Yes
    INTERACT = <No Spatial Filter>
    ESRIJSON_USE_SEARCH_ENVELOPE = NO
    DATASET = @Value(Query)
    FORMAT = ESRIJSON
    ESRIJSON_MAKE_DONUTS = No
    ESRIJSON_USE_BASENAME_AS_DEFAULT_FEATURE_TYPE = No
    ESRIJSON_MAKE_PATHS = No
    ESRIJSON_DELETE_DOWNLOAD_FILE = Yes
    ESRIJSON_CLIP_TO_ENVELOPE = NO
    <OTHER> -> Reprojector_12 [off]
Reprojector_12 [off]
    INTERPOLATION_TYPE_NAME = Nearest Neighbor
    DEST = EPSG:32633
    SOURCE = Read from feature
    RASTER_CELL_SIZE = Preserve Cells
    REPROJECTED -> Matcher_7 [off]
Matcher_7 [off]
    MATCH = 2D
    MATCH_STRATEGY = Match Selected Attributes
    CNT_ATTR = _match_id
    BLANK_AND_MISSING_DIFFER = No
    LENIENT_MATCH = No
    SINGLE_MATCHED -> Naturnvernomr (writer SHAPE_1) [off]
    NOT_MATCHED -> Naturnvernomr (writer SHAPE_1) [off]
Naturnvernomr (writer SHAPE_1) [off]
    attributes: _match_id char(200)
Note: NB:32633
Creator_8 [off]
    COORDS = $(MINX) $(MINY) $(MAXX) $(MINY) $(MAXX) $(MAXY)  $(MINX) $(MAXY)  $(MINX) $(MINY)
    GEOMTYPE = 2D Coordinate List
    COORDSYS = EPSG:25833
    NUM = 1
    CREATED -> Reprojector_13 [off]
Note: Projiserer envelopen til 25833
Reprojector_13 [off]
    INTERPOLATION_TYPE_NAME = Nearest Neighbor
    DEST = EPSG:25833
    SOURCE = Read from feature
    RASTER_CELL_SIZE = Preserve Cells
    STROKE_ARCS = Yes
    REPROJECTED -> Tiler_8 [off]
Note: Tiler opp envelopen i mindre / områder
Tiler_8 [off]
    TILING_TYPE = Tile Size
    COL_ATTR = _column
    XINC = 100000
    ROW_ATTR = _row
    YINC = 100000
    TILED -> BoundsExtractor_8 [off]
BoundsExtractor_8 [off]
    ZMIN = _zmin
    ZMAX = _zmax
    XMIN = _xmin
    XMAX = _xmax
    YMIN = _ymin
    YMAX = _ymax
    -> AttributeCreator_8 [off]
AttributeCreator_8 [off]
    ATTR_LIST = Query,http://wms.miljodirektoratet.no/arcgis/rest/services/vern/MapServer/2/query?where=1%3D1&text=&objectIds=&time=&geometry=@Value(_xmin),@Value(_ymin),@Value(_xmax),@Value(_ymax)&geometryType=esriGeometryEnvelope&inSR=&spatialRel=esriSpatialRelIntersects&relationParam=&outFields=&returnGeometry=true&maxAllowableOffset=&geometryPrecision=&outSR=&returnIdsOnly=false&returnCountOnly=false&orderByFields=&groupByFieldsForStatistics=&outStatistics=&returnZ=false&returnM=false&gdbVersion=&returnDistinctValues=false&returnTrueCurves=false&resultOffset=&resultRecordCount=&f=pjson
    -> FeatureReader_8 [off]
FeatureReader_8 [off]
    OUTPUT_FEATURES_DISPLAY = Only Data Features
    COMBINE_GEOM = Use Result
    ATTR_ACCUM_MODE = Only Use Result
    FEATURETYPES_RADIO = FEATURETYPES
    ESRIJSON_SIMPLIFY_MULTIS = Yes
    INTERACT = <No Spatial Filter>
    ESRIJSON_USE_SEARCH_ENVELOPE = NO
    DATASET = @Value(Query)
    FORMAT = ESRIJSON
    ESRIJSON_MAKE_DONUTS = No
    ESRIJSON_USE_BASENAME_AS_DEFAULT_FEATURE_TYPE = No
    ESRIJSON_MAKE_PATHS = No
    ESRIJSON_DELETE_DOWNLOAD_FILE = Yes
    ESRIJSON_CLIP_TO_ENVELOPE = NO
    <OTHER> -> Reprojector_14 [off]
Reprojector_14 [off]
    INTERPOLATION_TYPE_NAME = Nearest Neighbor
    DEST = EPSG:32633
    SOURCE = Read from feature
    RASTER_CELL_SIZE = Preserve Cells
    REPROJECTED -> Matcher_8 [off]
Matcher_8 [off]
    MATCH = 2D
    MATCH_STRATEGY = Match Selected Attributes
    CNT_ATTR = _match_id
    BLANK_AND_MISSING_DIFFER = No
    LENIENT_MATCH = No
    SINGLE_MATCHED -> Naturnvernomr_foreslaatt (writer SHAPE_1) [off]
    NOT_MATCHED -> Naturnvernomr_foreslaatt (writer SHAPE_1) [off]
Naturnvernomr_foreslaatt (writer SHAPE_1) [off]
    attributes: _match_id char(200)
Creator_10 [off]
    COORDS = $(MINX) $(MINY) $(MAXX) $(MINY) $(MAXX) $(MAXY)  $(MINX) $(MAXY)  $(MINX) $(MINY)
    GEOMTYPE = 2D Coordinate List
    COORDSYS = EPSG:25833
    NUM = 1
    CREATED -> Reprojector_17 [off]
Note: Projiserer envelopen til 25833
Reprojector_17 [off]
    INTERPOLATION_TYPE_NAME = Nearest Neighbor
    DEST = EPSG:25833
    SOURCE = Read from feature
    RASTER_CELL_SIZE = Preserve Cells
    STROKE_ARCS = Yes
    REPROJECTED -> Tiler_11 [off]
Note: Tiler opp envelopen i mindre / områder
Tiler_11 [off]
    TILING_TYPE = Tile Size
    COL_ATTR = _column
    XINC = 100000
    ROW_ATTR = _row
    YINC = 100000
    TILED -> BoundsExtractor_11 [off]
BoundsExtractor_11 [off]
    ZMIN = _zmin
    ZMAX = _zmax
    XMIN = _xmin
    XMAX = _xmax
    YMIN = _ymin
    YMAX = _ymax
    -> AttributeCreator_11 [off]
AttributeCreator_11 [off]
    ATTR_LIST = Query,http://wms.miljodirektoratet.no/arcgis/rest/services/NiN/MapServer/4/query?where=1%3D1&text=&objectIds=&time=&geometry=@Value(_xmin),@Value(_ymin),@Value(_xmax),@Value(_ymax)&geometryType=esriGeometryEnvelope&inSR=&spatialRel=esriSpatialRelIntersects&relationParam=&outFields=&returnGeometry=true&maxAllowableOffset=&geometryPrecision=&outSR=&returnIdsOnly=false&returnCountOnly=false&orderByFields=&groupByFieldsForStatistics=&outStatistics=&returnZ=false&returnM=false&gdbVersion=&returnDistinctValues=false&returnTrueCurves=false&resultOffset=&resultRecordCount=&f=pjson
    -> FeatureReader_11 [off]
FeatureReader_11 [off]
    OUTPUT_FEATURES_DISPLAY = Only Data Features
    COMBINE_GEOM = Use Result
    ATTR_ACCUM_MODE = Only Use Result
    FEATURETYPES_RADIO = FEATURETYPES
    ESRIJSON_SIMPLIFY_MULTIS = Yes
    INTERACT = <No Spatial Filter>
    ESRIJSON_USE_SEARCH_ENVELOPE = NO
    DATASET = @Value(Query)
    FORMAT = ESRIJSON
    ESRIJSON_MAKE_DONUTS = No
    ESRIJSON_USE_BASENAME_AS_DEFAULT_FEATURE_TYPE = No
    ESRIJSON_MAKE_PATHS = No
    ESRIJSON_DELETE_DOWNLOAD_FILE = Yes
    ESRIJSON_CLIP_TO_ENVELOPE = NO
    <OTHER> -> Reprojector_18 [off]
Reprojector_18 [off]
    INTERPOLATION_TYPE_NAME = Nearest Neighbor
    DEST = EPSG:32633
    SOURCE = Read from feature
    RASTER_CELL_SIZE = Preserve Cells
    REPROJECTED -> Matcher_12 [off]
Matcher_12 [off]
    MATCH = 2D
    MATCH_STRATEGY = Match Selected Attributes
    CNT_ATTR = _match_id
    BLANK_AND_MISSING_DIFFER = No
    LENIENT_MATCH = No
    SINGLE_MATCHED -> naturt_i_norge_landskap (writer SHAPE_1) [off]
    NOT_MATCHED -> naturt_i_norge_landskap (writer SHAPE_1) [off]
naturt_i_norge_landskap (writer SHAPE_1) [off]
    attributes: _match_id char(200)
Creator_9 [off]
    COORDS = $(MINX) $(MINY) $(MAXX) $(MINY) $(MAXX) $(MAXY)  $(MINX) $(MAXY)  $(MINX) $(MINY)
    GEOMTYPE = 2D Coordinate List
    COORDSYS = EPSG:25833
    NUM = 1
    CREATED -> Reprojector_15 [off]
Note: Projiserer envelopen til 25833
Reprojector_15 [off]
    INTERPOLATION_TYPE_NAME = Nearest Neighbor
    DEST = EPSG:25833
    SOURCE = Read from feature
    RASTER_CELL_SIZE = Preserve Cells
    STROKE_ARCS = Yes
    REPROJECTED -> Tiler_9 [off]
Note: Tiler opp envelopen i mindre / områder
Tiler_9 [off]
    TILING_TYPE = Tile Size
    COL_ATTR = _column
    XINC = 100000
    ROW_ATTR = _row
    YINC = 100000
    TILED -> BoundsExtractor_9 [off]
BoundsExtractor_9 [off]
    ZMIN = _zmin
    ZMAX = _zmax
    XMIN = _xmin
    XMAX = _xmax
    YMIN = _ymin
    YMAX = _ymax
    -> AttributeCreator_9 [off]
AttributeCreator_9 [off]
    ATTR_LIST = Query,http://wms.miljodirektoratet.no/arcgis/rest/services/artnasjonal/MapServer/3/query?where=1%3D1&text=&objectIds=&time=&geometry=@Value(_xmin),@Value(_ymin),@Value(_xmax),@Value(_ymax)&geometryType=esriGeometryEnvelope&inSR=&spatialRel=esriSpatialRelIntersects&relationParam=&outFields=&returnGeometry=true&maxAllowableOffset=&geometryPrecision=&outSR=&returnIdsOnly=false&returnCountOnly=false&orderByFields=&groupByFieldsForStatistics=&outStatistics=&returnZ=false&returnM=false&gdbVersion=&returnDistinctValues=false&returnTrueCurves=false&resultOffset=&resultRecordCount=&f=pjson
    -> FeatureReader_9 [off]
FeatureReader_9 [off]
    OUTPUT_FEATURES_DISPLAY = Only Data Features
    COMBINE_GEOM = Use Result
    ATTR_ACCUM_MODE = Only Use Result
    FEATURETYPES_RADIO = FEATURETYPES
    ESRIJSON_SIMPLIFY_MULTIS = Yes
    INTERACT = <No Spatial Filter>
    ESRIJSON_USE_SEARCH_ENVELOPE = NO
    DATASET = @Value(Query)
    FORMAT = ESRIJSON
    ESRIJSON_MAKE_DONUTS = No
    ESRIJSON_USE_BASENAME_AS_DEFAULT_FEATURE_TYPE = No
    ESRIJSON_MAKE_PATHS = No
    ESRIJSON_DELETE_DOWNLOAD_FILE = Yes
    ESRIJSON_CLIP_TO_ENVELOPE = NO
    <OTHER> -> Reprojector_16 [off]
Reprojector_16 [off]
    INTERPOLATION_TYPE_NAME = Nearest Neighbor
    DEST = EPSG:32633
    SOURCE = Read from feature
    RASTER_CELL_SIZE = Preserve Cells
    REPROJECTED -> Matcher_9 [off]
Matcher_9 [off]
    MATCH = 2D
    MATCH_STRATEGY = Match Selected Attributes
    CNT_ATTR = _match_id
    BLANK_AND_MISSING_DIFFER = No
    LENIENT_MATCH = No
    SINGLE_MATCHED -> arter_nasj_for_int (writer SHAPE_1) [off]
    NOT_MATCHED -> arter_nasj_for_int (writer SHAPE_1) [off]
arter_nasj_for_int (writer SHAPE_1) [off]
    attributes: _match_id char(200)
Creator_12 [off]
    COORDS = $(MINX) $(MINY) $(MAXX) $(MINY) $(MAXX) $(MAXY)  $(MINX) $(MAXY)  $(MINX) $(MINY)
    GEOMTYPE = 2D Coordinate List
    COORDSYS = EPSG:25833
    NUM = 1
    CREATED -> Reprojector_19 [off]
Note: Projiserer envelopen til 25833
Reprojector_19 [off]
    INTERPOLATION_TYPE_NAME = Nearest Neighbor
    DEST = EPSG:25833
    SOURCE = Read from feature
    RASTER_CELL_SIZE = Preserve Cells
    STROKE_ARCS = Yes
    REPROJECTED -> Tiler_12 [off]
Note: Tiler opp envelopen i mindre / områder
Tiler_12 [off]
    TILING_TYPE = Tile Size
    COL_ATTR = _column
    XINC = 100000
    ROW_ATTR = _row
    YINC = 100000
    TILED -> BoundsExtractor_12 [off]
BoundsExtractor_12 [off]
    ZMIN = _zmin
    ZMAX = _zmax
    XMIN = _xmin
    XMAX = _xmax
    YMIN = _ymin
    YMAX = _ymax
    -> AttributeCreator_12 [off]
AttributeCreator_12 [off]
    ATTR_LIST = Query,http://wms.miljodirektoratet.no/arcgis/rest/services/naturtyper_dn/MapServer/0/query?where=1%3D1&text=&objectIds=&time=&geometry=@Value(_xmin),@Value(_ymin),@Value(_xmax),@Value(_ymax)&geometryType=esriGeometryEnvelope&inSR=&spatialRel=esriSpatialRelIntersects&relationParam=&outFields=&returnGeometry=true&maxAllowableOffset=&geometryPrecision=&outSR=&returnIdsOnly=false&returnCountOnly=false&orderByFields=&groupByFieldsForStatistics=&outStatistics=&returnZ=false&returnM=false&gdbVersion=&returnDistinctValues=false&returnTrueCurves=false&resultOffset=&resultRecordCount=&f=pjson
    -> FeatureReader_12 [off]
FeatureReader_12 [off]
    OUTPUT_FEATURES_DISPLAY = Only Data Features
    COMBINE_GEOM = Use Result
    ATTR_ACCUM_MODE = Only Use Result
    FEATURETYPES_RADIO = FEATURETYPES
    ESRIJSON_SIMPLIFY_MULTIS = Yes
    INTERACT = <No Spatial Filter>
    ESRIJSON_USE_SEARCH_ENVELOPE = NO
    DATASET = @Value(Query)
    FORMAT = ESRIJSON
    ESRIJSON_MAKE_DONUTS = No
    ESRIJSON_USE_BASENAME_AS_DEFAULT_FEATURE_TYPE = No
    ESRIJSON_MAKE_PATHS = No
    ESRIJSON_DELETE_DOWNLOAD_FILE = Yes
    ESRIJSON_CLIP_TO_ENVELOPE = NO
    <OTHER> -> Reprojector_20 [off]
Reprojector_20 [off]
    INTERPOLATION_TYPE_NAME = Nearest Neighbor
    DEST = EPSG:32633
    SOURCE = Read from feature
    RASTER_CELL_SIZE = Preserve Cells
    REPROJECTED -> Matcher_11 [off]
Matcher_11 [off]
    MATCH = 2D
    MATCH_STRATEGY = Match Selected Attributes
    CNT_ATTR = _match_id
    BLANK_AND_MISSING_DIFFER = No
    LENIENT_MATCH = No
    SINGLE_MATCHED -> naturt_utvalgte (writer SHAPE_1) [off]
    NOT_MATCHED -> naturt_utvalgte (writer SHAPE_1) [off]
naturt_utvalgte (writer SHAPE_1) [off]
    attributes: _match_id char(200)
