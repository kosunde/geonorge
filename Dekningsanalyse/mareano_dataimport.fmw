FME workspace mareano_dataimport.fmw

Parameters:
- SourceDataset_POSTGIS = sjomaling_prd   # Database
- DestDataset_SHAPE = C:\Users\xmaland\Desktop\Mareano   # Destination Esri Shape Folder

Readers:
- POSTGIS_1: POSTGIS from $(SourceDataset_POSTGIS)

Writers:
- SHAPE_1: SHAPE to $(DestDataset_SHAPE)

data.flerstrale (reader POSTGIS_1)
    attributes: ogc_fid int4, id float8, versjonsnu float8, max_hor_st float8, oppdrag_id char(40), posisjoner char(40), ekkolodd char(40), sjoemaalin char(40), farvannsty char(40), innsamling char(40), digitalise char(40), godkjennin char(40)
    -> data.flerstrale (writer SHAPE_1)
data.flerstrale (writer SHAPE_1)
    attributes: ogc_fid number(11,0), id number(31,15), versjonsnu number(31,15), max_hor_st number(31,15), oppdrag_id char(40), posisjoner char(40), ekkolodd char(40), sjoemaalin char(40), farvannsty char(40), innsamling char(40), digitalise char(40), godkjennin char(40)
data.hybas_geo_grense_maaleoppdrag (reader POSTGIS_1)
    attributes: ogc_fid serial,BTREE, id float8, versjonsnu float8, max_hor_st float8, oppdrag_id char(40), posisjoner char(40), ekkolodd char(40), sjoemaalin char(40), farvannsty char(40), innsamling char(40), digitalise char(40), godkjennin char(40), s44_standa char(11), areal float8, startdato date, sluttdato date, modelldato date, xyzdato date, tilfartoyd date, tilprosdat date
    -> data.hybas_geo_grense_maaleoppdrag (writer SHAPE_1)
data.hybas_geo_grense_maaleoppdrag (writer SHAPE_1)
    attributes: ogc_fid number(11,0), id number(31,15), versjonsnu number(31,15), max_hor_st number(31,15), oppdrag_id char(40), posisjoner char(40), ekkolodd char(40), sjoemaalin char(40), farvannsty char(40), innsamling char(40), digitalise char(40), godkjennin char(40), s44_standa char(11), areal number(31,15), startdato date, sluttdato date, modelldato date, xyzdato date, tilfartoyd date, tilprosdat date
data.celleavgrensing_project (reader POSTGIS_1)
    attributes: ogc_fid serial,PRIKEY, oid_ numeric(10,0), cellenavn char(20), celletitte char(50), sw_n numeric(24,5), sw_e numeric(24,5), ne_n numeric(24,5), ne_e numeric(24,5), sort_verdi char(4), ltt_featur numeric(10,0), ltt_status char(2), ltt_curren numeric(10,0), ltt_versio numeric(10,0), ltt_commit numeric(10,0), ltt_retire numeric(10,0), ltt_unique numeric(10,0), tidev_korr numeric(24,5), tidev_komm char(80), godkjent numeric(10,0)
    -> data.celleavgrensing_project (writer SHAPE_1)
data.celleavgrensing_project (writer SHAPE_1)
    attributes: ogc_fid number(11,0), oid_ number(10,0), cellenavn char(20), celletitte char(50), sw_n number(24,5), sw_e number(24,5), ne_n number(24,5), ne_e number(24,5), sort_verdi char(4), ltt_featur number(10,0), ltt_status char(2), ltt_curren number(10,0), ltt_versio number(10,0), ltt_commit number(10,0), ltt_retire number(10,0), ltt_unique number(10,0), tidev_korr number(24,5), tidev_komm char(80), godkjent number(10,0)
data.mareano_planlagt_sjomaaling (reader POSTGIS_1)
    attributes: ogc_fid serial,BTREE, id1 numeric(10,0), navn char(50), År char(50)
    -> data.mareano_planlagt_sjomaaling (writer SHAPE_1)
data.mareano_planlagt_sjomaaling (writer SHAPE_1)
    attributes: ogc_fid number(11,0), id1 number(10,0), navn char(50), År char(50)
data.mareano_ferdig_sjomaalt (reader POSTGIS_1)
    attributes: ogc_fid serial,BTREE, id numeric(10,0), info char(50)
    -> data.mareano_ferdig_sjomaalt (writer SHAPE_1)
data.mareano_ferdig_sjomaalt (writer SHAPE_1)
    attributes: ogc_fid number(11,0), id number(10,0), info char(50)
data.enkelstrale (reader POSTGIS_1)
    attributes: ogc_fid int4, id float8, versjonsnu float8, max_hor_st float8, oppdrag_id char(40), posisjoner char(40), ekkolodd char(40), sjoemaalin char(40), farvannsty char(40), innsamling char(40), digitalise char(40), godkjennin char(40)
    -> data.enkelstrale (writer SHAPE_1)
data.enkelstrale (writer SHAPE_1)
    attributes: ogc_fid number(11,0), id number(31,15), versjonsnu number(31,15), max_hor_st number(31,15), oppdrag_id char(40), posisjoner char(40), ekkolodd char(40), sjoemaalin char(40), farvannsty char(40), innsamling char(40), digitalise char(40), godkjennin char(40)
