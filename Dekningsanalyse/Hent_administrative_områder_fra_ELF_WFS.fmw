FME workspace Hent_administrative_områder_fra_ELF_WFS.fmw

Parameters:
- SourceDataset_WFS = http://wfs.geonorge.no/skwms1/wfs.elf-au   # Source WFS (Web Feature Service) URL
- DestDataset_POSTGIS = geonortst@Nnridb504:5432/geonor01tst   # Connection

Readers:
- WFS_1: WFS from $(SourceDataset_WFS)

Writers:
- POSTGIS_1: POSTGIS to $(DestDataset_POSTGIS)

AdministrativeUnit (reader WFS_1)
    attributes: gml_parent_id xml_buffer, gml_parent_property xml_buffer, gml_id xml_buffer, geometry xml_geometry, nationalCode xml_buffer, inspireId.Identifier.localId xml_buffer, inspireId.Identifier.namespace xml_buffer, inspireId.Identifier.versionId xml_buffer, inspireId.Identifier.versionId.nilReason xml_buffer, inspireId.Identifier.versionId.xsi_nil xml_boolean, nationalLevel xml_buffer, nationalLevel.codeSpace xml_buffer, nationalLevelName{}.gco_nilReason xml_buffer, nationalLevelName{}.uuidref xml_buffer, nationalLevelName{}.xlink_href xml_buffer, nationalLevelName{}.xsi_nil xml_boolean, nationalLevelName{}.LocalisedCharacterString xml_buffer, nationalLevelName{}.LocalisedCharacterString.id xml_buffer, nationalLevelName{}.LocalisedCharacterString.locale xml_buffer, country.nilReason xml_buffer, country.Country xml_buffer, country.Country.codeList xml_buffer, country.Country.codeListValue xml_buffer, country.Country.codeSpace xml_buffer, name{}.GeographicalName.language xml_buffer, name{}.GeographicalName.language.nilReason xml_buffer, name{}.GeographicalName.language.xsi_nil xml_boolean, name{}.GeographicalName.nativeness xml_buffer, name{}.GeographicalName.nativeness.nilReason xml_buffer, name{}.GeographicalName.nativeness.codeSpace xml_buffer,
      name{}.GeographicalName.nativeness.xsi_nil xml_boolean, name{}.GeographicalName.nameStatus xml_buffer, name{}.GeographicalName.nameStatus.nilReason xml_buffer, name{}.GeographicalName.nameStatus.codeSpace xml_buffer, name{}.GeographicalName.nameStatus.xsi_nil xml_boolean, name{}.GeographicalName.sourceOfName xml_buffer, name{}.GeographicalName.sourceOfName.nilReason xml_buffer, name{}.GeographicalName.sourceOfName.xsi_nil xml_boolean, name{}.GeographicalName.pronunciation.nilReason xml_buffer, name{}.GeographicalName.pronunciation.xsi_nil xml_boolean, name{}.GeographicalName.pronunciation.PronunciationOfName.pronunciationSoundLink xml_buffer, name{}.GeographicalName.pronunciation.PronunciationOfName.pronunciationSoundLink.nilReason xml_buffer, name{}.GeographicalName.pronunciation.PronunciationOfName.pronunciationSoundLink.xsi_nil xml_boolean, name{}.GeographicalName.pronunciation.PronunciationOfName.pronunciationIPA xml_buffer, name{}.GeographicalName.pronunciation.PronunciationOfName.pronunciationIPA.nilReason xml_buffer, name{}.GeographicalName.pronunciation.PronunciationOfName.pronunciationIPA.xsi_nil xml_boolean, name{}.GeographicalName.spelling{}.SpellingOfName.text xml_buffer, name{}.GeographicalName.spelling{}.SpellingOfName.script xml_buffer, name{}.GeographicalName.spelling{}.SpellingOfName.script.nilReason xml_buffer, name{}.GeographicalName.spelling{}.SpellingOfName.script.xsi_nil xml_boolean, name{}.GeographicalName.spelling{}.SpellingOfName.transliterationScheme xml_buffer, name{}.GeographicalName.spelling{}.SpellingOfName.transliterationScheme.nilReason xml_buffer, name{}.GeographicalName.spelling{}.SpellingOfName.transliterationScheme.xsi_nil xml_boolean, name{}.GeographicalName.grammaticalGender xml_buffer, name{}.GeographicalName.grammaticalGender.nilReason xml_buffer, name{}.GeographicalName.grammaticalGender.codeSpace xml_buffer, name{}.GeographicalName.grammaticalGender.xsi_nil xml_boolean, name{}.GeographicalName.grammaticalNumber xml_buffer, name{}.GeographicalName.grammaticalNumber.nilReason xml_buffer, name{}.GeographicalName.grammaticalNumber.codeSpace xml_buffer,
      name{}.GeographicalName.grammaticalNumber.xsi_nil xml_boolean, name{}.GeographicalName.referenceName xml_boolean, residenceOfAuthority{}.nilReason xml_buffer, residenceOfAuthority{}.xsi_nil xml_boolean, residenceOfAuthority{}.ResidenceOfAuthority.name.GeographicalName.language xml_buffer, residenceOfAuthority{}.ResidenceOfAuthority.name.GeographicalName.language.nilReason xml_buffer, residenceOfAuthority{}.ResidenceOfAuthority.name.GeographicalName.language.xsi_nil xml_boolean, residenceOfAuthority{}.ResidenceOfAuthority.name.GeographicalName.nativeness xml_buffer, residenceOfAuthority{}.ResidenceOfAuthority.name.GeographicalName.nativeness.nilReason xml_buffer, residenceOfAuthority{}.ResidenceOfAuthority.name.GeographicalName.nativeness.codeSpace xml_buffer, residenceOfAuthority{}.ResidenceOfAuthority.name.GeographicalName.nativeness.xsi_nil xml_boolean, residenceOfAuthority{}.ResidenceOfAuthority.name.GeographicalName.nameStatus xml_buffer, residenceOfAuthority{}.ResidenceOfAuthority.name.GeographicalName.nameStatus.nilReason xml_buffer, residenceOfAuthority{}.ResidenceOfAuthority.name.GeographicalName.nameStatus.codeSpace xml_buffer, residenceOfAuthority{}.ResidenceOfAuthority.name.GeographicalName.nameStatus.xsi_nil xml_boolean, residenceOfAuthority{}.ResidenceOfAuthority.name.GeographicalName.sourceOfName xml_buffer, residenceOfAuthority{}.ResidenceOfAuthority.name.GeographicalName.sourceOfName.nilReason xml_buffer, residenceOfAuthority{}.ResidenceOfAuthority.name.GeographicalName.sourceOfName.xsi_nil xml_boolean, residenceOfAuthority{}.ResidenceOfAuthority.name.GeographicalName.pronunciation.nilReason xml_buffer, residenceOfAuthority{}.ResidenceOfAuthority.name.GeographicalName.pronunciation.xsi_nil xml_boolean, residenceOfAuthority{}.ResidenceOfAuthority.name.GeographicalName.pronunciation.PronunciationOfName.pronunciationSoundLink xml_buffer, residenceOfAuthority{}.ResidenceOfAuthority.name.GeographicalName.pronunciation.PronunciationOfName.pronunciationSoundLink.nilReason xml_buffer, residenceOfAuthority{}.ResidenceOfAuthority.name.GeographicalName.pronunciation.PronunciationOfName.pronunciationSoundLink.xsi_nil xml_boolean, residenceOfAuthority{}.ResidenceOfAuthority.name.GeographicalName.pronunciation.PronunciationOfName.pronunciationIPA xml_buffer, residenceOfAuthority{}.ResidenceOfAuthority.name.GeographicalName.pronunciation.PronunciationOfName.pronunciationIPA.nilReason xml_buffer, residenceOfAuthority{}.ResidenceOfAuthority.name.GeographicalName.pronunciation.PronunciationOfName.pronunciationIPA.xsi_nil xml_boolean, residenceOfAuthority{}.ResidenceOfAuthority.name.GeographicalName.spelling{}.SpellingOfName.text xml_buffer, residenceOfAuthority{}.ResidenceOfAuthority.name.GeographicalName.spelling{}.SpellingOfName.script xml_buffer, residenceOfAuthority{}.ResidenceOfAuthority.name.GeographicalName.spelling{}.SpellingOfName.script.nilReason xml_buffer, residenceOfAuthority{}.ResidenceOfAuthority.name.GeographicalName.spelling{}.SpellingOfName.script.xsi_nil xml_boolean,
      residenceOfAuthority{}.ResidenceOfAuthority.name.GeographicalName.spelling{}.SpellingOfName.transliterationScheme xml_buffer, residenceOfAuthority{}.ResidenceOfAuthority.name.GeographicalName.spelling{}.SpellingOfName.transliterationScheme.nilReason xml_buffer, residenceOfAuthority{}.ResidenceOfAuthority.name.GeographicalName.spelling{}.SpellingOfName.transliterationScheme.xsi_nil xml_boolean, residenceOfAuthority{}.ResidenceOfAuthority.name.GeographicalName.grammaticalGender xml_buffer, residenceOfAuthority{}.ResidenceOfAuthority.name.GeographicalName.grammaticalGender.nilReason xml_buffer, residenceOfAuthority{}.ResidenceOfAuthority.name.GeographicalName.grammaticalGender.codeSpace xml_buffer, residenceOfAuthority{}.ResidenceOfAuthority.name.GeographicalName.grammaticalGender.xsi_nil xml_boolean, residenceOfAuthority{}.ResidenceOfAuthority.name.GeographicalName.grammaticalNumber xml_buffer, residenceOfAuthority{}.ResidenceOfAuthority.name.GeographicalName.grammaticalNumber.nilReason xml_buffer, residenceOfAuthority{}.ResidenceOfAuthority.name.GeographicalName.grammaticalNumber.codeSpace xml_buffer, residenceOfAuthority{}.ResidenceOfAuthority.name.GeographicalName.grammaticalNumber.xsi_nil xml_boolean, residenceOfAuthority{}.ResidenceOfAuthority.name.GeographicalName.referenceName xml_boolean, residenceOfAuthority{}.ResidenceOfAuthority.geometry xml_geometry, beginLifespanVersion xml_datetime, beginLifespanVersion.nilReason xml_buffer, beginLifespanVersion.xsi_nil xml_boolean, endLifespanVersion xml_datetime, endLifespanVersion.nilReason xml_buffer, endLifespanVersion.xsi_nil xml_boolean, NUTS{}.owns xml_boolean, NUTS{}.nilReason xml_buffer, NUTS{}.gml_remoteSchema xml_buffer, NUTS{}.xlink_href xml_buffer, NUTS{}.xsi_nil xml_boolean, condominium{}.owns xml_boolean, condominium{}.nilReason xml_buffer, condominium{}.gml_remoteSchema xml_buffer, condominium{}.xlink_href xml_buffer, condominium{}.xsi_nil xml_boolean, lowerLevelUnit{}.nilReason xml_buffer,
      lowerLevelUnit{}.gml_remoteSchema xml_buffer, lowerLevelUnit{}.xlink_href xml_buffer, lowerLevelUnit{}.owns xml_boolean, lowerLevelUnit{}.xsi_nil xml_boolean, upperLevelUnit.owns xml_boolean, upperLevelUnit.nilReason xml_buffer, upperLevelUnit.gml_remoteSchema xml_buffer, upperLevelUnit.xlink_href xml_buffer, upperLevelUnit.xsi_nil xml_boolean, administeredBy{}.owns xml_boolean, administeredBy{}.nilReason xml_buffer, administeredBy{}.gml_remoteSchema xml_buffer, administeredBy{}.xlink_href xml_buffer, administeredBy{}.xsi_nil xml_boolean, coAdminister{}.owns xml_boolean, coAdminister{}.nilReason xml_buffer, coAdminister{}.gml_remoteSchema xml_buffer, coAdminister{}.xlink_href xml_buffer, coAdminister{}.xsi_nil xml_boolean, boundary{}.owns xml_boolean, boundary{}.nilReason xml_buffer, boundary{}.gml_remoteSchema xml_buffer, boundary{}.xlink_href xml_buffer, boundary{}.xsi_nil xml_boolean, SHNCode.ThematicIdentifier.identifier xml_buffer, SHNCode.ThematicIdentifier.identifierScheme xml_buffer, validFrom xml_datetime, validFrom.nilReason xml_buffer, validFrom.xsi_nil xml_boolean, adminUnitArea{}.nilReason xml_buffer,
      adminUnitArea{}.gml_remoteSchema xml_buffer, adminUnitArea{}.xlink_href xml_buffer, adminUnitArea{}.owns xml_boolean, namedPlacePoint{}.nilReason xml_buffer, namedPlacePoint{}.gml_remoteSchema xml_buffer, namedPlacePoint{}.xlink_href xml_buffer, namedPlacePoint{}.owns xml_boolean
    -> AttributeFilter
AttributeFilter
    ATTR_NAME = nationalLevel
    ATTR_VALUES = <EMPTY>,<MISSING>,<NULL>,<UNFILTERED>,3rdOrder,1stOrder,2ndOrder
    2ndOrder -> AreaCalculator
    3rdOrder -> AreaCalculator_2
    1stOrder -> CoordinateSystemExtractor
CoordinateSystemExtractor
    CRDSYS_ATTR = _coordsys
    -> CoordinateSystemExtractor_Output
CoordinateSystemExtractor_Output: Inspector

Bookmark: Kommuner
AreaCalculator_2
    AREA_ATTR = _area
    AREA_TYPE = Plane Area
    MULT = 1
    -> Sorter_2
Sorter_2
    SORT_PARM = _area NUMERIC DESCENDING
    SORTED -> DuplicateRemover_2
DuplicateRemover_2
    KEYATTR = nationalCode
    UNIQUE -> AdminGrense.KommuneFlate (writer POSTGIS_1)
AdminGrense.KommuneFlate (writer POSTGIS_1)
    attributes: kommuneid int4

Bookmark: Fylker
AreaCalculator
    AREA_ATTR = _area
    AREA_TYPE = Plane Area
    MULT = 1
    -> Sorter
Sorter
    SORT_PARM = _area NUMERIC DESCENDING
    SORTED -> DuplicateRemover
DuplicateRemover
    KEYATTR = nationalCode
    UNIQUE -> AdminGrense.FylkesFlate (writer POSTGIS_1)
AdminGrense.FylkesFlate (writer POSTGIS_1)
    attributes: fylkeid int4
