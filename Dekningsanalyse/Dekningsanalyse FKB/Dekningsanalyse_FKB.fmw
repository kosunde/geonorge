FME workspace Dekningsanalyse_FKB.fmw

Parameters:
- FKB_datasett = PblTiltak   # Datasett som skal analyseres
- SourceDataset_POSTGRES = geonor01tst   # Database
- DestDataset_POSTGRES = geonor01tst   # Database

Readers:
- POSTGRES_1: POSTGRES from $(SourceDataset_POSTGRES)

Writers:
- POSTGRES_2: POSTGRES to $(DestDataset_POSTGRES)

Note: Leser kommunetabell (uten geometri)
admingrense.kommuner (reader POSTGRES_1)
    attributes: kommuneid int2,PRIKEY, navn varchar(80)
    -> AttributeCreator
AttributeCreator
    ATTR_LIST = datasett,$(FKB_datasett)
    -> Tester
Note: Henter ut transSize-attributten
XMLFlattener
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    NEW_ATTRIBUTES = transSize
    ATTRIBUTE_XML = _response_body
    XML_SOURCE_TYPE = Attribute with XML document
    EMBEDDED_EXPRESSIONS = *
    -> AttributeFilter
Note: Oppdaterer postgres
dekningsoversikt.dekningsoversikt (writer POSTGRES_2)
    attributes: kommuneid int4,PRIKEY, akvakultur bool, korallrev bool, dsb_110sentral bool, dsb_brannstasjon bool, dsb_distrkont_siv bool, dsb_sivforsvdistr bool, ra_brannsmitteomr bool, ra_tettetrehusm bool, ra_frededebygg bool, ra_enkeltminner bool, ra_kulturmiljo bool, ra_lokaliteter bool, ra_sikringssoner bool, kv_hovedbiled bool, kv_ispshavneanlegg bool, kv_losbordingsfelt bool, kv_losstasjoner bool, nve_flomsoner10 bool, nve_flomsoner20 bool, nve_flomsoner50 bool, nve_flomsoner100 bool, nve_flomsoner200 bool, nve_flomsoner500 bool, nve_flomsoner1000 bool, nve_flomsoner200_i_aar2100 bool, nve_flomsonekartplan bool, nve_elvis_hovedelv bool, nve_elvis_elvenett bool, nve_innsjodata bool,
      nve_dybdekart bool, nve_nedborfelt_regine bool, nve_vassdragsomrade bool, nve_totnedbfelt_mstasjon bool, nve_vannkraftverk bool, nve_vindparkomrader bool, nve_vindturbin bool, nve_kraftlinjer bool, nve_sjokabler bool, nve_transformatorstasjoner bool, nve_omradekonsesjoner bool, nve_sikringstiltak bool, nve_verneplan_vassdrag bool, nve_kvikkleire bool, nve_aktsomhet_snoskred bool, nve_aktsomhet_steinsprang bool, nve_aktsomhet_snosteinsprang bool, nve_aktsomhet_jordflomskred bool, nve_skredhendelser bool, nve_kraftverk_alle_kst bool, nve_magasin bool, nve_dam bool, nve_vanninntak bool, nve_vannvei bool, nve_delfelt_vannkraft bool, nve_vindkraftverk bool, nve_skredsoner bool, dsb_anleggfarligstoff bool, dsb_storulykkeanlegg bool, dsb_eksplosivanlegg bool,
      nibio_jordkvalitet bool, md_forurensetgrunn bool, md_frilstatligsikra bool, md_frilkartlverds bool, md_verdif_kulturlandsk bool, md_viktige_naturt bool, md_villreinomr bool, md_naturvernomr bool, md_naturvernomr_foresl bool, md_arter_nasjon_forv bool, md_naturt_landskap bool, md_naturt_utv bool, fkb_ar5 bool, fkb_adresse bool, fkb_arealbruk bool, fkb_bane bool, fkb_bygnanlegg bool, fkb_bygning bool, fkb_bygningspunkt bool, fkb_hoydekurve-5m bool, fkb_hoydekurve bool, fkb_ledning bool, fkb_ledningva bool, fkb_lufthavn bool, fkb_matrikkelkartdekteig bool, fkb_naturinfo bool, fkb_pbltiltak bool, fkb_servitutt bool, fkb_tekst1000 bool, fkb_tekst5000 bool,
      fkb_traktorvegsti bool, fkb_vann bool, fkb_vbase bool, fkb_veg bool

Bookmark: KommuneID ledende 0
Tester
    TEST_CLAUSE = TEST @Value(kommuneid) < 1000
    TEST_DESCRIPTION = ""
    BOOL_OP = OR
    TEST_MODE = Automatic
    PASSED -> AttributeCreator_2
    FAILED -> TestFilter
AttributeCreator_2
    ATTR_LIST = kommuneid,0@Value(kommuneid)
    -> TestFilter

Bookmark: Finner lokale UTM-soner
TestFilter
    TEST_LIST = BOOL_OP,OR,COMPOSITE_TEST,<Unused>,TEST_CLAUSE,"TEST @Value(kommuneid) < 1800",Sone32,BOOL_OP,OR,COMPOSITE_TEST,<Unused>,TEST_CLAUSE,"TEST @Value(kommuneid) < 2000",Sone33
    DEFAULT_VALUE = Sone35
    Sone32 -> HTTPCaller
    Sone33 -> HTTPCaller_2
    Sone35 -> HTTPCaller_3

Bookmark: Leser XML Metadata
HTTPCaller
    RESPONSE_HEADER_LIST_ATTR = _headers
    TARGET_ATTR = _response_body
    TARGET_ATTR_ENCODING = auto-detect
    TRANSFER_TIMEOUT_LENGTH = 90
    SAVE_FILE = Attribute
    ERROR_ATTR = _error
    CONNECTION_TIMEOUT_LENGTH = 60
    TARGET_URL = http://159.162.103.4/metadata/FKB40/32_@Value(kommuneid)$(FKB_datasett).xml
    FOLLOW_REDIRECTS = Yes
    VERIFY_SSL_CERTIFICATES = Yes
    HTTP_METHOD = GET
    STATUS_CODE_ATTR = _http_status_code
    USE_COOKIES = No
    -> XMLFlattener
HTTPCaller_2
    RESPONSE_HEADER_LIST_ATTR = _headers
    TARGET_ATTR = _response_body
    TARGET_ATTR_ENCODING = auto-detect
    TRANSFER_TIMEOUT_LENGTH = 90
    SAVE_FILE = Attribute
    ERROR_ATTR = _error
    CONNECTION_TIMEOUT_LENGTH = 60
    TARGET_URL = http://159.162.103.4/metadata/FKB40/33_@Value(kommuneid)$(FKB_datasett).xml
    FOLLOW_REDIRECTS = Yes
    VERIFY_SSL_CERTIFICATES = Yes
    HTTP_METHOD = GET
    STATUS_CODE_ATTR = _http_status_code
    USE_COOKIES = No
    -> XMLFlattener
HTTPCaller_3
    RESPONSE_HEADER_LIST_ATTR = _headers
    TARGET_ATTR = _response_body
    TARGET_ATTR_ENCODING = auto-detect
    TRANSFER_TIMEOUT_LENGTH = 90
    SAVE_FILE = Attribute
    ERROR_ATTR = _error
    CONNECTION_TIMEOUT_LENGTH = 60
    TARGET_URL = http://159.162.103.4/metadata/FKB40/35_@Value(kommuneid)$(FKB_datasett).xml
    FOLLOW_REDIRECTS = Yes
    VERIFY_SSL_CERTIFICATES = Yes
    HTTP_METHOD = GET
    STATUS_CODE_ATTR = _http_status_code
    USE_COOKIES = No
    -> XMLFlattener

Bookmark: Er det dekning?
AttributeFilter
    ATTR_VALUES = <EMPTY>,<MISSING>,<NULL>,<UNFILTERED>,AR5,Adresse,Arealbruk,Bane,BygnAnlegg,Bygning,Bygningspunkt,Hoydekurve-5m,Hoydekurve,Ledning,LedningVa,Lufthavn,MatrikkelkartDekTeig,Naturinfo,PblTiltak,Servitutt,Tekst1000,Tekst5000,TraktorvegSti,Vann,Vbase,Veg
    ATTR_NAME = datasett
    AR5 -> AttributeCreator_3
    Adresse -> AttributeCreator_4
    Arealbruk -> AttributeCreator_5
    Bane -> AttributeCreator_6
    BygnAnlegg -> AttributeCreator_7
    Bygning -> AttributeCreator_8
    Bygningspunkt -> AttributeCreator_9
    Hoydekurve-5m -> AttributeCreator_10
    Hoydekurve -> AttributeCreator_11
    Ledning -> AttributeCreator_12
    LedningVa -> AttributeCreator_24
    Lufthavn -> AttributeCreator_23
    MatrikkelkartDekTeig -> AttributeCreator_22
    Naturinfo -> AttributeCreator_21
    PblTiltak -> AttributeCreator_20
    Servitutt -> AttributeCreator_19
    Tekst1000 -> AttributeCreator_18
    Tekst5000 -> AttributeCreator_17
    TraktorvegSti -> AttributeCreator_16
    Vann -> AttributeCreator_15
    Vbase -> AttributeCreator_14
    Veg -> AttributeCreator_13
AttributeCreator_3
    ATTR_LIST = fkb_ar5,"FME_CONDITIONAL:DEFAULT_VALUE'0'BOOL_OP;OR;COMPOSITE_TEST;<Unused>;TEST @Value(transSize) > 0'1'FME_NUM_CONDITIONS2___"
    -> BulkAttributeRenamer_2
AttributeCreator_4
    ATTR_LIST = fkb_adresse,"FME_CONDITIONAL:DEFAULT_VALUE'0'BOOL_OP;OR;COMPOSITE_TEST;<Unused>;TEST @Value(transSize) > 0'1'FME_NUM_CONDITIONS2___"
    -> BulkAttributeRenamer_2
AttributeCreator_5
    ATTR_LIST = fkb_arealbruk,"FME_CONDITIONAL:DEFAULT_VALUE'0'BOOL_OP;OR;COMPOSITE_TEST;<Unused>;TEST @Value(transSize) > 0'1'FME_NUM_CONDITIONS2___"
    -> BulkAttributeRenamer_2
AttributeCreator_6
    ATTR_LIST = fkb_bane,"FME_CONDITIONAL:DEFAULT_VALUE'0'BOOL_OP;OR;COMPOSITE_TEST;<Unused>;TEST @Value(transSize) > 0'1'FME_NUM_CONDITIONS2___"
    -> BulkAttributeRenamer_2
AttributeCreator_7
    ATTR_LIST = fkb_bygnanlegg,"FME_CONDITIONAL:DEFAULT_VALUE'0'BOOL_OP;OR;COMPOSITE_TEST;<Unused>;TEST @Value(transSize) > 0'1'FME_NUM_CONDITIONS2___"
    -> BulkAttributeRenamer_2
AttributeCreator_8
    ATTR_LIST = fkb_bygning,"FME_CONDITIONAL:DEFAULT_VALUE'0'BOOL_OP;OR;COMPOSITE_TEST;<Unused>;TEST @Value(transSize) > 0'1'FME_NUM_CONDITIONS2___"
    -> BulkAttributeRenamer_2
AttributeCreator_9
    ATTR_LIST = fkb_bygningspunkt,"FME_CONDITIONAL:DEFAULT_VALUE'0'BOOL_OP;OR;COMPOSITE_TEST;<Unused>;TEST @Value(transSize) > 0'1'FME_NUM_CONDITIONS2___"
    -> BulkAttributeRenamer_2
AttributeCreator_10
    ATTR_LIST = fkb_hoydekurve-5m,"FME_CONDITIONAL:DEFAULT_VALUE'0'BOOL_OP;OR;COMPOSITE_TEST;<Unused>;TEST @Value(transSize) > 0'1'FME_NUM_CONDITIONS2___"
    -> BulkAttributeRenamer_2
AttributeCreator_11
    ATTR_LIST = fkb_hoydekurve,"FME_CONDITIONAL:DEFAULT_VALUE'0'BOOL_OP;OR;COMPOSITE_TEST;<Unused>;TEST @Value(transSize) > 0'1'FME_NUM_CONDITIONS2___"
    -> BulkAttributeRenamer_2
AttributeCreator_12
    ATTR_LIST = fkb_ledning,"FME_CONDITIONAL:DEFAULT_VALUE'0'BOOL_OP;OR;COMPOSITE_TEST;<Unused>;TEST @Value(transSize) > 0'1'FME_NUM_CONDITIONS2___"
    -> BulkAttributeRenamer_2
AttributeCreator_24
    ATTR_LIST = fkb_ledningva,"FME_CONDITIONAL:DEFAULT_VALUE'0'BOOL_OP;OR;COMPOSITE_TEST;<Unused>;TEST @Value(transSize) > 0'1'FME_NUM_CONDITIONS2___"
    -> BulkAttributeRenamer_2
AttributeCreator_23
    ATTR_LIST = fkb_lufthavn,"FME_CONDITIONAL:DEFAULT_VALUE'0'BOOL_OP;OR;COMPOSITE_TEST;<Unused>;TEST @Value(transSize) > 0'1'FME_NUM_CONDITIONS2___"
    -> BulkAttributeRenamer_2
AttributeCreator_22
    ATTR_LIST = fkb_matrikkelkartdekteig,"FME_CONDITIONAL:DEFAULT_VALUE'0'BOOL_OP;OR;COMPOSITE_TEST;<Unused>;TEST @Value(transSize) > 0'1'FME_NUM_CONDITIONS2___"
    -> BulkAttributeRenamer_2
AttributeCreator_21
    ATTR_LIST = fkb_naturinfo,"FME_CONDITIONAL:DEFAULT_VALUE'0'BOOL_OP;OR;COMPOSITE_TEST;<Unused>;TEST @Value(transSize) > 0'1'FME_NUM_CONDITIONS2___"
    -> BulkAttributeRenamer_2
AttributeCreator_20
    ATTR_LIST = fkb_pbltiltak,"FME_CONDITIONAL:DEFAULT_VALUE'0'BOOL_OP;OR;COMPOSITE_TEST;<Unused>;TEST @Value(transSize) > 0'1'FME_NUM_CONDITIONS2___"
    -> BulkAttributeRenamer_2
AttributeCreator_19
    ATTR_LIST = fkb_servitutt,"FME_CONDITIONAL:DEFAULT_VALUE'0'BOOL_OP;OR;COMPOSITE_TEST;<Unused>;TEST @Value(transSize) > 0'1'FME_NUM_CONDITIONS2___"
    -> BulkAttributeRenamer_2
AttributeCreator_18
    ATTR_LIST = fkb_tekst1000,"FME_CONDITIONAL:DEFAULT_VALUE'0'BOOL_OP;OR;COMPOSITE_TEST;<Unused>;TEST @Value(transSize) > 0'1'FME_NUM_CONDITIONS2___"
    -> BulkAttributeRenamer_2
AttributeCreator_17
    ATTR_LIST = fkb_tekst5000,"FME_CONDITIONAL:DEFAULT_VALUE'0'BOOL_OP;OR;COMPOSITE_TEST;<Unused>;TEST @Value(transSize) > 0'1'FME_NUM_CONDITIONS2___"
    -> BulkAttributeRenamer_2
AttributeCreator_16
    ATTR_LIST = fkb_traktorvegsti,"FME_CONDITIONAL:DEFAULT_VALUE'0'BOOL_OP;OR;COMPOSITE_TEST;<Unused>;TEST @Value(transSize) > 0'1'FME_NUM_CONDITIONS2___"
    -> BulkAttributeRenamer_2
AttributeCreator_15
    ATTR_LIST = fkb_vann,"FME_CONDITIONAL:DEFAULT_VALUE'0'BOOL_OP;OR;COMPOSITE_TEST;<Unused>;TEST @Value(transSize) > 0'1'FME_NUM_CONDITIONS2___"
    -> BulkAttributeRenamer_2
AttributeCreator_14
    ATTR_LIST = fkb_vbase,"FME_CONDITIONAL:DEFAULT_VALUE'0'BOOL_OP;OR;COMPOSITE_TEST;<Unused>;TEST @Value(transSize) > 0'1'FME_NUM_CONDITIONS2___"
    -> BulkAttributeRenamer_2
AttributeCreator_13
    ATTR_LIST = fkb_veg,"FME_CONDITIONAL:DEFAULT_VALUE'0'BOOL_OP;OR;COMPOSITE_TEST;<Unused>;TEST @Value(transSize) > 0'1'FME_NUM_CONDITIONS2___"
    -> BulkAttributeRenamer_2
Note: Alle attributter til små bokstaver
BulkAttributeRenamer_2
    CASE_CHANGE_TYPE = lowercase
    PATTERN_ACTION_DISP = Change Case
    ATTRCHOICE = All Attributes
    -> Tester_3

Bookmark: KommuneID ledende 0
Tester_3
    TEST_CLAUSE = TEST @Value(kommuneid) BEGINS_WITH 0
    TEST_DESCRIPTION = ""
    BOOL_OP = OR
    TEST_MODE = Automatic
    PASSED -> SubstringExtractor
    FAILED -> dekningsoversikt.dekningsoversikt (writer POSTGRES_2)
SubstringExtractor
    START = 1
    END = -1
    RESULT_ATTR = kommuneid
    SRC_STRING = @Value(kommuneid)
    -> dekningsoversikt.dekningsoversikt (writer POSTGRES_2)
