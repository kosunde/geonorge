FME workspace Akvakultur_wfs2postgis.fmw

Parameters:
- CONFIG_FILE:   # Python Script
      #-------------------------------------------------------------------------------
      # Name:        GetConfigFile
      # Purpose:
      #
      # Author:      xsunknu
      #
      # Created:     21.08.2015
      # Copyright:   (c) xsunknu 2015
      # Licence:     <your licence>
      #-------------------------------------------------------------------------------
      
      import os, fme
      
      fmwdir = fme.macroValues['FME_MF_DIR']
      fmwfile = fme.macroValues['FME_MF_NAME']
      
      fmwfile = os.path.join(fmwdir, fmwfile)
      configfile = os.path.splitext(fmwfile)[0] + '_config.xml'
      
      return configfile
- WFS_IN:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('wfsin').text
      
      return value
- PG_DB:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgdb').text
      
      return value
- COORDSYS_OUT = EPSG:4258   # Coordsys out

Readers:
- WFS_1: WFS from $(WFS_IN)

Writers:
- POSTGIS_1: POSTGIS to $(PG_DB)
- POSTGRES_1: POSTGRES to $(PG_DB)

DateFormatter
    DATE_ATTR = mudato
    SRCFMT = %d.%m.%Y
    FMT = FME Date (%Y%m%d)
    INVALID_DATE_VALUE = FME_NULL_VALUE
    -> AttributeCreator_6
Note: Legger på kopidato
AttributeCreator_6
    ATTR_LIST = mudato,"FME_CONDITIONAL:DEFAULT_VALUE'@Value(mudato)'BOOL_OP;OR;COMPOSITE_TEST;<Unused>;TEST @Value(mudato) < 19000101'FME_NULL_VALUE'FME_NUM_CONDITIONS2___",kopidato,@Timestamp(^Y^m^d)
    -> Reprojector
Note: Reprojiserer til EPSG:4258
Reprojector
    RASTER_CELL_SIZE = Preserve Cells
    DEST = $(COORDSYS_OUT)
    SOURCE = Read from feature
    INTERPOLATION_TYPE_NAME = Nearest Neighbor
    REPROJECTED -> FeatureTypeFilter
FeatureTypeFilter
    ATTRIBUTES = layer_92,layer_245,layer_460,layer_553,<BLANK>,<UNFILTERED>
    layer_245 -> DuplicateRemover
    layer_553 -> SplittAttributter
    layer_460 -> DuplicateRemover
    layer_92 -> AttributeCreator_11
AttributeCreator_11
    ATTR_LIST = flateid,@Evaluate(@Count(akvakulturflate, 1))
    -> GeometryCoercer
    -> AttributeCreator_9
GeometryCoercer
    GQUERY:
      for $geom in //geometry
      where $geom/count(parent::geometry) = 0
      return number($geom/@fme_id)
    KIND = fme_line
    COERCED -> AttributeCreator_4
AttributeCreator_4
    ATTR_LIST = objtype,Akvakulturgrense,avgrensningfk,@Value(flateid),objid,@Evaluate(@Count(akvakulturgrense, 1))
    -> akvakultur.akvakulturgrense (writer POSTGIS_1)
AttributeCreator_9
    ATTR_LIST = objid,@Value(flateid),objtype,Akvakulturområde
    -> akvakultur.akvakulturflate (writer POSTGIS_1)
SplittAttributter
    POST_ADRESSE = @Value(post_adresse)
    GEOM = @Value(geom)
    PLASSERING = @Value(plassering)
    LOKNR = @Value(loknr)
    PRODUKSJON = @Value(produksjon)
    NAVN = @Value(navn)
    AREAL_M2 = @Value(areal_m2)
    ID = @Value(id)
    LOKALITET = @Value(lokalitet)
    FORMAAL = @Value(formaal)
    KAPASITET = @Value(kapasitet)
    INNEHAVER = @Value(innehaver)
    AV_CLASS = @Value(av_class)
    ORGANISASJONSNUMMER = @Value(organisasjonsnummer)
    VANNMILJO = @Value(vannmiljo)
    FIRMA_ADRESSE = @Value(firma_adresse)
    POST_POSTSTED = @Value(post_poststed)
    TILLATELSE_HTML = @Value(tillatelse_html)
    FIRMA_POSTSTED = @Value(firma_poststed)
    MSGEOMETRY = @Value(msGeometry)
    OBJECTID = @Value(objectid)
    GEOM_25833 = @Value(geom_25833)
    ART = @Value(art)
    TILLATELSESNR = @Value(tillatelsesnr)
    -> AttributeCreator
AttributeCreator
    ATTR_LIST = objtype,Akvakultur,akva_enhet,@Value(enhet),akva_kapasitet,@Value(kapasitet),firma,@Value(innehaver),adresse,@Value(post_adresse),postnr,@Value(post_postnummer),postadresse,@Value(post_poststed),akvakulturid,@Evaluate(@Count(akvakultur, 1))
    -> ListExploder_2
    -> ListExploder
    -> AttributeCreator_2
    -> AttributeCreator_10
AttributeCreator_10
    ATTR_LIST = objid,@Value(akvakulturid)
    -> akvakultur.akvakulturpunkt (writer POSTGIS_1)
AttributeCreator_2
    ATTR_LIST = adresse,@Value(firma_adresse),postnr,@Value(firma_postnummer),postadresse,@Value(firma_poststed),firmaeierfk,@Value(akvakulturid),objid,@Evaluate(@Count(firmaeier, 1))
    -> akvakultur.firmaeier (writer POSTGRES_1)
ListExploder_2
    ATTR_CONFLICT_RES = Use Original
    INDEX_ATTR = _element_index
    LIST_ATTR = tillatelsesnummere{}
    ATTR_ACCUM_MODE = Merge Incoming List
    LIST_FOUND -> AttributeCreator_7
AttributeCreator_7
    ATTR_LIST = objid,@Evaluate(@Count(akvatillatelsesinformasjon, 1)),lok_navn,@Value(lokaliteter{1}),lok_nr,@Value(loknr),tillatelseshtml,@Value(tillatelse_htmler{@Value(_element_index)}),tillatelsesinformasjonfk,@Value(akvakulturid),akvatillatelsesnummer,@Evaluate(@Substring(@Value(tillatelsesnummere),4,4)),fiskebruknummerfylke,@Substring(@Value(tillatelsesnummere),0,2),fiskebruknummerkommune,@Substring(@Value(tillatelsesnummere),2,2)
    -> AttributeSplitter
AttributeSplitter
    DELIMITER = "
    DROP_EMPTY_PARTS = No
    LIST_NAME = tillatelseshtml
    TRIM_OPTION = Both
    ATTR_NAME = tillatelseshtml
    -> AttributeCreator_8
AttributeCreator_8
    ATTR_LIST = tillatelsesurl,@Value(tillatelseshtml{1})
    -> akvakultur.akvatillatelsesinformasjon (writer POSTGRES_1)
ListExploder
    ATTR_CONFLICT_RES = Use Original
    INDEX_ATTR = _element_index
    LIST_ATTR = arter{}
    ATTR_ACCUM_MODE = Merge Incoming List
    LIST_FOUND -> AttributeCreator_3
AttributeCreator_3
    ATTR_LIST = art,@Value(arter),objtype,Art,artfk,@Value(akvakulturid),objid,@Evaluate(@Count(artnr, 1))
    -> akvakultur.art (writer POSTGRES_1)
DuplicateRemover
    KEYATTR = loknr loktilstand miljoundersokelse_type mudato
    UNIQUE -> AttributeCreator_5
AttributeCreator_5
    ATTR_LIST = objid,@Evaluate(@Count(miljoundersokelse,1)),objtype,Mijøundersøkelse
    -> akvakultur.miljoundersokelse (writer POSTGRES_1)

Bookmark: Input WFS layers
Note: Lokalitet - flate fra klarerte ytterpunkt
layer_92 (reader WFS_1)
    attributes: gml_parent_id xml_buffer, gml_parent_property xml_buffer, gml_id xml_buffer, msGeometry xml_geometry, id xml_buffer, navn xml_buffer, areal_m2 xml_buffer
    -> AttributeCreator_6
Note: Alle lokaliteter m/ innehaver
layer_553 (reader WFS_1)
    attributes: gml_parent_id xml_buffer, gml_parent_property xml_buffer, gml_id xml_buffer, msGeometry xml_geometry, objectid xml_buffer, loknr xml_buffer, lokalitet xml_buffer, innehaver xml_buffer, organisasjonsnummer xml_buffer, firma_adresse xml_buffer, firma_poststed xml_buffer, post_adresse xml_buffer, post_poststed xml_buffer, tillatelsesnr xml_buffer, kapasitet xml_buffer, art xml_buffer, produksjon xml_buffer, formaal xml_buffer, plassering xml_buffer, vannmiljo xml_buffer, geom xml_buffer, av_class xml_buffer, tillatelse_html xml_buffer, geom_25833 xml_buffer
    -> AttributeCreator_6
Note: MOM C
layer_460 (reader WFS_1)
    attributes: gml_parent_id xml_buffer, gml_parent_property xml_buffer, gml_id xml_buffer, msGeometry xml_geometry, loknr xml_buffer, lokalitet xml_buffer, tillatelsesnr xml_buffer, art xml_buffer, kapasitet xml_buffer, navn xml_buffer, produksjon xml_buffer, formaal xml_buffer, mudato xml_buffer, uri xml_buffer, plassering xml_buffer, prodorgnavn xml_buffer, miljoundersokelse_type xml_buffer, av_class xml_buffer
    -> DateFormatter
Note: MOM B
layer_245 (reader WFS_1)
    attributes: gml_parent_id xml_buffer, gml_parent_property xml_buffer, gml_id xml_buffer, msGeometry xml_geometry, loknr xml_buffer, lokalitet xml_buffer, tillatelsesnr xml_buffer, art xml_buffer, kapasitet xml_buffer, navn xml_buffer, produksjon xml_buffer, formaal xml_buffer, loktilstand xml_buffer, mudato xml_buffer, uri xml_buffer, plassering xml_buffer, prodorgnavn xml_buffer, miljoundersokelse_type xml_buffer, av_class xml_buffer
    -> DateFormatter

Bookmark: Output PostGIS tables
akvakultur.akvakulturgrense (writer POSTGIS_1)
    attributes: objid int4,PRIKEY, objtype varchar(32), avgrensningfk int4,BTREE, kopidato date
akvakultur.akvakulturflate (writer POSTGIS_1)
    attributes: objid int4,PRIKEY, objtype varchar(32), id int4, navn varchar(80), areal_m2 int4, kopidato date
akvakultur.akvakulturpunkt (writer POSTGIS_1)
    attributes: objid int4,PRIKEY, objtype varchar(32), akva_enhet varchar(80), akva_kapasitet float4, av_class varchar(80), plassering varchar(80), vannmiljo varchar(80), kopidato date

Bookmark: Output PostgreSQL tables
akvakultur.firmaeier (writer POSTGRES_1)
    attributes: objid int4,PRIKEY, objtype varchar(32), firma varchar(80), fiske_bedr_eier varchar(80), adresse varchar(80), postnr int4, postadresse varchar(80), telefonnr int4, kontaktperson varchar(80), firmaeierfk int4,BTREE, kopidato date
akvakultur.akvatillatelsesinformasjon (writer POSTGRES_1)
    attributes: objid serial,PRIKEY, lok_navn varchar(80), lok_nr int4, fiskebruknummerfylke varchar(80), fiskebruknummerkommune varchar(80), akvatillatelsesnummer int4, tillatelsesformaal varchar(80), tillatelsesstatus varchar(80), tillatelsestype varchar(80), tillatelsesurl varchar(255), tillatelsesinformasjonfk int4,BTREE, kopidatp date
akvakultur.art (writer POSTGRES_1)
    attributes: objid int4,PRIKEY, art varchar(80), artfk int4,BTREE, kopidato date
akvakultur.miljoundersokelse (writer POSTGRES_1)
    attributes: objid int4,PRIKEY, mudato date, miljoundersokelse_type varchar(80), loktilstand varchar(80), akvamiljoeundersoekelsefk int4,BTREE, kopidato date

FME custom transformer SplittAttributter

Parameters:
- KAPASITET = @Value(kapasitet)   # kapasitet
- AREAL_M2 = @Value(areal_m2)   # Areal M2
- ART = @Value(art)   # art
- AV_CLASS = @Value(av_class)   # Av Class
- FIRMA_ADRESSE = @Value(firma_adresse)   # Firma Adresse
- FIRMA_POSTSTED = @Value(firma_poststed)   # Firma Poststed
- FORMAAL = @Value(formaal)   # formaal
- GEOM = @Value(geom)   # geom
- GEOM_25833 = @Value(geom_25833)   # Geom 25833
- ID = @Value(id)   # id
- INNEHAVER = @Value(innehaver)   # innehaver
- LOKALITET = @Value(lokalitet)   # lokalitet
- LOKNR = @Value(loknr)   # loknr
- MSGEOMETRY = @Value(msGeometry)   # msGeometry
- NAVN = @Value(navn)   # navn
- OBJECTID = @Value(objectid)   # objectid
- ORGANISASJONSNUMMER = @Value(organisasjonsnummer)   # organisasjonsnummer
- PLASSERING = @Value(plassering)   # plassering
- POST_ADRESSE = @Value(post_adresse)   # Post Adresse
- POST_POSTSTED = @Value(post_poststed)   # Post Poststed
- PRODUKSJON = @Value(produksjon)   # produksjon
- TILLATELSE_HTML = @Value(tillatelse_html)   # Tillatelse Html
- TILLATELSESNR = @Value(tillatelsesnr)   # tillatelsesnr
- VANNMILJO = @Value(vannmiljo)   # vannmiljo

Note: Splitter sammensatte attributter og lister
Input (input)
    -> AttributeSplitter
Output (output)

Bookmark: Kapasitet
AttributeSplitter
    DELIMITER = " "
    DROP_EMPTY_PARTS = No
    LIST_NAME = kapasitet_enhet
    TRIM_OPTION = Both
    ATTR_NAME = kapasitet
    -> AttributeCreator
AttributeCreator
    ATTR_LIST = kapasitet,@Value(kapasitet_enhet{0}),enhet,@Value(kapasitet_enhet{1})
    -> AttributeValueMapper
AttributeValueMapper
    VAL_ATTR = enhet
    LUT = M3,1,STK,2,TN,4,DA,3,KG,7,M2,8
    DIRECTION = Forward (Source To Destination)
    SRC = enhet
    -> AttributeSplitter_2

Bookmark: Postnummer og poststed
AttributeSplitter_2
    DELIMITER = " "
    DROP_EMPTY_PARTS = No
    LIST_NAME = postnummer_poststed
    TRIM_OPTION = Both
    ATTR_NAME = post_poststed
    -> AttributeCreator_2
AttributeCreator_2
    ATTR_LIST = post_postnummer,@Value(postnummer_poststed{0}),post_poststed,@Value(postnummer_poststed{1})
    -> AttributeSplitter_3
AttributeSplitter_3
    DELIMITER = " "
    DROP_EMPTY_PARTS = No
    LIST_NAME = postnummer_poststed
    TRIM_OPTION = Both
    ATTR_NAME = firma_poststed
    -> AttributeCreator_3
AttributeCreator_3
    ATTR_LIST = firma_postnummer,@Value(postnummer_poststed{0}),firma_poststed,@Value(postnummer_poststed{1})
    -> AttributeSplitter_4

Bookmark: Arter
AttributeSplitter_4
    DELIMITER = ,
    DROP_EMPTY_PARTS = No
    LIST_NAME = arter
    TRIM_OPTION = Both
    ATTR_NAME = art
    -> AttributeSplitter_5

Bookmark: Tillatelser
AttributeSplitter_5
    DELIMITER = ,
    DROP_EMPTY_PARTS = No
    LIST_NAME = tillatelsesnummere
    TRIM_OPTION = Both
    ATTR_NAME = tillatelsesnr
    -> AttributeSplitter_6
AttributeSplitter_6
    DELIMITER = ,
    DROP_EMPTY_PARTS = No
    LIST_NAME = tillatelse_htmler
    TRIM_OPTION = Both
    ATTR_NAME = tillatelse_html
    -> AttributeSplitter_7
AttributeSplitter_7
    DELIMITER = " "
    DROP_EMPTY_PARTS = No
    LIST_NAME = lokaliteter
    TRIM_OPTION = Both
    ATTR_NAME = lokalitet
    -> Output (output)
