FME workspace Akvakultur_postgis2sosi.fmw
# Copyright: (c) xgrimor 2015
# Licence: <your licence>
Shutdown Python:
      # -*- coding: utf-8 -*-
      #-------------------------------------------------------------------------------
      # Name:        zipfiles.py
      # Purpose:     Pakker filer i output folderen
      #
      # Author:      xsunknu
      #
      # Created:     18.09.2015
      # Copyright:   (c) xsunknu 2015
      # Licence:     <your licence>
      #-------------------------------------------------------------------------------

      import sys, os, zipfile, fme

      def zip(sosifile, zfile):
          from os.path import basename

          # Lager korresponderende zip-fil av SOSI-fil
          if os.path.isfile(zfile):
              os.remove(zfile)

          zf = zipfile.ZipFile(zfile, "w", zipfile.ZIP_DEFLATED)

          # Ønsker ikke full sti inn i ZIP-filen
          arcname = basename(sosifile)

          # ZIP-formatet støtter ikke non-ascii tegn
          # Erstatter AØÅæøå med ascii-tegn
          arcname = arcname.replace('\xc6', 'E')
          arcname = arcname.replace('\xd8', 'O')
          arcname = arcname.replace('\xc5', 'A')
          arcname = arcname.replace('\xe6', 'e')
          arcname = arcname.replace('\xf8', 'o')
          arcname = arcname.replace('\xe5', 'a')

          zf.write(sosifile, arcname)
          zf.close()
          os.remove(sosifile)

          return

      def main():

          # Kjøres ikke på FME Server, da FME Server selv sørger for pakkingen
          if not 'FME_SERVER_DEST_DIR' in fme.macroValues:
              if 'FANOUT_FOLDER' in fme.macroValues:
                  path = fme.macroValues['FANOUT_FOLDER']
                  for dirpath, dnames, fnames in os.walk(path):
                      for f in fnames:
                          if f.endswith(".sos"):
                              # Scanner gjennom alle SOSI-filer
                              sosifile = os.path.join(path, f)
                              zfile = os.path.splitext(sosifile)[0] + '.zip'
                              if os.path.isfile(zfile):

                                  # Korresponderende ZIP-fil finnes, sjekker timestamps
                                  sositstamp = os.stat(sosifile).st_mtime
                                  ziptstamp = os.stat(zfile).st_mtime

                                  if sositstamp > ziptstamp:
                                      # SOSI-fil er nyere enn ZIP-fila, ZIP-fila oppdateres
                                      # SOSI-fila slettes
                                      try:
                                          zip(sosifile, zfile)
                                      except:
                                          print 'Kunne ikke pakke: ' + sosifile
                                  else:
                                      # SOSI-fila er eldre enn ZIP-fila
                                      # SOSI-fila slettes
                                      try:
                                          os.remove(sosifile)
                                      except:
                                          print 'Kunne ikke slette: ' + sosifile
                              else:
                                  # ZIP-fila eksisterer ikke og lages
                                  # SOSI-fila slettes
                                  try:
                                      zip(sosifile, zfile)
                                  except:
                                      print 'Kunne ikke pakke: ' + sosifile


      if __name__ == '__main__':
          main()

Parameters:
- KNR =   # Kommune(r)
- FNR =   # Fylke(r)
- CLIPPERCOORDS =   # Clipper coordinates
- CLIPPER_EPSG_CODE =   # Clipper EPSG code
- CLIPPER_FILE =   # "" Clipper file (any format)
- OUTPUT_EPSG_CODE = 25833   # Output EPSG code
- FANOUT =   # Fanout områder
- CONFIG_FILE:   # Python Script
      #-------------------------------------------------------------------------------
      # Name:        GetConfigFile
      # Purpose:
      #
      # Author:      xsunknu
      #
      # Created:     21.08.2015
      # Copyright:   (c) xsunknu 2015
      # Licence:     <your licence>
      #-------------------------------------------------------------------------------
      
      import os, fme
      
      fmwdir = fme.macroValues['FME_MF_DIR']
      fmwfile = fme.macroValues['FME_MF_NAME']
      
      fmwfile = os.path.join(fmwdir, fmwfile)
      configfile = os.path.splitext(fmwfile)[0] + '_config.xml'
      
      return configfile
- PG_PWD:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgpwd').text
      
      return value
- PG_USER:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pguser').text
      
      return value
- PG_PORT:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgport').text
      
      return value
- PG_HOST:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pghost').text
      
      return value
- PG_DB:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgdb').text
      
      return value
- CLIPPERCOORDSYS:   # Python Script
      #-------------------------------------------------------------------------------
      # Name:        SetCoordinateSystem
      # Purpose:
      #
      # Author:      xsunknu
      #
      # Created:     21.08.2015
      # Copyright:   (c) xsunknu 2015
      # Licence:     <your licence>
      #-------------------------------------------------------------------------------
      
      import os, fme
      
      EPSGvalue = fme.macroValues['CLIPPER_EPSG_CODE']
      EPSGcode  = 'EPSG:' + EPSGvalue
      
      return EPSGcode
- FIXEDCLIPPERCOORDS:   # Python Script
      #-------------------------------------------------------------------------------
      # Name:        FixClipperCoords
      # Purpose:
      #
      # Author:      xsunknu
      #
      # Created:     21.08.2015
      # Copyright:   (c) xsunknu 2015
      # Licence:     <your licence>
      #-------------------------------------------------------------------------------
      
      import fme
      clippercoords = fme.macroValues['CLIPPERCOORDS']
      
      if clippercoords == '':
          clippercoords = '1 1'
      
      return clippercoords
- DESTCOORDSYS:   # Python Script
      #-------------------------------------------------------------------------------
      # Name:        SetCoordinateSystem
      # Purpose:
      #
      # Author:      xsunknu
      #
      # Created:     21.08.2015
      # Copyright:   (c) xsunknu 2015
      # Licence:     <your licence>
      #-------------------------------------------------------------------------------
      
      import os, fme
      
      EPSGvalue = fme.macroValues['OUTPUT_EPSG_CODE']
      EPSGcode  = 'EPSG:' + EPSGvalue
      
      return EPSGcode
- MAPPING_FILE:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme, os
      from xml.etree import ElementTree as ET
      
      #Read XML config file
      configtree = ET.parse(fme.macroValues['CONFIG_FILE'])
      configdoc = configtree.getroot()
      
      value = os.path.join(fme.macroValues['FME_MF_DIR'], configdoc.find('mappingfile').text)
      
      return value
- SOSIDEF_FILE:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme, os
      from xml.etree import ElementTree as ET
      
      #Read XML config file
      configtree = ET.parse(fme.macroValues['CONFIG_FILE'])
      configdoc = configtree.getroot()
      
      value = os.path.join(fme.macroValues['FME_MF_DIR'], configdoc.find('sosideffile').text)
      
      return value
- LOG_FILE:   # Python Script
      #-------------------------------------------------------------------------------
      # Name:        GetConfigFile
      # Purpose:
      #
      # Author:      xsunknu
      #
      # Created:     21.08.2015
      # Copyright:   (c) xsunknu 2015
      # Licence:     <your licence>
      #-------------------------------------------------------------------------------
      
      import os, uuid, fme
      
      fmwdir = fme.macroValues['FME_MF_DIR']
      fmwfile = fme.macroValues['FME_MF_NAME']
      
      logdir = os.path.join(fmwdir, 'log')
      if not os.path.isdir(logdir):
          os.mkdir(logdir)
      
      logfile = os.path.splitext(fmwfile)[0] + '_' + str(uuid.uuid1()).replace('-','') + '.log'
      logfile = os.path.join(logdir, logfile)
      
      return logfile
- HOVEDTEMA = Fiskeri   # Hovedtema
- UNDERTEMA = Akvakultur   # Undertema
- FANOUT_FOLDER:   # Python Script
      #-------------------------------------------------------------------------------
      # Name:        GetConfigFile
      # Purpose:
      #
      # Author:      xsunknu
      #
      # Created:     21.08.2015
      # Copyright:   (c) xsunknu 2015
      # Licence:     <your licence>
      #-------------------------------------------------------------------------------
      
      import os, fme
      from xml.etree import ElementTree as ET
      
      if 'FME_SERVER_DEST_DIR' in fme.macroValues:
          value = fme.macroValues['FME_SERVER_DEST_DIR']
      else:
          #Read XML config file
          configtree = ET.parse(fme.macroValues['CONFIG_FILE'])
          configdoc = configtree.getroot()
          value = configdoc.find('destdir').text
      
      return value

Readers:
- POSTGIS_1: POSTGIS from $(PG_DB)
- POSTGRES_1: POSTGRES from $(PG_DB)
- POSTGIS_2: POSTGIS from $(PG_DB)

Writers:
- SOSI_1: SOSI to C:\Users\xsunknu\Documents\geonorge\Fiskeridirektoratet\Output\Akvakultur.sos

CreateClipper
    CLIPPERCOORDSYS = $(CLIPPERCOORDSYS)
    DESTCOORDSYS = $(DESTCOORDSYS)
    CLIPPERCOORDS = $(FIXEDCLIPPERCOORDS)
    -> Clipper [input 1]
AttributeCreator_4
    ATTR_LIST = _clippercoords,$(CLIPPERCOORDS),_clipper_file,$(CLIPPER_FILE),_fnr,$(FNR),_knr,$(KNR)
    -> Tester_3
Note: Klipper ikke hvis ikke / klippeparametere er / gitt
Tester_3
    BOOL_OP = AND
    TEST_DESCRIPTION = ""
    TEST_MODE = Automatic
    TEST_CLAUSE:
      TEST _clipper_file ATTRIBUTE_IS_EMPTY ""
      TEST _clippercoords ATTRIBUTE_IS_EMPTY ""
      TEST _fnr ATTRIBUTE_IS_EMPTY ""
      TEST _knr ATTRIBUTE_IS_EMPTY ""
    FAILED -> Clipper [input 2]
    PASSED -> SosiFilenameSetter
Clipper
    CREATE_AGGREGATES = Yes
    CLIPPED_ATTR = _clipped
    ATTR_ACCUM_MODE = Merge Clipper
    CLIP_TYPE = Multiple Clippers
    BOUNDARY_CASES = Treat as Inside
    PRESERVE_CLIPPEE_EXTENTS = No
    ATTR_CONFLICT_RES = Use Clippee
    INSIDE -> SosiFilenameSetter
SosiFilenameSetter
    KOMMUNEID = @Value(kommuneid)
    _CLIPPED = @Value(_clipped)
    FYLKEID = @Value(fylkeid)
    PG_USER:
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------

      import fme
      from xml.etree import ElementTree as ET

      #Read XML config file
      configtree = ET.parse(fme.macroValues['CONFIG_FILE'])
      configdoc = configtree.getroot()
      value = configdoc.find('pguser').text

      return value
    HOVEDTEMA = $(HOVEDTEMA)
    AKVA_KAPASITET = @Value(akva_kapasitet)
    FANOUT = $(FANOUT)
    PG_PORT:
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------

      import fme
      from xml.etree import ElementTree as ET

      #Read XML config file
      configtree = ET.parse(fme.macroValues['CONFIG_FILE'])
      configdoc = configtree.getroot()
      value = configdoc.find('pgport').text

      return value
    _KNR = @Value(_knr)
    VANNMILJO = @Value(vannmiljo)
    OUTPUT_EPSG_CODE = $(OUTPUT_EPSG_CODE)
    NAVN = @Value(navn)
    OBJID = @Value(objid)
    _FNR = @Value(_fnr)
    ID = @Value(id)
    PG_DB:
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------

      import fme
      from xml.etree import ElementTree as ET

      #Read XML config file
      configtree = ET.parse(fme.macroValues['CONFIG_FILE'])
      configdoc = configtree.getroot()
      value = configdoc.find('pgdb').text

      return value
    AKVA_ENHET = @Value(akva_enhet)
    _CLIPPERCOORDS = @Value(_clippercoords)
    AREAL_M2 = @Value(areal_m2)
    PLASSERING = @Value(plassering)
    PG_PWD:
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------

      import fme
      from xml.etree import ElementTree as ET

      #Read XML config file
      configtree = ET.parse(fme.macroValues['CONFIG_FILE'])
      configdoc = configtree.getroot()
      value = configdoc.find('pgpwd').text

      return value
    AVGRENSNINGFK = @Value(avgrensningfk)
    _CREATION_INSTANCE = @Value(_creation_instance)
    UNDERTEMA = $(UNDERTEMA)
    KOPIDATO = @Value(kopidato)
    _CLIPPER_FILE = @Value(_clipper_file)
    AV_CLASS = @Value(av_class)
    PG_HOST:
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------

      import fme
      from xml.etree import ElementTree as ET

      #Read XML config file
      configtree = ET.parse(fme.macroValues['CONFIG_FILE'])
      configdoc = configtree.getroot()
      value = configdoc.find('pghost').text

      return value
    OBJTYPE = @Value(objtype)
    -> Reprojector
Note: Reprojiserer til destcoordsys
Reprojector
    DEST = $(DESTCOORDSYS)
    RASTER_CELL_SIZE = Preserve Cells
    SOURCE = Read from feature
    INTERPOLATION_TYPE_NAME = Nearest Neighbor
    REPROJECTED -> FeatureTypeFilter
FeatureTypeFilter
    ATTRIBUTES = <BLANK>,<UNFILTERED>,akvakultur.akvakulturflate,akvakultur.akvakulturgrense,akvakultur.akvakulturpunkt
    akvakultur.akvakulturpunkt -> FeatureMerger_2 [input 1]
    akvakultur.akvakulturflate -> AttributeCreator
    akvakultur.akvakulturgrense -> AttributeCreator_2
Note: Kobler inn eier 1-1
FeatureMerger_2
    LIST_NAME = L:akva_art
    PROCESS_DUPS = No
    MERGE_TYPE = Attributes Only
    ATTR_ACCUM_MODE = Merge Supplier
    JOIN_KEYS = @Value(objid) @Value(firmaeierfk) AUTO
    IGNORE_NULLS = No
    ATTR_CONFLICT_RES = Use Requestor
    SUPPLIERS_FIRST = No
    MERGED -> FeatureMerger [input 1]
Note: Kobler inn art 0-n
FeatureMerger
    LIST_NAME = L:akva_art
    PROCESS_DUPS = No
    MERGE_TYPE = Attributes Only
    ATTR_ACCUM_MODE = Merge Supplier
    JOIN_KEYS = @Value(objid) @Value(artfk) AUTO
    IGNORE_NULLS = No
    ATTR_CONFLICT_RES = Use Requestor
    SUPPLIERS_FIRST = No
    MERGED -> FeatureMerger_3 [input 1]
Note: Kobler inn / tillatelsesinformasjon
FeatureMerger_3
    LIST_NAME = L:akvatillatelsesinformasjon
    PROCESS_DUPS = No
    MERGE_TYPE = Attributes Only
    ATTR_ACCUM_MODE = Merge Supplier
    JOIN_KEYS = @Value(objid) @Value(tillatelsesinformasjonfk) AUTO
    IGNORE_NULLS = No
    ATTR_CONFLICT_RES = Use Requestor
    SUPPLIERS_FIRST = No
    MERGED -> AttributeCreator_3

Bookmark: Fylke and/or kommune clippers
admingrense.fylkeflate (reader POSTGIS_2)
    attributes: fylkeid int4
    -> Tester
Tester
    BOOL_OP = OR
    TEST_DESCRIPTION = ""
    TEST_MODE = Automatic
    TEST_CLAUSE = TEST @Value(fylkeid) IN $(FNR)
    PASSED -> Reprojector_2
admingrense.kommuneflate (reader POSTGIS_2)
    attributes: kommuneid int4
    -> Tester_2
Tester_2
    BOOL_OP = OR
    TEST_DESCRIPTION = ""
    TEST_MODE = Automatic
    TEST_CLAUSE = TEST @Value(kommuneid) IN $(KNR)
    PASSED -> Reprojector_2
Reprojector_2
    DEST = EPSG:4258
    RASTER_CELL_SIZE = Preserve Cells
    SOURCE = Read from feature
    INTERPOLATION_TYPE_NAME = Nearest Neighbor
    REPROJECTED -> Clipper [input 1]

Bookmark: Clipper file (any format)
Creator
    GEOMTYPE = Geometry Object
    NUM = 1
    CREATED -> FeatureReader
FeatureReader
    GENERIC_REAL_FORMAT = GUESS_FROM_EXTENSION
    DATASET = $(CLIPPER_FILE)
    ATTR_ACCUM_MODE = Only Use Result
    INTERACT = <No Spatial Filter>
    FORMAT = GENERIC
    FEATURETYPES_RADIO = FEATURETYPES
    COMBINE_GEOM = Use Result
    ATTRIBUTES = NewFeatureType,
    OUTPUT_FEATURES_DISPLAY = Based on Connections
    <OTHER> -> Reprojector_3
Reprojector_3
    DEST = EPSG:4258
    RASTER_CELL_SIZE = Preserve Cells
    SOURCE = Read from feature
    INTERPOLATION_TYPE_NAME = Nearest Neighbor
    REPROJECTED -> Clipper [input 1]

Bookmark: PostGIS in
akvakultur.akvakulturflate (reader POSTGIS_1)
    attributes: objid int4,PRIKEY, objtype varchar(32), id int4, navn varchar(80), areal_m2 int4, kopidato date
    -> AttributeCreator_4
akvakultur.akvakulturgrense (reader POSTGIS_1)
    attributes: objid int4,PRIKEY, objtype varchar(32), avgrensningfk int4,BTREE, kopidato date
    -> AttributeCreator_4
akvakultur.akvakulturpunkt (reader POSTGIS_1)
    attributes: objid int4,PRIKEY, objtype varchar(32), akva_enhet varchar(80), plassering varchar(80), vannmiljo varchar(80), akva_kapasitet float4, av_class varchar(80), kopidato date
    -> AttributeCreator_4

Bookmark: Legger på SOSI-attributter
AttributeCreator
    ATTR_LIST = dataeier,Fiskeridirektoratet,fylkesnr,@Value(fylkeid),komm,"FME_CONDITIONAL:DEFAULT_VALUE'@PadLeft(@Value(kommuneid),4,0)'BOOL_OP;OR;COMPOSITE_TEST;<Unused>;TEST kommuneid ATTRIBUTE_IS_MISSING _FME_BLANK_STRING_'FME_NULL_VALUE'FME_NUM_CONDITIONS2___"
    -> akvakultur.akvakulturflate (writer SOSI_1)
AttributeCreator_2
    ATTR_LIST = dataeier,Fiskeridirektoratet,malemetode,99,synbarhet,0,noyaktighet,99,komm,"FME_CONDITIONAL:DEFAULT_VALUE'@PadLeft(@Value(kommuneid),4,0)'BOOL_OP;OR;COMPOSITE_TEST;<Unused>;TEST kommuneid ATTRIBUTE_IS_MISSING _FME_BLANK_STRING_'FME_NULL_VALUE'FME_NUM_CONDITIONS2___",fylkesnr,@Value(fylkeid)
    -> akvakultur.akvakulturgrense (writer SOSI_1)
AttributeCreator_3
    ATTR_LIST = dataeier,Fiskeridirektoratet,malemetode,99,synbarhet,0,noyaktighet,99,komm,"FME_CONDITIONAL:DEFAULT_VALUE'@PadLeft(@Value(kommuneid),4,0)'BOOL_OP;OR;COMPOSITE_TEST;<Unused>;TEST kommuneid ATTRIBUTE_IS_MISSING _FME_BLANK_STRING_'FME_NULL_VALUE'FME_NUM_CONDITIONS2___",fylkesnr,@Value(fylkeid)
    -> akvakultur.akvakulturpunkt (writer SOSI_1)

Bookmark: SOSI out
akvakultur.akvakulturflate (writer SOSI_1)
    attributes: objtype SOSI_varchar(32), navn SOSI_varchar(80), areal_m2 SOSI_int32, dataeier SOSI_varchar(80), kopidato SOSI_date, komm SOSI_varchar(4), fylkesnr SOSI_int16
akvakultur.akvakulturgrense (writer SOSI_1)
    attributes: objtype SOSI_varchar(32), dataeier SOSI_varchar(80), kopidato SOSI_date, malemetode SOSI_int16, noyaktighet SOSI_int16, synbarhet SOSI_int16, komm SOSI_varchar(4), fylkesnr SOSI_int16
akvakultur.akvakulturpunkt (writer SOSI_1)
    attributes: objtype SOSI_varchar(32), L:akva_art{}.art SOSI_varchar(80), akva_enhet SOSI_varchar(80), akva_kapasitet SOSI_real32, av_class SOSI_varchar(80), firma SOSI_varchar(80), fiske_bedr_eier SOSI_varchar(80), adresse SOSI_varchar(80), postnr SOSI_int32, postadresse SOSI_varchar(80), telefonnr SOSI_int32, kontaktperson SOSI_varchar(80), plassering SOSI_varchar(80), L:akvatillatelsesinformasjon{}.lok_nr SOSI_int32, L:akvatillatelsesinformasjon{}.lok_navn SOSI_varchar(80), L:akvatillatelsesinformasjon{}.fiskebruknummerkommune SOSI_varchar(80), L:akvatillatelsesinformasjon{}.akvatillatelsesnummer SOSI_int32, L:akvatillatelsesinformasjon{}.tillatelsesformaal SOSI_varchar(80), L:akvatillatelsesinformasjon{}.tillatelsesstatus SOSI_varchar(80), L:akvatillatelsesinformasjon{}.tillatelsestype SOSI_varchar(80), L:akvatillatelsesinformasjon{}.tillatelsesurl SOSI_varchar(255), vannmiljo SOSI_varchar(80), dataeier SOSI_varchar(80), kopidato SOSI_varchar(80), malemetode SOSI_int16, synbarhet SOSI_int16, noyaktighet SOSI_int16, komm SOSI_varchar(4), fylkesnr SOSI_int16

Bookmark: PostgreSQL in
akvakultur.firmaeier (reader POSTGRES_1)
    attributes: objid int4,PRIKEY, objtype varchar(32), firma varchar(80), fiske_bedr_eier varchar(80), adresse varchar(80), postnr int4, postadresse varchar(80), telefonnr int4, kontaktperson varchar(80), firmaeierfk int4,BTREE, kopidato date
    -> FeatureMerger_2 [input 2]
akvakultur.art (reader POSTGRES_1)
    attributes: objid int4,PRIKEY, art varchar(80), artfk int4,BTREE, kopidato date
    -> FeatureMerger [input 2]
akvakultur.akvatillatelsesinformasjon (reader POSTGRES_1)
    attributes: objid serial,PRIKEY, lok_navn varchar(80), lok_nr int4, tillatelsesformaal varchar(80), tillatelsesstatus varchar(80), tillatelsestype varchar(80), tillatelsesinformasjonfk int4,BTREE, fiskebruknummerfylke varchar(80), fiskebruknummerkommune varchar(80), akvatillatelsesnummer int4, tillatelsesurl varchar(255), kopidatp date
    -> FeatureMerger_3 [input 2]
akvakultur.miljoundersokelse (reader POSTGRES_1) [off]
    attributes: objid int4,PRIKEY, mudato date, miljoundersokelse_type varchar(80), loktilstand varchar(80), akvamiljoeundersoekelsefk int4,BTREE, kopidato date

FME custom transformer CreateClipper

Parameters:
- CLIPPERCOORDS = 253577 6650999 253577 6651246 253763 6651246 253763 6650999 253577 6650999   # Clipper Coordinate List
- CLIPPERCOORDSYS = EPSG:25833   # Clipper Coordinate System
- DESTCOORDSYS = "ESRIWKT|ETRS_1989_UTM_Zone_35N|PROJCS["ETRS_1989_UTM_Zone_35N",GEOGCS["GCS_ETRS_1989",DATUM["D_ETRS_1989",SPHEROID["GRS_1980",6378137.0,298.257222101]],PRIMEM["Greenwich",0.0],UNIT["Degree",0.0174532925199433]],PROJECTION["Transverse_Mercator"],PARAMETER["False_Easting",500000.0],PARAMETER["False_Northing",0.0],PARAMETER["Central_Meridian",27.0],PARAMETER["Scale_Factor",0.9996],PARAMETER["Latitude_Of_Origin",0.0],UNIT["Meter",1.0]]"   # Destination Coordinate System

Note: Creating geometry from / the Clipper coords
Creator
    GEOMTYPE = 2D Coordinate List
    COORDSYS = $(CLIPPERCOORDSYS)
    NUM = 1
    COORDS = $(CLIPPERCOORDS)
    CREATED -> BoundingBoxAccumulator
Note: Calculating the bounding / box (envelope) from the geometry
BoundingBoxAccumulator
    TOPFER_INDEX = No
    BOUNDING_BOX -> SpatialFilter [input 1]
    ORIGINAL -> SpatialFilter [input 2]
Note: If the geometry is equal to its / own bounding box - it is a rectangle!
SpatialFilter
    PASS_CRITERIA = Pass Against One Base
    BASE_TYPE = Single Base
    USE_BOUNDING_BOX = No
    MERGE_ATTRS = No
    PREDICATES = EQUALS
    CURVE_BOUNDARY_RULE_PARAM = Default Rule
    PREDATTR = _predicate
    PASSED -> Reprojector
    FAILED -> Reprojector_2
Note: If rectangle, reproject the / geometry to the destination / coordinate system
Reprojector
    STROKE_ARCS = Yes
    DEST = $(DESTCOORDSYS)
    RASTER_CELL_SIZE = Preserve Cells
    SOURCE = Read from feature
    INTERPOLATION_TYPE_NAME = Nearest Neighbor
    REPROJECTED -> BoundingBoxAccumulator_2
Note: Then calculate the bounding / box from the projected geoemtry
BoundingBoxAccumulator_2
    TOPFER_INDEX = No
    BOUNDING_BOX -> Reprojector_3
Note: Reproject the geometry back to / the DB coordsys (LL/EUREF89)
Reprojector_3
    STROKE_ARCS = Yes
    DEST = EPSG:4258
    RASTER_CELL_SIZE = Preserve Cells
    SOURCE = Read from feature
    INTERPOLATION_TYPE_NAME = Nearest Neighbor
    REPROJECTED -> GeometryFilter
Note: Reproject clipper to / the DB coordsys (LL/EUREF89)
Reprojector_2
    STROKE_ARCS = Yes
    DEST = EPSG:4258
    RASTER_CELL_SIZE = Preserve Cells
    SOURCE = Read from feature
    INTERPOLATION_TYPE_NAME = Nearest Neighbor
    REPROJECTED -> GeometryFilter
Note: Getting rid of dummies
GeometryFilter
    BREAK_AGG = No
    GEOM_PORT_NAMES = Area
    AREA -> Output (output)
Output (output)

FME custom transformer SosiFilenameSetter

Parameters:
- OUTPUT_EPSG_CODE = 25832   # Destination coordinate system
- FANOUT = Kommuner   # Fanout områder
- UNDERTEMA =   # Undertema
- HOVEDTEMA =   # Hovedtema
- _CLIPPED = @Value(_clipped)   # Clipped
- _CLIPPER_FILE = @Value(_clipper_file)   # Clipper File
- _CLIPPERCOORDS = @Value(_clippercoords)   # Clippercoords
- _CREATION_INSTANCE = @Value(_creation_instance)   # Creation Instance
- _FNR = @Value(_fnr)   # Fnr
- _KNR = @Value(_knr)   # Knr
- AKVA_ENHET = @Value(akva_enhet)   # Akva Enhet
- AKVA_KAPASITET = @Value(akva_kapasitet)   # Akva Kapasitet
- AREAL_M2 = @Value(areal_m2)   # Areal M2
- AV_CLASS = @Value(av_class)   # Av Class
- AVGRENSNINGFK = @Value(avgrensningfk)   # avgrensningfk
- FYLKEID = @Value(fylkeid)   # fylkeid
- ID = @Value(id)   # id
- KOMMUNEID = @Value(kommuneid)   # kommuneid
- KOPIDATO = @Value(kopidato)   # kopidato
- NAVN = @Value(navn)   # navn
- OBJID = @Value(objid)   # objid
- OBJTYPE = @Value(objtype)   # objtype
- PLASSERING = @Value(plassering)   # plassering
- VANNMILJO = @Value(vannmiljo)   # vannmiljo
- PG_DB:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgdb').text
      
      return value
- PG_HOST:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pghost').text
      
      return value
- PG_PORT:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgport').text
      
      return value
- PG_PWD:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgpwd').text
      
      return value
- PG_USER:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pguser').text
      
      return value

Input (input)
    -> ParameterFetcher
ParameterFetcher
    ATTR_LIST = _output_epsg_code {$(OUTPUT_EPSG_CODE)} _fanout {$(FANOUT)}
    -> AttributeValueMapper
Note: Fikser kjente feil i kommunenummer
AttributeValueMapper
    LUT = 1901,1903
    SRC = kommuneid
    VAL_ATTR = kommuneid
    DIRECTION = Forward (Source To Destination)
    DEFAULT_VALUE = @Value(kommuneid)
    -> TestFilter_2
TestFilter_2
    TEST_LIST = BOOL_OP,OR,COMPOSITE_TEST,<Unused>,TEST_CLAUSE,"TEST $(FANOUT) = Kommuner",Kommuner,BOOL_OP,OR,COMPOSITE_TEST,<Unused>,TEST_CLAUSE,"TEST $(FANOUT) = Fylker",Fylker
    DEFAULT_VALUE = Ufiltrert
    Kommuner -> Joiner
    Ufiltrert -> AttributeCreator_13
    Fylker -> Joiner_2
Joiner
    PREFETCH_EXHAUSTIVE = Yes
    POSTGIS_HOST = $(PG_HOST)
    TABLE = admingrense.kommuner
    ADDED_FIELDS = navn
    DATASET = $(PG_DB)
    JOIN_KEYS = kommuneid kommuneid
    POSTGIS_USER_NAME = $(PG_USER)
    FORMAT = POSTGIS
    POSTGIS_QUERY_FEATURE_TYPES_FOR_MERGE_FILTERS = Yes
    MATCH_RULE_DISPLAY = Must Match Exactly One (1:1)
    POSTGIS_PORT = $(PG_PORT)
    POSTGIS_PASSWORD = $(PG_PWD)
    CACHE_SIZE = 5000
    POSTGIS_USE_TRUE_POSTGIS_TYPES = yes
    POSTGIS_DISABLE_COLLECTION_SPLITTING = yes
    JOINED -> StringReplacer
Joiner_2
    PREFETCH_EXHAUSTIVE = Yes
    POSTGIS_HOST = $(PG_HOST)
    TABLE = admingrense.fylkeflate
    ADDED_FIELDS = navn
    DATASET = $(PG_DB)
    JOIN_KEYS = fylkeid fylkeid
    POSTGIS_USER_NAME = $(PG_USER)
    FORMAT = POSTGIS
    POSTGIS_QUERY_FEATURE_TYPES_FOR_MERGE_FILTERS = Yes
    MATCH_RULE_DISPLAY = Must Match Exactly One (1:1)
    POSTGIS_PORT = $(PG_PORT)
    POSTGIS_PASSWORD = $(PG_PWD)
    CACHE_SIZE = 5000
    POSTGIS_USE_TRUE_POSTGIS_TYPES = yes
    POSTGIS_DISABLE_COLLECTION_SPLITTING = yes
    JOINED -> StringReplacer
AttributeCreator_13
    ATTR_LIST = sosifile,"FME_CONDITIONAL:DEFAULT_VALUE'$(HOVEDTEMA)_$(OUTPUT_EPSG_CODE)_$(UNDERTEMA)_SOSI'BOOL_OP;OR;COMPOSITE_TEST;<Unused>;TEST $(FANOUT) LIKE Kommuner'$(HOVEDTEMA)_@PadLeft(@Value(kommuneid),4,0)_@Value(navn)_$(OUTPUT_EPSG_CODE)_$(UNDERTEMA)_SOSI'BOOL_OP;OR;COMPOSITE_TEST;<Unused>;TEST $(FANOUT) LIKE Fylker'$(HOVEDTEMA)_@PadLeft(@Value(fylkeid),2,0)_@Value(navn)_$(OUTPUT_EPSG_CODE)_$(UNDERTEMA)_SOSI'BOOL_OP;OR;COMPOSITE_TEST;<Unused>;TEST $(FANOUT) LIKE Norge'$(HOVEDTEMA)_Norge_$(OUTPUT_EPSG_CODE)_$(UNDERTEMA)_SOSI'FME_NUM_CONDITIONS4___"
    -> Output (output)
Output (output)

Bookmark: Substituerer ÆØÅ og mellomrom
StringReplacer
    FIND_TEXT = " "
    NO_MATCH = _FME_NO_OP_
    CASE = no
    SRC_ATTRS = navn
    REPLACE_TEXT = _
    REGEXP = no
    -> StringReplacer_2
StringReplacer_2
    FIND_TEXT = Æ
    NO_MATCH = _FME_NO_OP_
    CASE = yes
    SRC_ATTRS = navn
    REPLACE_TEXT = E
    REGEXP = no
    -> StringReplacer_3
StringReplacer_3
    FIND_TEXT = Ø
    NO_MATCH = _FME_NO_OP_
    CASE = yes
    SRC_ATTRS = navn
    REPLACE_TEXT = O
    REGEXP = no
    -> StringReplacer_4
StringReplacer_4
    FIND_TEXT = Å
    NO_MATCH = _FME_NO_OP_
    CASE = yes
    SRC_ATTRS = navn
    REPLACE_TEXT = A
    REGEXP = no
    -> StringReplacer_5
StringReplacer_5
    FIND_TEXT = æ
    NO_MATCH = _FME_NO_OP_
    CASE = yes
    SRC_ATTRS = navn
    REPLACE_TEXT = e
    REGEXP = no
    -> StringReplacer_6
StringReplacer_6
    FIND_TEXT = ø
    NO_MATCH = _FME_NO_OP_
    CASE = yes
    SRC_ATTRS = navn
    REPLACE_TEXT = o
    REGEXP = no
    -> StringReplacer_7
StringReplacer_7
    FIND_TEXT = å
    NO_MATCH = _FME_NO_OP_
    CASE = yes
    SRC_ATTRS = navn
    REPLACE_TEXT = a
    REGEXP = no
    -> AttributeCreator_13
