FME workspace Tilgjengelighet_postgis2sosi.fmw
# Copyright: (c) xgrimor 2015
# Licence: <your licence>
Shutdown Python:
      # -*- coding: utf-8 -*-
      #-------------------------------------------------------------------------------
      # Name:        zipfiles.py
      # Purpose:     Pakker filer i output folderen
      #
      # Author:      xsunknu
      #
      # Created:     18.09.2015
      # Copyright:   (c) xsunknu 2015
      # Licence:     <your licence>
      #-------------------------------------------------------------------------------

      import sys, os, zipfile, fme

      def zip(sosifile, zfile):
          from os.path import basename

          # Lager korresponderende zip-fil av SOSI-fil
          if os.path.isfile(zfile):
              os.remove(zfile)

          zf = zipfile.ZipFile(zfile, "w", zipfile.ZIP_DEFLATED)

          # Ønsker ikke full sti inn i ZIP-filen
          arcname = basename(sosifile)

          # ZIP-formatet støtter ikke non-ascii tegn
          # Erstatter AØÅæøå med ascii-tegn
          arcname = arcname.replace('\xc6', 'E')
          arcname = arcname.replace('\xd8', 'O')
          arcname = arcname.replace('\xc5', 'A')
          arcname = arcname.replace('\xe6', 'e')
          arcname = arcname.replace('\xf8', 'o')
          arcname = arcname.replace('\xe5', 'a')

          zf.write(sosifile, arcname)
          zf.close()
          os.remove(sosifile)

          return

      def main():

          # Kjøres ikke på FME Server, da FME Server selv sørger for pakkingen
          if not 'FME_SERVER_DEST_DIR' in fme.macroValues:
              if 'FANOUT_FOLDER' in fme.macroValues:
                  path = fme.macroValues['FANOUT_FOLDER']
                  for dirpath, dnames, fnames in os.walk(path):
                      for f in fnames:
                          if f.endswith(".sos"):
                              # Scanner gjennom alle SOSI-filer
                              sosifile = os.path.join(path, f)
                              zfile = os.path.splitext(sosifile)[0] + '.zip'
                              if os.path.isfile(zfile):

                                  # Korresponderende ZIP-fil finnes, sjekker timestamps
                                  sositstamp = os.stat(sosifile).st_mtime
                                  ziptstamp = os.stat(zfile).st_mtime

                                  if sositstamp > ziptstamp:
                                      # SOSI-fil er nyere enn ZIP-fila, ZIP-fila oppdateres
                                      # SOSI-fila slettes
                                      try:
                                          zip(sosifile, zfile)
                                      except:
                                          print 'Kunne ikke pakke: ' + sosifile
                                  else:
                                      # SOSI-fila er eldre enn ZIP-fila
                                      # SOSI-fila slettes
                                      try:
                                          os.remove(sosifile)
                                      except:
                                          print 'Kunne ikke slette: ' + sosifile
                              else:
                                  # ZIP-fila eksisterer ikke og lages
                                  # SOSI-fila slettes
                                  try:
                                      zip(sosifile, zfile)
                                  except:
                                      print 'Kunne ikke pakke: ' + sosifile


      if __name__ == '__main__':
          main()

Parameters:
- KNR =   # Kommune(r)
- FNR =   # Fylke(r)
- CLIPPERCOORDS =   # Clipper coordinates
- CLIPPER_EPSG_CODE =   # Clipper coordinate system
- CLIPPER_FILE =   # "" Clipper file (any format)
- OUTPUT_EPSG_CODE = 25833   # Destination coordinate system
- FANOUT =   # Fanout områder
- CONFIG_FILE:   # Python Script
      #-------------------------------------------------------------------------------
      # Name:        GetConfigFile
      # Purpose:
      #
      # Author:      xsunknu
      #
      # Created:     21.08.2015
      # Copyright:   (c) xsunknu 2015
      # Licence:     <your licence>
      #-------------------------------------------------------------------------------
      
      import os, fme
      
      fmwdir = fme.macroValues['FME_MF_DIR']
      fmwfile = fme.macroValues['FME_MF_NAME']
      
      fmwfile = os.path.join(fmwdir, fmwfile)
      configfile = os.path.splitext(fmwfile)[0] + '_config.xml'
      
      return configfile
- CLIPPERCOORDSYS:   # Python Script
      #-------------------------------------------------------------------------------
      # Name:        SetCoordinateSystem
      # Purpose:
      #
      # Author:      xsunknu
      #
      # Created:     21.08.2015
      # Copyright:   (c) xsunknu 2015
      # Licence:     <your licence>
      #-------------------------------------------------------------------------------
      
      import os, fme
      
      EPSGvalue = fme.macroValues['CLIPPER_EPSG_CODE']
      EPSGcode  = 'EPSG:' + EPSGvalue
      
      return EPSGcode
- DESTCOORDSYS:   # Python Script
      #-------------------------------------------------------------------------------
      # Name:        SetCoordinateSystem
      # Purpose:
      #
      # Author:      xsunknu
      #
      # Created:     21.08.2015
      # Copyright:   (c) xsunknu 2015
      # Licence:     <your licence>
      #-------------------------------------------------------------------------------
      
      import os, fme
      
      EPSGvalue = fme.macroValues['OUTPUT_EPSG_CODE']
      EPSGcode  = 'EPSG:' + EPSGvalue
      
      return EPSGcode
- SPATIAL_FILTER:   # Python Script
      #-------------------------------------------------------------------------------
      # Name:        SetSpatialFilter
      # Purpose:
      #
      # Author:      xsunknu
      #
      # Created:     21.08.2015
      # Copyright:   (c) xsunknu 2015
      # Licence:     <your licence>
      #-------------------------------------------------------------------------------
      
      import fme
      
      spatialfilter = 'Intersects'
      
      knr = fme.macroValues['KNR']
      fnr = fme.macroValues['FNR']
      coords = fme.macroValues['CLIPPERCOORDS']
      file = fme.macroValues['CLIPPER_FILE']
      
      if knr == '' and fnr == '' and coords == '' and file == '':
          spatialfilter = '<No Spatial Filter>'
      
      return spatialfilter
- FIXEDCLIPPERCOORDS:   # Python Script
      #-------------------------------------------------------------------------------
      # Name:        FixClipperCoords
      # Purpose:
      #
      # Author:      xsunknu
      #
      # Created:     21.08.2015
      # Copyright:   (c) xsunknu 2015
      # Licence:     <your licence>
      #-------------------------------------------------------------------------------
      
      import fme
      clippercoords = fme.macroValues['CLIPPERCOORDS']
      
      if clippercoords == '':
          clippercoords = '1 1'
      
      return clippercoords
- HOVEDTEMA = UniversellUtforming   # Hovedtema
- UNDERTEMA = Tilgjengelighet   # Undertema
- PG_DB:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgdb').text
      
      return value
- PG_HOST:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pghost').text
      
      return value
- PG_PORT:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgport').text
      
      return value
- PG_USER:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pguser').text
      
      return value
- PG_PWD:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgpwd').text
      
      return value
- MAPPINGFILE:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme, os
      from xml.etree import ElementTree as ET
      
      #Read XML config file
      configtree = ET.parse(fme.macroValues['CONFIG_FILE'])
      configdoc = configtree.getroot()
      
      value = os.path.join(fme.macroValues['FME_MF_DIR'], configdoc.find('mappingfile').text)
      
      return value
- SOSIDEF_FILE:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme, os
      from xml.etree import ElementTree as ET
      
      #Read XML config file
      configtree = ET.parse(fme.macroValues['CONFIG_FILE'])
      configdoc = configtree.getroot()
      
      value = os.path.join(fme.macroValues['FME_MF_DIR'], configdoc.find('sosideffile').text)
      
      return value
- FANOUT_FOLDER:   # Python Script
      #-------------------------------------------------------------------------------
      # Name:        GetConfigFile
      # Purpose:
      #
      # Author:      xsunknu
      #
      # Created:     21.08.2015
      # Copyright:   (c) xsunknu 2015
      # Licence:     <your licence>
      #-------------------------------------------------------------------------------
      
      import os, fme
      from xml.etree import ElementTree as ET
      
      if 'FME_SERVER_DEST_DIR' in fme.macroValues:
          value = fme.macroValues['FME_SERVER_DEST_DIR']
      else:
          #Read XML config file
          configtree = ET.parse(fme.macroValues['CONFIG_FILE'])
          configdoc = configtree.getroot()
          value = configdoc.find('destdir').text
      
      return value
- LOG_FILE:   # Python Script
      #-------------------------------------------------------------------------------
      # Name:        GetConfigFile
      # Purpose:
      #
      # Author:      xsunknu
      #
      # Created:     21.08.2015
      # Copyright:   (c) xsunknu 2015
      # Licence:     <your licence>
      #-------------------------------------------------------------------------------
      
      import os, uuid, fme
      
      fmwdir = fme.macroValues['FME_MF_DIR']
      fmwfile = fme.macroValues['FME_MF_NAME']
      
      logdir = os.path.join(fmwdir, 'log')
      if not os.path.isdir(logdir):
          os.mkdir(logdir)
      
      logfile = os.path.splitext(fmwfile)[0] + '_' + str(uuid.uuid1()).replace('-','') + '.log'
      logfile = os.path.join(logdir, logfile)
      
      return logfile

Readers:
- POSTGIS_1: POSTGIS from $(PG_DB)

Writers:
- SOSI_1: SOSI to D:\scratch\Tilgjengelighet.sos
- SOSI_2: SOSI to D:\scratch\Tilgjengelighet.sos

CreateClipper
    DESTCOORDSYS = $(DESTCOORDSYS)
    CLIPPERCOORDSYS = $(CLIPPERCOORDSYS)
    CLIPPERCOORDS = $(FIXEDCLIPPERCOORDS)
    -> Clipper [input 1]
    -> FeatureReader_3

Bookmark: Fylke and/or kommune clippers
admingrense.fylkeflate (reader POSTGIS_1)
    attributes: fylkeid int4, navn varchar(80)
    -> Tester
    -> AttributeCreator_8
AttributeCreator_8
    ATTR_LIST = _clippercoords,$(CLIPPERCOORDS),_clipper_file,$(CLIPPER_FILE),_fnr,$(FNR),_knr,$(KNR)
    -> Tester_4
Tester_4
    TEST_CLAUSE:
      TEST _clipper_file ATTRIBUTE_IS_EMPTY ""
      TEST _clippercoords ATTRIBUTE_IS_EMPTY ""
      TEST _fnr ATTRIBUTE_IS_EMPTY ""
      TEST _knr ATTRIBUTE_IS_EMPTY ""
    BOOL_OP = AND
    TEST_MODE = Automatic
    TEST_DESCRIPTION = ""
    PASSED -> Reprojector_2
Tester
    TEST_CLAUSE = TEST @Value(fylkeid) IN $(FNR)
    BOOL_OP = OR
    TEST_MODE = Automatic
    TEST_DESCRIPTION = ""
    PASSED -> Reprojector_2
admingrense.kommuneflate (reader POSTGIS_1)
    attributes: kommuneid int4, navn varchar(80)
    -> Tester_2
Tester_2
    TEST_CLAUSE = TEST @Value(kommuneid) IN $(KNR)
    BOOL_OP = OR
    TEST_MODE = Automatic
    TEST_DESCRIPTION = ""
    PASSED -> Reprojector_2
Note: Sender inn hele landet som initiator / dersom alle klippeparametrene er / blanke
Reprojector_2
    SOURCE = Read from feature
    INTERPOLATION_TYPE_NAME = Nearest Neighbor
    DEST = EPSG:4258
    RASTER_CELL_SIZE = Preserve Cells
    REPROJECTED -> Clipper [input 1]
    REPROJECTED -> Dissolver

Bookmark: Clipper file (any format)
Creator
    NUM = 1
    GEOMTYPE = Geometry Object
    CREATED -> FeatureReader
FeatureReader
    ATTR_ACCUM_MODE = Only Use Result
    ATTRIBUTES = NewFeatureType,
    DATASET = $(CLIPPER_FILE)
    FEATURETYPES_RADIO = FEATURETYPES
    GENERIC_REAL_FORMAT = GUESS_FROM_EXTENSION
    INTERACT = $(SPATIAL_FILTER)
    COMBINE_GEOM = Use Result
    FORMAT = GENERIC
    OUTPUT_FEATURES_DISPLAY = Based on Connections
    <OTHER> -> Reprojector_3
Reprojector_3
    SOURCE = Read from feature
    INTERPOLATION_TYPE_NAME = Nearest Neighbor
    DEST = EPSG:4258
    RASTER_CELL_SIZE = Preserve Cells
    REPROJECTED -> Clipper [input 1]
    REPROJECTED -> Dissolver

Bookmark: Leser features
Dissolver
    NO_OVRLP = No
    ACCUM_INPUT_ATTRS = No
    AREA -> FeatureReader_3
FeatureReader_3
    FORMAT = POSTGIS
    POSTGIS_USER_NAME = $(PG_USER)
    POSTGIS_CLIP_TO_ENVELOPE = NO
    POSTGIS_PASSWORD = $(PG_PWD)
    FEATURETYPES = uufriluftsomrader.uufriluftbaderampe uufriluftsomrader.uufriluftfiskeplass uufriluftsomrader.uufriluftfriluftsomrade uufriluftsomrader.uufriluftgapahuk uufriluftsomrader.uufriluftgrillbalplass uufriluftsomrader.uufrilufthcparkering uufriluftsomrader.uufriluftparkeringsomrade uufriluftsomrader.uufriluftsittegruppe uufriluftsomrader.uufrilufttoalett uufriluftsomrader.uufriluftturvei uutettsted.uutettstedhcparkering uutettsted.uutettstedinngangbygg uutettsted.uutettstedparkeringsomrade uutettsted.uutettstedvei uufriluftsomrader.uufrilufthyttertilrettelagt uufriluftsomrader.uufriluftstatligsikrafriluftsomrader
    POSTGIS_QUERY_FEATURE_TYPES_FOR_MERGE_FILTERS = Yes
    OUTPUT_FEATURES_DISPLAY = Based on Connections
    ATTRIBUTES = uufriluftsomrader.uufriluftbaderampe,"objid,objtype,rampe,rampebredde,rampestigning,handlist,handlisthoyde1,handlisthoyde2,rampeterskel,rampetilgjengelig,tilgjengvurderingrullestol,tilgjengvurderingsyn,ogcfid,opphav,kommune,bilde,registrert,oppdatert,kommentar,forbedringsforslag",uufriluftsomrader.uufriluftfiskeplass,"objid,objtype,flytebrygge,rampe,rampebredde,rampestigning,handlist,handlisthoyde1,handlisthoyde2,rampeterskel,rampetilgjengelig,dekke,plankeavstand,dekketilstand,diametersnusirkel,rekkverk,stoppkant,stoppkanthoyde,tilgjengvurderingrullestol,tilgjengvurderingelrullestol,tilgjengvurderingsyn,ogcfid,opphav,kommune,bilde,registrert,oppdatert,kommentar,forbedringsforslag",uufriluftsomrader.uufriluftfriluftsomrade,"objid,objtype,navn,naturbasenr,parkeringsomrade,hcparkeringsplass,toalett,turvei,baderampe,fiskeplass,grillbalplass,sittegruppe,gapahuk,informasjon,annen,ogcfid,opphav,kommune,bilde,registrert,oppdatert,kommentar,forbedringsforslag",uufriluftsomrader.uufriluftgapahuk,"objid,objtype,rampe,rampebredde,rampestigning,handlist,handlisthoyde1,handlisthoyde2,rampeterskel,rampetilgjengelig,breddeinngang,hoydeinngang,terskelhoyde,kontrastinngang,diametersnusirkel,dekke,dekketilstand,tilgjengvurderingrullestol,tilgjengvurderingelrullestol,tilgjengvurderingsyn,ogcfid,opphav,kommune,bilde,registrert,oppdatert,kommentar,forbedringsforslag",uufriluftsomrader.uufriluftgrillbalplass,"objid,objtype,dekke,dekketilstand,helning,tilgjengvurderingrullestol,ogcfid,opphav,kommune,bilde,registrert,oppdatert,kommentar,forbedringsforslag",uufriluftsomrader.uufrilufthcparkering,"objid,objtype,skiltet,merket,bredde,lengde,avstandfasilitet,avgift,automathoyde,tilgjengeligautomat,tilgjengvurderingrullestol,tilgjengvurderingelrullestol,ogcfid,opphav,kommune,bilde,registrert,oppdatert,kommentar,forbedringsforslag",uufriluftsomrader.uufrilufthyttertilrettelagt,"objid,objtype,eier,lenke,navn,tilrettelagt,ogcfid,opphav,kommune,bilde,registrert,oppdatert,kommentar,forbedringsforslag",uufriluftsomrader.uufriluftparkeringsomrade,"objid,objtype,kapasitetpersonbiler,kapasitetuu,arstidsbruk,dekke,dekketilstand,tilgjengvurderingrullestol,tilgjengvurderingelrullestol,ogcfid,opphav,kommune,bilde,registrert,oppdatert,kommentar,forbedringsforslag",uufriluftsomrader.uufriluftsittegruppe,"objid,objtype,dekke,dekketilstand,helning,hoydebord,utstikkbord,tilgjengvurderingrullestol,ogcfid,opphav,kommune,bilde,registrert,oppdatert,kommentar,forbedringsforslag",uufriluftsomrader.uufriluftstatligsikrafriluftsomrader,"objid,objtype,linkbilde,linkskjema,naturbasenr,navn,ogcfid,opphav,kommune,bilde,registrert,oppdatert,kommentar,forbedringsforslag",uufriluftsomrader.uufrilufttoalett,"objid,objtype,byggtype,rampe,rampebredde,rampestigning,handlist,handlisthoyde1,handlisthoyde2,rampeterskel,rampetilgjengelighet,avstandhc,dortype,dorapner,manoverknapphoyde,breddeinngang,kontrastinngang,terskelhoyde,diametersnusirkel,belysning,omkledningtilgjengelig,servanttilgjengelig,wctilgjengelig,tilgjengvurderingrullestol,tilgjengvurderingelrullestol,tilgjengvurderingsyn,ogcfid,opphav,kommune,bilde,registrert,oppdatert,kommentar,forbedringsforslag",uufriluftsomrader.uufriluftturvei,"objid,objtype,veitype,spesialfotrutetype,arstidsbruk,sperrebom,sperrebomtilgjengelig,dekke,dekketilstand,motehvileplass,antalltilstrekkelig,belysning,bredde,stigning,tverrfall,frihoyde,ledelinje,ledelinjekontrast,tilgjengvurderingrullestol,tilgjengvurderingelrullestol,tilgjengvurderingsyn,ogcfid,opphav,kommune,bilde,registrert,oppdatert,kommentar,forbedringsforslag",uutettsted.uutettstedhcparkering,"objid,objtype,overbygg,varmekabel,skiltet,merket,bredde,lengde,avstandservicebygg,avgift,automathoyde,tilgjengeligautomat,tilgjengvurderingrullestol,tilgjengvurderingelrullestol,ogcfid,kommune,opphav,registrert,oppdatert,byggingpagar,bilde,kommentar",uutettsted.uutettstedinngangbygg,"objid,objtype,byggfunksjon,avstandvanligparkering,avstandhc,rampe,rampebredde,rampestigning,handlist,handlisthoyde1,handlisthoyde2,rampeterskel,rampetilgjengelig,dortype,dorapner,manoverknapphoyde,inngangbredde,terskelhoyde,ringeklokke,ringeklokkehoyde,stigningadkomstvei,kontrast,tilgjengvurderingrullestol,tilgjengvurderingelrullestol,tilgjengvurderingsyn,ogcfid,kommune,opphav,registrert,oppdatert,byggingpagar,bilde,kommentar",uutettsted.uutettstedparkeringsomrade,"objid,objtype,kapasitetpersonbiler,kapasitetuu,eierforhold,arstidsbruk,overbygg,varmekabel,dekke,dekketilstand,tilgjengvurderingrullestol,tilgjengvurderingelrullestol,ogcfid,kommune,opphav,registrert,oppdatert,byggingpagar,bilde,kommentar",uutettsted.uutettstedvei,"objid,objtype,gatetype,dekke,dekketilstand,bredde,nedsenk1,nedsenk2,stigning,tverrfall,moteplass,varmekabel,lyssignal,lydsignal,ledelinje,ledelinjekontrast,tilgjengvurderingrullestol,tilgjengvurderingelrullestol,tilgjengvurderingsyn,ogcfid,kommune,opphav,registrert,oppdatert,byggingpagar,bilde,kommentar"
    FEATURETYPES_RADIO = FEATURETYPES
    POSTGIS_SCHEMALIST = uufriluftsomrader uutettsted
    POSTGIS_DISABLE_COLLECTION_SPLITTING = yes
    POSTGIS_PORT = $(PG_PORT)
    COMBINE_GEOM = Use Result
    POSTGIS_USE_TRUE_POSTGIS_TYPES = yes
    INTERACT = Intersects
    POSTGIS_USE_SEARCH_ENVELOPE = NO
    ATTR_ACCUM_MODE = Only Use Result
    DATASET = $(PG_DB)
    POSTGIS_HOST = $(PG_HOST)
    uufriluftsomrader.uufriluftbaderampe -> AttributeCreator_12
    uufriluftsomrader.uufriluftfiskeplass -> AttributeCreator_12
    uufriluftsomrader.uufriluftfriluftsomrade -> AttributeCreator_12
    uufriluftsomrader.uufriluftgapahuk -> AttributeCreator_12
    uufriluftsomrader.uufriluftgrillbalplass -> AttributeCreator_12
    uufriluftsomrader.uufrilufthcparkering -> AttributeCreator_12
    uufriluftsomrader.uufriluftparkeringsomrade -> AttributeCreator_12
    uufriluftsomrader.uufriluftsittegruppe -> AttributeCreator_12
    uufriluftsomrader.uufrilufttoalett -> AttributeCreator_12
    uufriluftsomrader.uufriluftturvei -> AttributeCreator_12
    uutettsted.uutettstedhcparkering -> AttributeCreator_12
    uutettsted.uutettstedinngangbygg -> AttributeCreator_12
    uutettsted.uutettstedparkeringsomrade -> AttributeCreator_12
    uutettsted.uutettstedvei -> AttributeCreator_12
    uufriluftsomrader.uufrilufthyttertilrettelagt -> AttributeCreator_12
    uufriluftsomrader.uufriluftstatligsikrafriluftsomrader -> AttributeCreator_12
AttributeCreator_12
    ATTR_LIST = _clippercoords,$(CLIPPERCOORDS),_clipper_file,$(CLIPPER_FILE),_fnr,$(FNR),_knr,$(KNR)
    -> TestFilter
TestFilter
    TEST_LIST:
      BOOL_OP,AND,COMPOSITE_TEST,<Unused>,TEST_CLAUSE,"TEST _clipper_file ATTRIBUTE_IS_EMPTY """"
      TEST _clippercoords ATTRIBUTE_IS_EMPTY """"
      TEST _fnr ATTRIBUTE_IS_EMPTY """"
      TEST _knr ATTRIBUTE_IS_EMPTY """"",Landsdekkende,BOOL_OP,AND,COMPOSITE_TEST,<Unused>,TEST_CLAUSE,"TEST _clipper_file ATTRIBUTE_IS_EMPTY """"
      TEST _clippercoords ATTRIBUTE_IS_EMPTY """"
      TEST _fnr NOT_ATTRIBUTE_IS_EMPTY """"
      TEST _knr ATTRIBUTE_IS_EMPTY """"",Fylkesvis,BOOL_OP,AND,COMPOSITE_TEST,<Unused>,TEST_CLAUSE,"TEST _clipper_file ATTRIBUTE_IS_EMPTY """"
      TEST _clippercoords ATTRIBUTE_IS_EMPTY """"
      TEST _fnr ATTRIBUTE_IS_EMPTY """"
      TEST _knr NOT_ATTRIBUTE_IS_EMPTY """"",Kommunevis
    DEFAULT_VALUE = <UNFILTERED>
    Fylkesvis -> Clipper [input 2]
    Kommunevis -> Clipper [input 2]
    <UNFILTERED> -> Clipper [input 2]
    Landsdekkende -> SosiFilenameSetter

Bookmark: Klipper
Clipper
    CREATE_AGGREGATES = No
    PRESERVE_CLIPPEE_EXTENTS = No
    ATTR_ACCUM_MODE = Merge Clipper
    CLIP_TYPE = Multiple Clippers
    BOUNDARY_CASES = Treat as Inside
    ATTR_CONFLICT_RES = Use Clippee
    CLIPPED_ATTR = _clipped
    INSIDE -> SosiFilenameSetter

Bookmark: Tagger og reprojiserer
SosiFilenameSetter
    BREDDEINNGANG = @Value(breddeinngang)
    AVSTANDHC = @Value(avstandhc)
    NAVN = @Value(navn)
    FRIHOYDE = @Value(frihoyde)
    VARMEKABEL = @Value(varmekabel)
    GATETYPE = @Value(gatetype)
    BELYSNING = @Value(belysning)
    HOYDEBORD = @Value(hoydebord)
    BYGGFUNKSJON = @Value(byggfunksjon)
    SERVANTTILGJENGELIG = @Value(servanttilgjengelig)
    KAPASITETUU = @Value(kapasitetuu)
    AVSTANDVANLIGPARKERING = @Value(avstandvanligparkering)
    SPERREBOMTILGJENGELIG = @Value(sperrebomtilgjengelig)
    DIAMETERSNUSIRKEL = @Value(diametersnusirkel)
    DEKKE = @Value(dekke)
    DEKKETILSTAND = @Value(dekketilstand)
    MERKET = @Value(merket)
    RAMPEBREDDE = @Value(rampebredde)
    ANNEN = @Value(annen)
    LYSSIGNAL = @Value(lyssignal)
    TURVEI = @Value(turvei)
    RINGEKLOKKE = @Value(ringeklokke)
    NATURBASENR = @Value(naturbasenr)
    OPPHAV = @Value(opphav)
    KAPASITETPERSONBILER = @Value(kapasitetpersonbiler)
    PLANKEAVSTAND = @Value(plankeavstand)
    RAMPE = @Value(rampe)
    VEITYPE = @Value(veitype)
    REKKVERK = @Value(rekkverk)
    PG_PWD:
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------

      import fme
      from xml.etree import ElementTree as ET

      #Read XML config file
      configtree = ET.parse(fme.macroValues['CONFIG_FILE'])
      configdoc = configtree.getroot()
      value = configdoc.find('pgpwd').text

      return value
    AUTOMATHOYDE = @Value(automathoyde)
    HANDLIST = @Value(handlist)
    HELNING = @Value(helning)
    FISKEPLASS = @Value(fiskeplass)
    STOPPKANT = @Value(stoppkant)
    PG_DB:
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------

      import fme
      from xml.etree import ElementTree as ET

      #Read XML config file
      configtree = ET.parse(fme.macroValues['CONFIG_FILE'])
      configdoc = configtree.getroot()
      value = configdoc.find('pgdb').text

      return value
    MOTEPLASS = @Value(moteplass)
    TILGJENGVURDERINGELRULLESTOL = @Value(tilgjengvurderingelrullestol)
    HCPARKERINGSPLASS = @Value(hcparkeringsplass)
    STIGNINGADKOMSTVEI = @Value(stigningadkomstvei)
    HOVEDTEMA = $(HOVEDTEMA)
    OVERBYGG = @Value(overbygg)
    _CLIPPERCOORDS = @Value(_clippercoords)
    TILGJENGELIGAUTOMAT = @Value(tilgjengeligautomat)
    LEDELINJEKONTRAST = @Value(ledelinjekontrast)
    GRILLBALPLASS = @Value(grillbalplass)
    TILGJENGVURDERINGSYN = @Value(tilgjengvurderingsyn)
    TILGJENGVURDERINGRULLESTOL = @Value(tilgjengvurderingrullestol)
    _CREATION_INSTANCE = @Value(_creation_instance)
    HANDLISTHOYDE1 = @Value(handlisthoyde1)
    PG_HOST:
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------

      import fme
      from xml.etree import ElementTree as ET

      #Read XML config file
      configtree = ET.parse(fme.macroValues['CONFIG_FILE'])
      configdoc = configtree.getroot()
      value = configdoc.find('pghost').text

      return value
    HANDLISTHOYDE2 = @Value(handlisthoyde2)
    _KNR = @Value(_knr)
    AVSTANDSERVICEBYGG = @Value(avstandservicebygg)
    EIERFORHOLD = @Value(eierforhold)
    DORTYPE = @Value(dortype)
    MOTEHVILEPLASS = @Value(motehvileplass)
    RINGEKLOKKEHOYDE = @Value(ringeklokkehoyde)
    STOPPKANTHOYDE = @Value(stoppkanthoyde)
    KOMMENTAR = @Value(kommentar)
    BYGGINGPAGAR = @Value(byggingpagar)
    SPERREBOM = @Value(sperrebom)
    FANOUT = $(FANOUT)
    FLYTEBRYGGE = @Value(flytebrygge)
    RAMPETERSKEL = @Value(rampeterskel)
    PG_PORT:
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------

      import fme
      from xml.etree import ElementTree as ET

      #Read XML config file
      configtree = ET.parse(fme.macroValues['CONFIG_FILE'])
      configdoc = configtree.getroot()
      value = configdoc.find('pgport').text

      return value
    OBJTYPE = @Value(objtype)
    SPESIALFOTRUTETYPE = @Value(spesialfotrutetype)
    FORBEDRINGSFORSLAG = @Value(forbedringsforslag)
    KONTRASTINNGANG = @Value(kontrastinngang)
    OMKLEDNINGTILGJENGELIG = @Value(omkledningtilgjengelig)
    GAPAHUK = @Value(gapahuk)
    DORAPNER = @Value(dorapner)
    RAMPETILGJENGELIG = @Value(rampetilgjengelig)
    OBJID = @Value(objid)
    RAMPETILGJENGELIGHET = @Value(rampetilgjengelighet)
    TERSKELHOYDE = @Value(terskelhoyde)
    LENGDE = @Value(lengde)
    ANTALLTILSTREKKELIG = @Value(antalltilstrekkelig)
    LEDELINJE = @Value(ledelinje)
    BREDDE = @Value(bredde)
    SKILTET = @Value(skiltet)
    WCTILGJENGELIG = @Value(wctilgjengelig)
    BADERAMPE = @Value(baderampe)
    OUTPUT_EPSG_CODE = $(OUTPUT_EPSG_CODE)
    INNGANGBREDDE = @Value(inngangbredde)
    KOMMUNEID = @Value(kommuneid)
    AVGIFT = @Value(avgift)
    FYLKEID = @Value(fylkeid)
    OPPDATERT = @Value(oppdatert)
    KONTRAST = @Value(kontrast)
    _CLIPPER_FILE = @Value(_clipper_file)
    TOALETT = @Value(toalett)
    UTSTIKKBORD = @Value(utstikkbord)
    MANOVERKNAPPHOYDE = @Value(manoverknapphoyde)
    ARSTIDSBRUK = @Value(arstidsbruk)
    RAMPESTIGNING = @Value(rampestigning)
    _FNR = @Value(_fnr)
    NEDSENK1 = @Value(nedsenk1)
    NEDSENK2 = @Value(nedsenk2)
    _CLIPPED = @Value(_clipped)
    PG_USER:
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------

      import fme
      from xml.etree import ElementTree as ET

      #Read XML config file
      configtree = ET.parse(fme.macroValues['CONFIG_FILE'])
      configdoc = configtree.getroot()
      value = configdoc.find('pguser').text

      return value
    AVSTANDFASILITET = @Value(avstandfasilitet)
    PARKERINGSOMRADE = @Value(parkeringsomrade)
    UNDERTEMA = $(UNDERTEMA)
    BILDE = @Value(bilde)
    REGISTRERT = @Value(registrert)
    HOYDEINNGANG = @Value(hoydeinngang)
    TVERRFALL = @Value(tverrfall)
    INFORMASJON = @Value(informasjon)
    OGCFID = @Value(ogcfid)
    STIGNING = @Value(stigning)
    BYGGTYPE = @Value(byggtype)
    KOMMUNE = @Value(kommune)
    LYDSIGNAL = @Value(lydsignal)
    SITTEGRUPPE = @Value(sittegruppe)
    -> Reprojector
Reprojector
    SOURCE = Read from feature
    INTERPOLATION_TYPE_NAME = Nearest Neighbor
    DEST = $(DESTCOORDSYS)
    RASTER_CELL_SIZE = Preserve Cells
    REPROJECTED -> AttributeCreator
AttributeCreator
    ATTR_LIST = OBJTYPE,@Value(objtype)
    -> FeatureTypeFilter
FeatureTypeFilter
    ATTRIBUTES = uufriluftsomrader.uufriluftbaderampe,uufriluftsomrader.uufriluftfiskeplass,uufriluftsomrader.uufriluftfriluftsomrade,uufriluftsomrader.uufriluftgapahuk,uufriluftsomrader.uufriluftgrillbalplass,uufriluftsomrader.uufrilufthcparkering,uufriluftsomrader.uufriluftparkeringsomrade,uufriluftsomrader.uufriluftsittegruppe,uufriluftsomrader.uufrilufttoalett,uufriluftsomrader.uufriluftturvei,uufriluftsomrader.uufrilufthyttertilrettelagt,uufriluftsomrader.uufriluftstatligsikrafriluftsomrader,uutettsted.uutettstedhcparkering,uutettsted.uutettstedinngangbygg,uutettsted.uutettstedparkeringsomrade,uutettsted.uutettstedvei,<BLANK>,<UNFILTERED>
    uufriluftsomrader.uufriluftfiskeplass -> AttributeCreator_3
    uufriluftsomrader.uufriluftfriluftsomrade -> AttributeCreator_4
    uufriluftsomrader.uufriluftbaderampe -> AttributeCreator_2
    uufriluftsomrader.uufriluftgapahuk -> AttributeCreator_6
    uufriluftsomrader.uufriluftgrillbalplass -> AttributeCreator_7
    uufriluftsomrader.uufrilufthcparkering -> AttributeCreator_9
    uufriluftsomrader.uufriluftparkeringsomrade -> AttributeCreator_10
    uufriluftsomrader.uufriluftsittegruppe -> AttributeCreator_13
    uufriluftsomrader.uufrilufttoalett -> AttributeCreator_14
    uufriluftsomrader.uufriluftturvei -> AttributeCreator_15
    uutettsted.uutettstedhcparkering -> AttributeCreator_16
    uutettsted.uutettstedinngangbygg -> AttributeCreator_17
    uutettsted.uutettstedparkeringsomrade -> AttributeCreator_18
    uutettsted.uutettstedvei -> AttributeCreator_20
    uufriluftsomrader.uufrilufthyttertilrettelagt -> AttributeCreator_21
    uufriluftsomrader.uufriluftstatligsikrafriluftsomrader -> AttributeCreator_22

Bookmark: SOSI-tuner data
AttributeCreator_2
    ATTR_LIST = kommune,@PadLeft(@Value(kommune), 4,  0)
    -> uufriluftsomrader.uufriluftbaderampe (writer SOSI_1)
AttributeCreator_3
    ATTR_LIST = kommune,@PadLeft(@Value(kommune), 4,  0)
    -> uufriluftsomrader.uufriluftfiskeplass (writer SOSI_1)
AttributeCreator_4
    ATTR_LIST = kommune,@PadLeft(@Value(kommune), 4,  0)
    -> uufriluftsomrader.uufriluftfriluftsomrade (writer SOSI_1)
    -> DonutHoleExtractor_2
DonutHoleExtractor_2
    OUTERSHELL -> GeometryCoercer
    HOLE -> GeometryCoercer
GeometryCoercer
    GQUERY:
      for $geom in //geometry
      where $geom/count(parent::geometry) = 0
      return number($geom/@fme_id)
    KIND = fme_line
    COERCED -> AttributeCreator_5
AttributeCreator_5
    ATTR_LIST = OBJTYPE,UUFriluftFriluftsområdeGrense
    -> uufriluftsomrader.uufriluftfriluftsomradegrense (writer SOSI_1)
AttributeCreator_6
    ATTR_LIST = kommune,@PadLeft(@Value(kommune), 4,  0)
    -> uufriluftsomrader.uufriluftgapahuk (writer SOSI_1)
AttributeCreator_7
    ATTR_LIST = kommune,@PadLeft(@Value(kommune), 4,  0)
    -> uufriluftsomrader.uufriluftgrillbalplass (writer SOSI_1)
AttributeCreator_9
    ATTR_LIST = kommune,@PadLeft(@Value(kommune), 4,  0)
    -> uufriluftsomrader.uufrilufthcparkering (writer SOSI_1)
AttributeCreator_10
    ATTR_LIST = kommune,@PadLeft(@Value(kommune), 4,  0)
    -> uufriluftsomrader.uufriluftparkeringsomrade (writer SOSI_1)
    -> DonutHoleExtractor_3
DonutHoleExtractor_3
    OUTERSHELL -> GeometryCoercer_2
    HOLE -> GeometryCoercer_2
GeometryCoercer_2
    GQUERY:
      for $geom in //geometry
      where $geom/count(parent::geometry) = 0
      return number($geom/@fme_id)
    KIND = fme_line
    COERCED -> AttributeCreator_11
AttributeCreator_11
    ATTR_LIST = OBJTYPE,UUFriluftParkeringsområdeGrense
    -> uufriluftsomrader.uufriluftparkeringsomradegrense (writer SOSI_1)
AttributeCreator_13
    ATTR_LIST = kommune,@PadLeft(@Value(kommune), 4,  0)
    -> uufriluftsomrader.uufriluftsittegruppe (writer SOSI_1)
AttributeCreator_14
    ATTR_LIST = kommune,@PadLeft(@Value(kommune), 4,  0)
    -> uufriluftsomrader.uufrilufttoalett (writer SOSI_1)
AttributeCreator_15
    ATTR_LIST = kommune,@PadLeft(@Value(kommune), 4,  0)
    -> uufriluftsomrader.uufriluftturvei (writer SOSI_1)
AttributeCreator_21
    ATTR_LIST = kommune,"FME_CONDITIONAL:DEFAULT_VALUE'@PadLeft(@Value(kommune), 4,  0)'BOOL_OP;OR;COMPOSITE_TEST;<Unused>;TEST kommune ATTRIBUTE_VALUE_NULL _FME_BLANK_STRING_;TEST kommune ATTRIBUTE_IS_EMPTY _FME_BLANK_STRING_;TEST kommune ATTRIBUTE_IS_MISSING _FME_BLANK_STRING_'FME_NULL_VALUE'FME_NUM_CONDITIONS2___"
    -> uufriluftsomrader.uufrilufthyttertilrettelagt (writer SOSI_1)
AttributeCreator_22
    ATTR_LIST = kommune,"FME_CONDITIONAL:DEFAULT_VALUE'@PadLeft(@Value(kommune), 4,  0)'BOOL_OP;OR;COMPOSITE_TEST;<Unused>;TEST kommune ATTRIBUTE_VALUE_NULL _FME_BLANK_STRING_;TEST kommune ATTRIBUTE_IS_EMPTY _FME_BLANK_STRING_;TEST kommune ATTRIBUTE_IS_MISSING _FME_BLANK_STRING_'FME_NULL_VALUE'FME_NUM_CONDITIONS2___"
    -> uufriluftsomrader.uufriluftstatligsikrafriluftsomrader (writer SOSI_1)
    -> DonutHoleExtractor
DonutHoleExtractor
    OUTERSHELL -> GeometryCoercer_4
    HOLE -> GeometryCoercer_4
GeometryCoercer_4
    GQUERY:
      for $geom in //geometry
      where $geom/count(parent::geometry) = 0
      return number($geom/@fme_id)
    KIND = fme_line
    COERCED -> AttributeCreator_23
    UNTOUCHED -> AttributeCreator_23
AttributeCreator_23
    ATTR_LIST = OBJTYPE,UUFriluftStatligSikraFriluftsområderGrense
    -> uufriluftsomrader.uufriluftstatligsikrafriluftsomradergrense (writer SOSI_1)
AttributeCreator_16
    ATTR_LIST = kommune,@PadLeft(@Value(kommune), 4,  0)
    -> uutettsted.uutettstedhcparkering (writer SOSI_2)
AttributeCreator_17
    ATTR_LIST = kommune,@PadLeft(@Value(kommune), 4,  0)
    -> uutettsted.uutettstedinngangbygg (writer SOSI_2)
AttributeCreator_18
    ATTR_LIST = kommune,@PadLeft(@Value(kommune), 4,  0)
    -> uutettsted.uutettstedparkeringsomrade (writer SOSI_2)
    -> GeometryCoercer_3
GeometryCoercer_3
    GQUERY:
      for $geom in //geometry
      where $geom/count(parent::geometry) = 0
      return number($geom/@fme_id)
    KIND = fme_line
    COERCED -> AttributeCreator_19
AttributeCreator_19
    ATTR_LIST = OBJTYPE,UUTettstedParkeringsområdeGrense
    -> uutettsted.uutettstedparkeringsomradegrense (writer SOSI_2)
AttributeCreator_20
    ATTR_LIST = kommune,@PadLeft(@Value(kommune), 4,  0)
    -> uutettsted.uutettstedvei (writer SOSI_2)

Bookmark: SOSI UUFriluftsOmråde
uufriluftsomrader.uufriluftbaderampe (writer SOSI_1)
    attributes: rampe SOSI_varchar(80), rampebredde SOSI_int32, rampestigning SOSI_real64, handlist SOSI_varchar(80), handlisthoyde1 SOSI_int32, handlisthoyde2 SOSI_int32, rampeterskel SOSI_real64, rampetilgjengelig SOSI_varchar(80), tilgjengvurderingrullestol SOSI_varchar(80), tilgjengvurderingsyn SOSI_varchar(80), ogcfid SOSI_int32, opphav SOSI_varchar(80), kommune SOSI_varchar(80), bilde SOSI_varchar(20), registrert SOSI_datetime, oppdatert SOSI_datetime, kommentar SOSI_varchar(500), forbedringsforslag SOSI_varchar(500)
uufriluftsomrader.uufriluftfiskeplass (writer SOSI_1)
    attributes: flytebrygge SOSI_varchar(80), rampe SOSI_varchar(80), rampebredde SOSI_int32, rampestigning SOSI_real64, handlist SOSI_varchar(80), handlisthoyde1 SOSI_int32, handlisthoyde2 SOSI_int32, rampeterskel SOSI_real64, rampetilgjengelig SOSI_varchar(80), dekke SOSI_varchar(80), plankeavstand SOSI_real64, dekketilstand SOSI_varchar(80), diametersnusirkel SOSI_int32, rekkverk SOSI_varchar(80), stoppkant SOSI_varchar(80), stoppkanthoyde SOSI_real64, tilgjengvurderingrullestol SOSI_varchar(80), tilgjengvurderingelrullestol SOSI_varchar(80), tilgjengvurderingsyn SOSI_varchar(80), ogcfid SOSI_int32, opphav SOSI_varchar(80), kommune SOSI_varchar(80), bilde SOSI_varchar(80), registrert SOSI_datetime, oppdatert SOSI_datetime, kommentar SOSI_varchar(500), forbedringsforslag SOSI_varchar(500)
uufriluftsomrader.uufriluftfriluftsomradegrense (writer SOSI_1)
uufriluftsomrader.uufriluftfriluftsomrade (writer SOSI_1)
    attributes: navn SOSI_varchar(80), naturbasenr SOSI_int32, parkeringsomrade SOSI_varchar(80), hcparkeringsplass SOSI_varchar(80), toalett SOSI_varchar(80), turvei SOSI_varchar(80), baderampe SOSI_varchar(80), fiskeplass SOSI_varchar(80), grillbalplass SOSI_varchar(80), sittegruppe SOSI_varchar(80), gapahuk SOSI_varchar(80), informasjon SOSI_varchar(80), annen SOSI_varchar(80), ogcfid SOSI_int32, opphav SOSI_varchar(80), kommune SOSI_varchar(80), bilde SOSI_varchar(80), registrert SOSI_datetime, oppdatert SOSI_datetime, kommentar SOSI_varchar(500), forbedringsforslag SOSI_varchar(500)
uufriluftsomrader.uufriluftgapahuk (writer SOSI_1)
    attributes: rampe SOSI_varchar(80), rampebredde SOSI_int32, rampestigning SOSI_real64, handlist SOSI_varchar(80), handlisthoyde1 SOSI_int32, handlisthoyde2 SOSI_int32, rampeterskel SOSI_real64, rampetilgjengelig SOSI_varchar(80), breddeinngang SOSI_int32, hoydeinngang SOSI_int32, terskelhoyde SOSI_real64, kontrastinngang SOSI_varchar(80), diametersnusirkel SOSI_int32, dekke SOSI_varchar(80), dekketilstand SOSI_varchar(80), tilgjengvurderingrullestol SOSI_varchar(80), tilgjengvurderingelrullestol SOSI_varchar(80), tilgjengvurderingsyn SOSI_varchar(80), ogcfid SOSI_int32, opphav SOSI_varchar(80), kommune SOSI_varchar(80), bilde SOSI_varchar(80), registrert SOSI_datetime, oppdatert SOSI_datetime, kommentar SOSI_varchar(500), forbedringsforslag SOSI_varchar(255)
uufriluftsomrader.uufriluftgrillbalplass (writer SOSI_1)
    attributes: dekke SOSI_varchar(80), dekketilstand SOSI_varchar(80), helning SOSI_real64, tilgjengvurderingrullestol SOSI_varchar(80), ogcfid SOSI_int32, opphav SOSI_varchar(80), kommune SOSI_varchar(80), bilde SOSI_varchar(80), registrert SOSI_datetime, oppdatert SOSI_datetime, kommentar SOSI_varchar(500), forbedringsforslag SOSI_varchar(500)
uufriluftsomrader.uufrilufthcparkering (writer SOSI_1)
    attributes: skiltet SOSI_varchar(80), merket SOSI_varchar(80), bredde SOSI_int32, lengde SOSI_int32, avstandfasilitet SOSI_int32, avgift SOSI_varchar(80), automathoyde SOSI_int32, tilgjengeligautomat SOSI_varchar(80), tilgjengvurderingrullestol SOSI_varchar(80), tilgjengvurderingelrullestol SOSI_varchar(80), ogcfid SOSI_int32, opphav SOSI_varchar(80), kommune SOSI_varchar(80), bilde SOSI_varchar(80), registrert SOSI_datetime, oppdatert SOSI_datetime, kommentar SOSI_varchar(500), forbedringsforslag SOSI_varchar(255)
uufriluftsomrader.uufriluftparkeringsomrade (writer SOSI_1)
    attributes: kapasitetpersonbiler SOSI_int32, kapasitetuu SOSI_int32, arstidsbruk SOSI_varchar(80), dekke SOSI_varchar(80), dekketilstand SOSI_varchar(80), tilgjengvurderingrullestol SOSI_varchar(80), tilgjengvurderingelrullestol SOSI_varchar(80), ogcfid SOSI_int32, opphav SOSI_varchar(80), kommune SOSI_varchar(80), bilde SOSI_varchar(80), registrert SOSI_datetime, oppdatert SOSI_datetime, kommentar SOSI_varchar(500), forbedringsforslag SOSI_varchar(500)
uufriluftsomrader.uufriluftparkeringsomradegrense (writer SOSI_1)
uufriluftsomrader.uufriluftsittegruppe (writer SOSI_1)
    attributes: dekke SOSI_varchar(80), dekketilstand SOSI_varchar(80), helning SOSI_real64, hoydebord SOSI_int32, utstikkbord SOSI_int32, tilgjengvurderingrullestol SOSI_varchar(80), ogcfid SOSI_int32, opphav SOSI_varchar(80), kommune SOSI_varchar(80), bilde SOSI_varchar(80), registrert SOSI_datetime, oppdatert SOSI_datetime, kommentar SOSI_varchar(500), forbedringsforslag SOSI_varchar(255)
uufriluftsomrader.uufrilufttoalett (writer SOSI_1)
    attributes: byggtype SOSI_varchar(80), rampe SOSI_varchar(80), rampebredde SOSI_int32, rampestigning SOSI_real64, handlist SOSI_varchar(80), handlisthoyde1 SOSI_int32, handlisthoyde2 SOSI_int32, rampeterskel SOSI_real64, rampetilgjengelighet SOSI_varchar(80), avstandhc SOSI_int32, dortype SOSI_varchar(80), dorapner SOSI_varchar(80), manoverknapphoyde SOSI_int32, breddeinngang SOSI_int32, kontrastinngang SOSI_varchar(80), terskelhoyde SOSI_real64, diametersnusirkel SOSI_int32, belysning SOSI_varchar(80), omkledningtilgjengelig SOSI_varchar(80), servanttilgjengelig SOSI_varchar(80), wctilgjengelig SOSI_varchar(80), tilgjengvurderingrullestol SOSI_varchar(80), tilgjengvurderingelrullestol SOSI_varchar(80), tilgjengvurderingsyn SOSI_varchar(80), ogcfid SOSI_int32, opphav SOSI_varchar(80), kommune SOSI_varchar(80), bilde SOSI_varchar(80), registrert SOSI_datetime, oppdatert SOSI_datetime,
      kommentar SOSI_varchar(500), forbedringsforslag SOSI_varchar(500)
uufriluftsomrader.uufriluftturvei (writer SOSI_1)
    attributes: veitype SOSI_varchar(80), spesialfotrutetype SOSI_varchar(80), arstidsbruk SOSI_varchar(80), sperrebom SOSI_varchar(80), sperrebomtilgjengelig SOSI_varchar(80), dekke SOSI_varchar(80), dekketilstand SOSI_varchar(80), motehvileplass SOSI_varchar(80), antalltilstrekkelig SOSI_varchar(80), belysning SOSI_varchar(80), bredde SOSI_int32, stigning SOSI_real64, tverrfall SOSI_real64, frihoyde SOSI_varchar(80), ledelinje SOSI_varchar(80), ledelinjekontrast SOSI_varchar(80), tilgjengvurderingrullestol SOSI_varchar(80), tilgjengvurderingelrullestol SOSI_varchar(80), tilgjengvurderingsyn SOSI_varchar(80), ogcfid SOSI_int32, opphav SOSI_varchar(80), kommune SOSI_varchar(80), bilde SOSI_varchar(80), registrert SOSI_datetime, oppdatert SOSI_datetime, kommentar SOSI_varchar(500), forbedringsforslag SOSI_varchar(255)
uufriluftsomrader.uufrilufthyttertilrettelagt (writer SOSI_1)
    attributes: eier SOSI_varchar(80), lenke SOSI_varchar(255), navn SOSI_varchar(80), tilrettelagt SOSI_varchar(80), ogcfid SOSI_int32, opphav SOSI_int32, kommune SOSI_varchar(80), bilde SOSI_varchar(80), registrert SOSI_datetime, oppdatert SOSI_datetime, kommentar SOSI_varchar(500), forbedringsforslag SOSI_varchar(500)
uufriluftsomrader.uufriluftstatligsikrafriluftsomrader (writer SOSI_1)
    attributes: navn SOSI_varchar(50), naturbasenr SOSI_varchar(12), linkbilde SOSI_varchar(50), linkskjema SOSI_varchar(50), ogcfid SOSI_int32, opphav SOSI_varchar(80), kommune SOSI_varchar(80), bilde SOSI_varchar(80), registrert SOSI_datetime, oppdatert SOSI_datetime, kommentar SOSI_varchar(2000), forbedringsforslag SOSI_varchar(2000)
uufriluftsomrader.uufriluftstatligsikrafriluftsomradergrense (writer SOSI_1)

Bookmark: SOSI UUTettsted
uutettsted.uutettstedhcparkering (writer SOSI_2)
    attributes: overbygg SOSI_varchar(80), varmekabel SOSI_varchar(80), skiltet SOSI_varchar(80), merket SOSI_varchar(80), bredde SOSI_int32, lengde SOSI_int32, avstandservicebygg SOSI_int32, avgift SOSI_varchar(80), automathoyde SOSI_int32, tilgjengeligautomat SOSI_varchar(80), tilgjengvurderingrullestol SOSI_varchar(80), tilgjengvurderingelrullestol SOSI_varchar(80), ogcfid SOSI_int32, kommune SOSI_varchar(80), opphav SOSI_varchar(80), registrert SOSI_datetime, oppdatert SOSI_datetime, byggingpagar SOSI_varchar(80), bilde SOSI_varchar(80), kommentar SOSI_varchar(500)
uutettsted.uutettstedinngangbygg (writer SOSI_2)
    attributes: byggfunksjon SOSI_varchar(80), avstandvanligparkering SOSI_int32, avstandhc SOSI_int32, rampe SOSI_varchar(80), rampebredde SOSI_int32, rampestigning SOSI_real64, handlist SOSI_varchar(80), handlisthoyde1 SOSI_int32, handlisthoyde2 SOSI_int32, rampeterskel SOSI_real64, rampetilgjengelig SOSI_varchar(80), dortype SOSI_varchar(80), dorapner SOSI_varchar(80), manoverknapphoyde SOSI_int32, inngangbredde SOSI_int32, terskelhoyde SOSI_real64, ringeklokke SOSI_varchar(80), ringeklokkehoyde SOSI_int32, stigningadkomstvei SOSI_real64, kontrast SOSI_varchar(80), tilgjengvurderingrullestol SOSI_varchar(80), tilgjengvurderingelrullestol SOSI_varchar(80), tilgjengvurderingsyn SOSI_varchar(80), ogcfid SOSI_int32, kommune SOSI_varchar(80), opphav SOSI_varchar(80), registrert SOSI_datetime, oppdatert SOSI_datetime, byggingpagar SOSI_varchar(80), bilde SOSI_varchar(80),
      kommentar SOSI_varchar(500)
uutettsted.uutettstedparkeringsomrade (writer SOSI_2)
    attributes: kapasitetpersonbiler SOSI_int32, kapasitetuu SOSI_int32, eierforhold SOSI_varchar(80), arstidsbruk SOSI_varchar(80), overbygg SOSI_varchar(80), varmekabel SOSI_varchar(80), dekke SOSI_varchar(80), dekketilstand SOSI_varchar(80), tilgjengvurderingrullestol SOSI_varchar(80), tilgjengvurderingelrullestol SOSI_varchar(80), ogcfid SOSI_int32, kommune SOSI_varchar(80), opphav SOSI_varchar(80), registrert SOSI_datetime, oppdatert SOSI_datetime, byggingpagar SOSI_varchar(80), bilde SOSI_varchar(80), kommentar SOSI_varchar(500)
uutettsted.uutettstedparkeringsomradegrense (writer SOSI_2)
uutettsted.uutettstedvei (writer SOSI_2)
    attributes: objid SOSI_int32, objtype SOSI_varchar(32), gatetype SOSI_varchar(80), dekke SOSI_varchar(80), dekketilstand SOSI_varchar(80), bredde SOSI_int32, nedsenk1 SOSI_real64, nedsenk2 SOSI_real64, stigning SOSI_real64, tverrfall SOSI_real64, moteplass SOSI_varchar(80), varmekabel SOSI_varchar(80), lyssignal SOSI_varchar(80), lydsignal SOSI_varchar(80), ledelinje SOSI_varchar(80), ledelinjekontrast SOSI_varchar(80), tilgjengvurderingrullestol SOSI_varchar(80), tilgjengvurderingelrullestol SOSI_varchar(80), tilgjengvurderingsyn SOSI_varchar(80), ogcfid SOSI_int32, kommune SOSI_varchar(80), opphav SOSI_varchar(80), registrert SOSI_datetime, oppdatert SOSI_datetime, byggingpagar SOSI_varchar(80), bilde SOSI_varchar(80), kommentar SOSI_varchar(500)

FME custom transformer CreateClipper

Parameters:
- CLIPPERCOORDS = 253577 6650999 253577 6651246 253763 6651246 253763 6650999 253577 6650999   # Clipper Coordinate List
- CLIPPERCOORDSYS = EPSG:25833   # Clipper Coordinate System
- DESTCOORDSYS = "ESRIWKT|ETRS_1989_UTM_Zone_35N|PROJCS["ETRS_1989_UTM_Zone_35N",GEOGCS["GCS_ETRS_1989",DATUM["D_ETRS_1989",SPHEROID["GRS_1980",6378137.0,298.257222101]],PRIMEM["Greenwich",0.0],UNIT["Degree",0.0174532925199433]],PROJECTION["Transverse_Mercator"],PARAMETER["False_Easting",500000.0],PARAMETER["False_Northing",0.0],PARAMETER["Central_Meridian",27.0],PARAMETER["Scale_Factor",0.9996],PARAMETER["Latitude_Of_Origin",0.0],UNIT["Meter",1.0]]"   # Destination Coordinate System

Note: Creating geometry from / the Clipper coords
Creator
    NUM = 1
    COORDS = $(CLIPPERCOORDS)
    GEOMTYPE = 2D Coordinate List
    COORDSYS = $(CLIPPERCOORDSYS)
    CREATED -> BoundingBoxAccumulator
Note: Calculating the bounding / box (envelope) from the geometry
BoundingBoxAccumulator
    TOPFER_INDEX = No
    BOUNDING_BOX -> SpatialFilter [input 1]
    ORIGINAL -> SpatialFilter [input 2]
Note: If the geometry is equal to its / own bounding box - it is a rectangle!
SpatialFilter
    PASS_CRITERIA = Pass Against One Base
    PREDATTR = _predicate
    PREDICATES = EQUALS
    BASE_TYPE = Single Base
    USE_BOUNDING_BOX = No
    MERGE_ATTRS = No
    CURVE_BOUNDARY_RULE_PARAM = Default Rule
    PASSED -> Reprojector
    FAILED -> Reprojector_2
Note: If rectangle, reproject the / geometry to the destination / coordinate system
Reprojector
    SOURCE = Read from feature
    STROKE_ARCS = Yes
    INTERPOLATION_TYPE_NAME = Nearest Neighbor
    DEST = $(DESTCOORDSYS)
    RASTER_CELL_SIZE = Preserve Cells
    REPROJECTED -> BoundingBoxAccumulator_2
Note: Then calculate the bounding / box from the projected geoemtry
BoundingBoxAccumulator_2
    TOPFER_INDEX = No
    BOUNDING_BOX -> Reprojector_3
Note: Reproject the geometry back to / the DB coordsys (LL/EUREF89)
Reprojector_3
    SOURCE = Read from feature
    STROKE_ARCS = Yes
    INTERPOLATION_TYPE_NAME = Nearest Neighbor
    DEST = EPSG:4258
    RASTER_CELL_SIZE = Preserve Cells
    REPROJECTED -> GeometryFilter
Note: Reproject clipper to / the DB coordsys (LL/EUREF89)
Reprojector_2
    SOURCE = Read from feature
    STROKE_ARCS = Yes
    INTERPOLATION_TYPE_NAME = Nearest Neighbor
    DEST = EPSG:4258
    RASTER_CELL_SIZE = Preserve Cells
    REPROJECTED -> GeometryFilter
Note: Getting rid of dummies
GeometryFilter
    BREAK_AGG = No
    GEOM_PORT_NAMES = Area
    AREA -> Output (output)
Output (output)

FME custom transformer SosiFilenameSetter

Parameters:
- OUTPUT_EPSG_CODE = 25832   # Destination coordinate system
- FANOUT = Kommuner   # Fanout områder
- UNDERTEMA =   # Undertema
- HOVEDTEMA =   # Hovedtema
- _CLIPPED = @Value(_clipped)   # Clipped
- _CLIPPER_FILE = @Value(_clipper_file)   # Clipper File
- _CLIPPERCOORDS = @Value(_clippercoords)   # Clippercoords
- _CREATION_INSTANCE = @Value(_creation_instance)   # Creation Instance
- _FNR = @Value(_fnr)   # Fnr
- _KNR = @Value(_knr)   # Knr
- ANNEN = @Value(annen)   # annen
- ANTALLTILSTREKKELIG = @Value(antalltilstrekkelig)   # antalltilstrekkelig
- ARSTIDSBRUK = @Value(arstidsbruk)   # arstidsbruk
- AUTOMATHOYDE = @Value(automathoyde)   # automathoyde
- AVGIFT = @Value(avgift)   # avgift
- AVSTANDFASILITET = @Value(avstandfasilitet)   # avstandfasilitet
- AVSTANDHC = @Value(avstandhc)   # avstandhc
- AVSTANDSERVICEBYGG = @Value(avstandservicebygg)   # avstandservicebygg
- AVSTANDVANLIGPARKERING = @Value(avstandvanligparkering)   # avstandvanligparkering
- BADERAMPE = @Value(baderampe)   # baderampe
- BELYSNING = @Value(belysning)   # belysning
- BILDE = @Value(bilde)   # bilde
- BREDDE = @Value(bredde)   # bredde
- BREDDEINNGANG = @Value(breddeinngang)   # breddeinngang
- BYGGFUNKSJON = @Value(byggfunksjon)   # byggfunksjon
- BYGGINGPAGAR = @Value(byggingpagar)   # byggingpagar
- BYGGTYPE = @Value(byggtype)   # byggtype
- DEKKE = @Value(dekke)   # dekke
- DEKKETILSTAND = @Value(dekketilstand)   # dekketilstand
- DIAMETERSNUSIRKEL = @Value(diametersnusirkel)   # diametersnusirkel
- DORAPNER = @Value(dorapner)   # dorapner
- DORTYPE = @Value(dortype)   # dortype
- EIERFORHOLD = @Value(eierforhold)   # eierforhold
- FISKEPLASS = @Value(fiskeplass)   # fiskeplass
- FLYTEBRYGGE = @Value(flytebrygge)   # flytebrygge
- FORBEDRINGSFORSLAG = @Value(forbedringsforslag)   # forbedringsforslag
- FRIHOYDE = @Value(frihoyde)   # frihoyde
- FYLKEID = @Value(fylkeid)   # fylkeid
- GAPAHUK = @Value(gapahuk)   # gapahuk
- GATETYPE = @Value(gatetype)   # gatetype
- GRILLBALPLASS = @Value(grillbalplass)   # grillbalplass
- HANDLIST = @Value(handlist)   # handlist
- HANDLISTHOYDE1 = @Value(handlisthoyde1)   # handlisthoyde1
- HANDLISTHOYDE2 = @Value(handlisthoyde2)   # handlisthoyde2
- HCPARKERINGSPLASS = @Value(hcparkeringsplass)   # hcparkeringsplass
- HELNING = @Value(helning)   # helning
- HOYDEBORD = @Value(hoydebord)   # hoydebord
- HOYDEINNGANG = @Value(hoydeinngang)   # hoydeinngang
- INFORMASJON = @Value(informasjon)   # informasjon
- INNGANGBREDDE = @Value(inngangbredde)   # inngangbredde
- KAPASITETPERSONBILER = @Value(kapasitetpersonbiler)   # kapasitetpersonbiler
- KAPASITETUU = @Value(kapasitetuu)   # kapasitetuu
- KOMMENTAR = @Value(kommentar)   # kommentar
- KOMMUNE = @Value(kommune)   # kommune
- KOMMUNEID = @Value(kommuneid)   # kommuneid
- KONTRAST = @Value(kontrast)   # kontrast
- KONTRASTINNGANG = @Value(kontrastinngang)   # kontrastinngang
- LEDELINJE = @Value(ledelinje)   # ledelinje
- LEDELINJEKONTRAST = @Value(ledelinjekontrast)   # ledelinjekontrast
- LENGDE = @Value(lengde)   # lengde
- LYDSIGNAL = @Value(lydsignal)   # lydsignal
- LYSSIGNAL = @Value(lyssignal)   # lyssignal
- MANOVERKNAPPHOYDE = @Value(manoverknapphoyde)   # manoverknapphoyde
- MERKET = @Value(merket)   # merket
- MOTEHVILEPLASS = @Value(motehvileplass)   # motehvileplass
- MOTEPLASS = @Value(moteplass)   # moteplass
- NATURBASENR = @Value(naturbasenr)   # naturbasenr
- NAVN = @Value(navn)   # navn
- NEDSENK1 = @Value(nedsenk1)   # nedsenk1
- NEDSENK2 = @Value(nedsenk2)   # nedsenk2
- OBJID = @Value(objid)   # objid
- OBJTYPE = @Value(objtype)   # objtype
- OGCFID = @Value(ogcfid)   # ogcfid
- OMKLEDNINGTILGJENGELIG = @Value(omkledningtilgjengelig)   # omkledningtilgjengelig
- OPPDATERT = @Value(oppdatert)   # oppdatert
- OPPHAV = @Value(opphav)   # opphav
- OVERBYGG = @Value(overbygg)   # overbygg
- PARKERINGSOMRADE = @Value(parkeringsomrade)   # parkeringsomrade
- PLANKEAVSTAND = @Value(plankeavstand)   # plankeavstand
- RAMPE = @Value(rampe)   # rampe
- RAMPEBREDDE = @Value(rampebredde)   # rampebredde
- RAMPESTIGNING = @Value(rampestigning)   # rampestigning
- RAMPETERSKEL = @Value(rampeterskel)   # rampeterskel
- RAMPETILGJENGELIG = @Value(rampetilgjengelig)   # rampetilgjengelig
- RAMPETILGJENGELIGHET = @Value(rampetilgjengelighet)   # rampetilgjengelighet
- REGISTRERT = @Value(registrert)   # registrert
- REKKVERK = @Value(rekkverk)   # rekkverk
- RINGEKLOKKE = @Value(ringeklokke)   # ringeklokke
- RINGEKLOKKEHOYDE = @Value(ringeklokkehoyde)   # ringeklokkehoyde
- SERVANTTILGJENGELIG = @Value(servanttilgjengelig)   # servanttilgjengelig
- SITTEGRUPPE = @Value(sittegruppe)   # sittegruppe
- SKILTET = @Value(skiltet)   # skiltet
- SPERREBOM = @Value(sperrebom)   # sperrebom
- SPERREBOMTILGJENGELIG = @Value(sperrebomtilgjengelig)   # sperrebomtilgjengelig
- SPESIALFOTRUTETYPE = @Value(spesialfotrutetype)   # spesialfotrutetype
- STIGNING = @Value(stigning)   # stigning
- STIGNINGADKOMSTVEI = @Value(stigningadkomstvei)   # stigningadkomstvei
- STOPPKANT = @Value(stoppkant)   # stoppkant
- STOPPKANTHOYDE = @Value(stoppkanthoyde)   # stoppkanthoyde
- TERSKELHOYDE = @Value(terskelhoyde)   # terskelhoyde
- TILGJENGELIGAUTOMAT = @Value(tilgjengeligautomat)   # tilgjengeligautomat
- TILGJENGVURDERINGELRULLESTOL = @Value(tilgjengvurderingelrullestol)   # tilgjengvurderingelrullestol
- TILGJENGVURDERINGRULLESTOL = @Value(tilgjengvurderingrullestol)   # tilgjengvurderingrullestol
- TILGJENGVURDERINGSYN = @Value(tilgjengvurderingsyn)   # tilgjengvurderingsyn
- TOALETT = @Value(toalett)   # toalett
- TURVEI = @Value(turvei)   # turvei
- TVERRFALL = @Value(tverrfall)   # tverrfall
- UTSTIKKBORD = @Value(utstikkbord)   # utstikkbord
- VARMEKABEL = @Value(varmekabel)   # varmekabel
- VEITYPE = @Value(veitype)   # veitype
- WCTILGJENGELIG = @Value(wctilgjengelig)   # wctilgjengelig
- PG_DB:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgdb').text
      
      return value
- PG_HOST:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pghost').text
      
      return value
- PG_PORT:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgport').text
      
      return value
- PG_PWD:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgpwd').text
      
      return value
- PG_USER:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pguser').text
      
      return value

Input (input)
    -> ParameterFetcher
ParameterFetcher
    ATTR_LIST = _output_epsg_code {$(OUTPUT_EPSG_CODE)} _fanout {$(FANOUT)}
    -> AttributeValueMapper
Note: Fikser kjente feil i kommunenummer
AttributeValueMapper
    LUT = 1901,1903
    DIRECTION = Forward (Source To Destination)
    SRC = kommuneid
    VAL_ATTR = kommuneid
    DEFAULT_VALUE = @Value(kommuneid)
    -> TestFilter_2
TestFilter_2
    TEST_LIST = BOOL_OP,OR,COMPOSITE_TEST,<Unused>,TEST_CLAUSE,"TEST $(FANOUT) = Kommuner",Kommuner,BOOL_OP,OR,COMPOSITE_TEST,<Unused>,TEST_CLAUSE,"TEST $(FANOUT) = Fylker",Fylker
    DEFAULT_VALUE = Ufiltrert
    Kommuner -> Joiner
    Fylker -> Joiner_2
    Ufiltrert -> FeatureTypeExtractor
Joiner
    JOIN_KEYS = kommuneid kommuneid
    POSTGIS_DISABLE_COLLECTION_SPLITTING = yes
    POSTGIS_PASSWORD = $(PG_PWD)
    DATASET = $(PG_DB)
    POSTGIS_USE_TRUE_POSTGIS_TYPES = yes
    PREFETCH_EXHAUSTIVE = Yes
    POSTGIS_HOST = $(PG_HOST)
    ADDED_FIELDS = navn
    MATCH_RULE_DISPLAY = Must Match Exactly One (1:1)
    POSTGIS_USER_NAME = $(PG_USER)
    TABLE = admingrense.kommuner
    POSTGIS_PORT = $(PG_PORT)
    POSTGIS_QUERY_FEATURE_TYPES_FOR_MERGE_FILTERS = Yes
    FORMAT = POSTGIS
    CACHE_SIZE = 5000
    JOINED -> StringReplacer_2
Joiner_2
    JOIN_KEYS = fylkeid fylkeid
    POSTGIS_DISABLE_COLLECTION_SPLITTING = yes
    POSTGIS_PASSWORD = $(PG_PWD)
    DATASET = $(PG_DB)
    POSTGIS_USE_TRUE_POSTGIS_TYPES = yes
    PREFETCH_EXHAUSTIVE = Yes
    POSTGIS_HOST = $(PG_HOST)
    ADDED_FIELDS = navn
    MATCH_RULE_DISPLAY = Must Match Exactly One (1:1)
    POSTGIS_USER_NAME = $(PG_USER)
    TABLE = admingrense.fylkeflate
    POSTGIS_PORT = $(PG_PORT)
    POSTGIS_QUERY_FEATURE_TYPES_FOR_MERGE_FILTERS = Yes
    FORMAT = POSTGIS
    CACHE_SIZE = 5000
    JOINED -> StringReplacer_2
FeatureTypeExtractor
    DEST_ATTR = _feature_type
    -> AttributeSplitter
AttributeSplitter
    ATTR_NAME = _feature_type
    DELIMITER = .
    TRIM_OPTION = Both
    LIST_NAME = _feature_type
    DROP_EMPTY_PARTS = No
    -> AttributeCreator
AttributeCreator
    ATTR_LIST = undertema,"FME_CONDITIONAL:DEFAULT_VALUE'Tilgjengelighet'BOOL_OP;OR;COMPOSITE_TEST;<Unused>;TEST @Value(_feature_type{0}) = uutettsted'Tettsted'BOOL_OP;OR;COMPOSITE_TEST;<Unused>;TEST @Value(_feature_type{0}) = uufriluftsomrader'Friluftsomrader'FME_NUM_CONDITIONS3___"
    -> AttributeCreator_13
AttributeCreator_13
    ATTR_LIST = sosifile,"FME_CONDITIONAL:DEFAULT_VALUE'$(HOVEDTEMA)_$(OUTPUT_EPSG_CODE)_@Value(undertema)_SOSI'BOOL_OP;OR;COMPOSITE_TEST;<Unused>;TEST $(FANOUT) LIKE Kommuner'$(HOVEDTEMA)_@PadLeft(@Value(kommuneid),4,0)_@Value(navn)_$(OUTPUT_EPSG_CODE)_@Value(undertema)_SOSI'BOOL_OP;OR;COMPOSITE_TEST;<Unused>;TEST $(FANOUT) LIKE Fylker'$(HOVEDTEMA)_@PadLeft(@Value(fylkeid),2,0)_@Value(navn)_$(OUTPUT_EPSG_CODE)_@Value(undertema)_SOSI'BOOL_OP;OR;COMPOSITE_TEST;<Unused>;TEST $(FANOUT) LIKE Norge'$(HOVEDTEMA)_Norge_$(OUTPUT_EPSG_CODE)_@Value(undertema)_SOSI'FME_NUM_CONDITIONS4___"
    -> Output (output)
Output (output)

Bookmark: Substituerer ÆØÅ og mellomrom
StringReplacer_2
    FIND_TEXT = " "
    NO_MATCH = _FME_NO_OP_
    REPLACE_TEXT = _
    REGEXP = no
    CASE = no
    SRC_ATTRS = navn
    -> StringReplacer_3
StringReplacer_3
    FIND_TEXT = Æ
    NO_MATCH = _FME_NO_OP_
    REPLACE_TEXT = E
    REGEXP = no
    CASE = yes
    SRC_ATTRS = navn
    -> StringReplacer_4
StringReplacer_4
    FIND_TEXT = Ø
    NO_MATCH = _FME_NO_OP_
    REPLACE_TEXT = O
    REGEXP = no
    CASE = yes
    SRC_ATTRS = navn
    -> StringReplacer_5
StringReplacer_5
    FIND_TEXT = Å
    NO_MATCH = _FME_NO_OP_
    REPLACE_TEXT = A
    REGEXP = no
    CASE = yes
    SRC_ATTRS = navn
    -> StringReplacer_6
StringReplacer_6
    FIND_TEXT = æ
    NO_MATCH = _FME_NO_OP_
    REPLACE_TEXT = e
    REGEXP = no
    CASE = yes
    SRC_ATTRS = navn
    -> StringReplacer_7
StringReplacer_7
    FIND_TEXT = ø
    NO_MATCH = _FME_NO_OP_
    REPLACE_TEXT = o
    REGEXP = no
    CASE = yes
    SRC_ATTRS = navn
    -> StringReplacer_8
StringReplacer_8
    FIND_TEXT = å
    NO_MATCH = _FME_NO_OP_
    REPLACE_TEXT = a
    REGEXP = no
    CASE = yes
    SRC_ATTRS = navn
    -> FeatureTypeExtractor
