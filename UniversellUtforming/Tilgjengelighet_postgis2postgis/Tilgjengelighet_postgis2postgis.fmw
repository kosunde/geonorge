FME workspace Tilgjengelighet_postgis2postgis.fmw

Parameters:
- CONFIG_FILE:   # Python Script
      #-------------------------------------------------------------------------------
      # Name:        GetConfigFile
      # Purpose:
      #
      # Author:      xsunknu
      #
      # Created:     21.08.2015
      # Copyright:   (c) xsunknu 2015
      # Licence:     <your licence>
      #-------------------------------------------------------------------------------
      
      import os, fme
      
      fmwdir = fme.macroValues['FME_MF_DIR']
      fmwfile = fme.macroValues['FME_MF_NAME']
      
      fmwfile = os.path.join(fmwdir, fmwfile)
      configfile = os.path.splitext(fmwfile)[0] + '_config.xml'
      
      return configfile
- PG_DB_SCHEMA:   # Python Script
      #-------------------------------------------------------------------------------
      # Name:        GetLatestSchema
      # Purpose:     Get latest tilgjengelighet schema
      #              from PostgreSQL DB
      #
      # Author:      xsunknu
      #
      # Created:     30.09.2015
      # Copyright:   (c) xsunknu 2015
      # Licence:     <your licence>
      #-------------------------------------------------------------------------------
      
      import fme, pypyodbc, fmeobjects
      import pypyodbc
      from xml.etree import ElementTree as ET
      
      logger = fmeobjects.FMELogFile()
      
      #Read XML config file
      configtree = ET.parse(fme.macroValues['CONFIG_FILE'])
      configdoc = configtree.getroot()
      sODBC = configdoc.find('pgODBCdriver').text
      pghost = configdoc.find('pginputhost').text
      pgport = configdoc.find('pginputport').text
      pgdb = configdoc.find('pginputdb').text
      pguser = configdoc.find('pginputuser').text
      pgpwd = configdoc.find('pginputpwd').text
      schemaprefix = configdoc.find('schemaprefix').text
      defaultschema = configdoc.find('defaultschema').text
      
      try:
      
          # Setter sammen ODBC connection string
          pgODBC  = 'DRIVER=' + sODBC + ';'
          pgODBC += 'SERVER=' + pghost + ';'
          pgODBC += 'PORT=' + pgport + ';'
          pgODBC += 'DATABASE=' + pgdb + ';'
          pgODBC += 'UID=' + pguser + ';'
          pgODBC += 'PWD=' + pgpwd + ';'
      
          # SQL for a liste alle skjema i databasen
          SQLstm  = 'select nspname from pg_catalog.pg_namespace;'
      
          #  Kobler til databasen med ODBC og lister alle skjema
          logger.logMessageString('pgODBC   = ' + pgODBC)
          conn = pypyodbc.connect(pgODBC)
          cur = conn.cursor()
          logger.logMessageString('SQLstm   = ' + SQLstm)
      
          # Fyrer av SQL og bygger liste over alle skjema som matcher schemaprefix
          schemas = []
          cur.execute(SQLstm)
          for row in cur.fetchall():
              if str(row[0]).find(schemaprefix) == 0:
                  schemas.append(row[0])
      
          # Sorterer lista avtakende, forste element blir da det nyeste skjemaet
          if len(schemas) > 0:
              schemas.sort(reverse=True)
              schema = schemas[0]
              logger.logMessageString('Funnet nyeste skjema: ' + schema)
          else:
              schema = defaultschema
              logger.logMessageString('Ingen matchende skjema funnet, benytter defaultskjema: ' + schema)
      
      except:
          # feilet, benytter default
          schema = defaultschema
          logger.logMessageString('Startup script feilet, benytter defaultskjema: ' + schema)
      
      return schema
- PG_OUTPUT_DB:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgoutputdb').text
      
      return value
- LOG_FILE:   # Python Script
      #-------------------------------------------------------------------------------
      # Name:        GetConfigFile
      # Purpose:
      #
      # Author:      xsunknu
      #
      # Created:     21.08.2015
      # Copyright:   (c) xsunknu 2015
      # Licence:     <your licence>
      #-------------------------------------------------------------------------------
      
      import os, uuid, fme
      
      fmwdir = fme.macroValues['FME_MF_DIR']
      fmwfile = fme.macroValues['FME_MF_NAME']
      
      logdir = os.path.join(fmwdir, 'log')
      if not os.path.isdir(logdir):
          os.mkdir(logdir)
      
      logfile = os.path.splitext(fmwfile)[0] + '_' + str(uuid.uuid1()).replace('-','') + '.log'
      logfile = os.path.join(logdir, logfile)
      
      return logfile

Readers:
- POSTGIS_1: POSTGIS from tilgjengelighet

Writers:
- POSTGIS_2: POSTGIS to $(PG_OUTPUT_DB)
- POSTGIS_3: POSTGIS to $(PG_OUTPUT_DB)

Note: Navner om fme_feature_type / til tidsuavhengig skjemanavn
PythonCaller
    PYTHONSOURCE:
      import fme
      import fmeobjects

      def SetFeatureType(feature):
          featuretype = 'tilgjengelighet.' + feature.getAttribute("fme_feature_type").split('.')[1]
          feature.setAttribute("fme_feature_type", featuretype)
    PYTHONSYMBOL = SetFeatureType
    NEW_ATTRIBUTES = fme_feature_type
    -> Reprojector
Note: Reprojiserer til EPSG:4258
Reprojector
    DEST = EPSG:4258
    INTERPOLATION_TYPE_NAME = Nearest Neighbor
    RASTER_CELL_SIZE = Preserve Cells
    SOURCE = Read from feature
    REPROJECTED -> NullAttributeMapper
FeatureTypeFilter
    ATTRIBUTES = tilgjengelighet.baderampe,tilgjengelighet.fiskeplass,tilgjengelighet.friluftsomrade,tilgjengelighet.gapahukhytte,tilgjengelighet.grillballplass,tilgjengelighet.hc_parkering_friluft,tilgjengelighet.hytter_tilrettelagt,tilgjengelighet.parkeringsomrade_friluft,tilgjengelighet.serveringkiosk,tilgjengelighet.sittegruppe,tilgjengelighet.statlig_sikra_friluftsomrade,tilgjengelighet.t_hc_parkering,tilgjengelighet.t_inngangbygg,tilgjengelighet.t_parkeringsomrade,tilgjengelighet.t_vei,tilgjengelighet.toalett,tilgjengelighet.turvei,<BLANK>,<UNFILTERED>
    tilgjengelighet.t_vei -> AttributeCreator_14
    tilgjengelighet.baderampe -> AttributeCreator_5
    tilgjengelighet.friluftsomrade -> AttributeCreator_7
    tilgjengelighet.grillballplass -> AttributeCreator_8
    tilgjengelighet.parkeringsomrade_friluft -> AttributeCreator_10
    tilgjengelighet.t_inngangbygg -> AttributeCreator_12
    tilgjengelighet.t_parkeringsomrade -> AttributeCreator_11
    tilgjengelighet.toalett -> AttributeCreator_6
    tilgjengelighet.hc_parkering_friluft -> AttributeCreator
    tilgjengelighet.t_hc_parkering -> AttributeCreator_13
    tilgjengelighet.gapahukhytte -> AttributeCreator_2
    tilgjengelighet.turvei -> AttributeCreator_3
    tilgjengelighet.sittegruppe -> AttributeCreator_4
    tilgjengelighet.fiskeplass -> AttributeCreator_9
    tilgjengelighet.hytter_tilrettelagt -> AttributeCreator_15
    tilgjengelighet.statlig_sikra_friluftsomrade -> AttributeCreator_16

Bookmark: Tilgjengelighet - PostGIS
$(PG_DB_SCHEMA).t_vei (reader POSTGIS_1)
    attributes: registrert timestamp, oppdatert timestamp, bilde varchar(50), dekke_tilstand varchar(255), tverrfall_grad float8, nedsenk_1 float8, lydsignal varchar(255), led_lin_kontrast varchar(255), shape_length float8, gate_type varchar(255), moteplass varchar(255), lyssignal varchar(255), t_rulle_backup char(255), varmekabel varchar(255), bredde int4, kommentar varchar(500), ledelinje varchar(255), stig_grad float8, objectid int4, nedsenk_2 float8, opphav varchar(255), dekke varchar(255), t_rulle_auto char(255), komm int4, t_rulle char(255), ogc_fid serial,PRIKEY, t_syn char(255), bygging_pagar char(50), t_el_rulle_auto char(255), oppdat_app timestamp
    -> PythonCaller
$(PG_DB_SCHEMA).turvei (reader POSTGIS_1)
    attributes: ogc_fid serial,PRIKEY, belysning varchar(255), bredde int4, dekke varchar(255), forbed_forslag varchar(500), gid int4, registrert timestamp, ledelinje varchar(255), led_lin_kontrast varchar(255), mote_hvileplass varchar(255), stigning float8, t_rulle varchar(255), t_syn varchar(255), tverrfall float8, userid varchar(255), dekke_tilstand varchar(255), veitype varchar(255), opphav varchar(255), komm int4, kommentar varchar(500), spesialfottyperute varchar(255), t_el_rulle_auto varchar(255), bilde varchar(50), frihoyde varchar(255), oppdatert timestamp, arstidbruk varchar(255), oppdat_app timestamp, sperrebom varchar(255), mote_hvile_tilstrekk varchar(255), sperrebom_tilgj varchar(255),
      t_rulle_auto varchar(255), t_rulle_backup varchar(255)
    -> PythonCaller
$(PG_DB_SCHEMA).toalett (reader POSTGIS_1)
    attributes: ogc_fid serial,PRIKEY, gid int4, registrert timestamp, byggtype varchar(255), inngang_type varchar(255), dorapner varchar(255), man_knap_hoyde int4, inngang_bredde int4, terskel_hoyde float8, rampe_bredde int4, handlist varchar(255), hand_hoy_1 int4, hand_hoy_2 int4, bilde varchar(50), t_rulle varchar(255), t_syn varchar(255), kommentar varchar(500), forbed_forslag varchar(500), userid varchar(250), opphav varchar(255), komm int4, t_el_rulle_auto varchar(255), rampe varchar(255), oppdatert timestamp, rampe_stigning float8, rampe_terskel float8, rampe_tilgj char(255), kontrast_inngang varchar(255), diameter int4, belysning varchar(255),
      omkledning_tilgj varchar(255), servant_tilgj varchar(255), wc_tilgj varchar(255), oppdat_app timestamp, sperrebom_tilgj varchar(255), t_rulle_auto varchar(255), t_rulle_backup varchar(255), atko_stigning float8
    -> PythonCaller
$(PG_DB_SCHEMA).hytter_tilrettelagt (reader POSTGIS_1)
    attributes: ogc_fid serial,PRIKEY, betjenings varchar(1), byggnr numeric(10,0), byggtyp_nb numeric(10,0), registrert timestamp, eier_tekst varchar(50), hytte_id numeric(10,0), hytteeier numeric(5,0), kommentar varchar(254), lenke varchar(200), malemetode numeric(10,0), navn varchar(32), noyaktighe numeric(10,0), objectid numeric(10,0), objtype varchar(32), operator varchar(6), oppdatert time, ptema numeric(10,0), subtypekod numeric(10,0), tilrettela varchar(200), oppdat_app timestamp
    -> PythonCaller
$(PG_DB_SCHEMA).serveringkiosk (reader POSTGIS_1)
    attributes: ogc_fid serial,PRIKEY, adko_ru_led varchar(255), adko_rull varchar(255), adko_syns varchar(255), bilde varchar(50), forbed_forslag varchar(500), gid int4, hoyde_skranke int4, registrert timestamp, kommentar varchar(500), t_rulle varchar(255), t_rullled varchar(255), userid varchar(80), opphav varchar(255), komm int4, t_syn varchar(255), adko_el_rulle varchar(255), t_elrull varchar(255), oppdatert timestamp, oppdat_app timestamp
    -> PythonCaller
$(PG_DB_SCHEMA).t_parkeringsomrade (reader POSTGIS_1)
    attributes: registrert timestamp, oppdatert timestamp, opphav char(255), bilde varchar(50), eierforhold varchar(255), kap_personbiler int4, dekke_tilstand varchar(255), overbygg varchar(255), objectid int4, shape_length float8, shape_area float8, kap_uu int4, dekke varchar(255), t_rulle_backup char(255), varmekabel varchar(255), kommentar varchar(500), arstidbruk varchar(255), komm int4, t_rulle_auto varchar(255), t_rulle char(255), X numeric(10,0), ogc_fid int4,PRIKEY, bygging_pagar char(50), oppdat_app timestamp
    -> PythonCaller
$(PG_DB_SCHEMA).gapahukhytte (reader POSTGIS_1)
    attributes: ogc_fid serial,PRIKEY, bilde varchar(50), forbed_forslag varchar(500), gid int4, hoyde_inngang int4, registrert timestamp, kommentar varchar(500), kontrast_inngang varchar(255), diameter int4, t_rulle varchar(255), userid varchar(80), opphav varchar(255), komm int4, t_syn varchar(255), oppdatert timestamp, rampe char(255), rampe_bredde int4, rampe_stigning float8, handlist char(255), hand_hoy_1 int4, hand_hoy_2 int4, rampe_terskel float8, rampe_tilgj char(255), bredde_inngang int4, terskelhoyde float8, oppdat_app timestamp, dekke char(255), dekke_tilstand varchar(255), t_el_rulle_auto varchar(255), t_rulle_auto varchar(255),
      t_rulle_backup varchar(255)
    -> PythonCaller
$(PG_DB_SCHEMA).statlig_sikra_friluftsomrade (reader POSTGIS_1)
    attributes: ogc_fid serial,PRIKEY, objectid numeric(10,0), navn varchar(50), komm varchar(50), naturbasenr varchar(12), registrert timestamp, turomraade varchar(80), turomraade_tilrettelagt_for varchar(80), badeplass varchar(80), badeplass_tilrettelagt_for varchar(80), fiskeplass varchar(80), fiskeplass_tilrettelagt_for varchar(80), kommentar varchar(80), tilgjengelighet_mulig varchar(50), link_skjema varchar(50), link_bilde varchar(50), kommunenr numeric(5,0), shape_length float8, shape_area float8, oppdatert text, oppdat_app timestamp
    -> PythonCaller
$(PG_DB_SCHEMA).baderampe (reader POSTGIS_1)
    attributes: ogc_fid serial,PRIKEY, bilde varchar(50), forbed_forslag varchar(500), gid int4, hand_hoy_1 int4, hand_hoy_2 int4, registrert timestamp, kommentar varchar(500), rampe_bredde int4, handlist varchar(255), rampe_stig float8, t_rulle varchar(255), userid varchar(255), opphav varchar(255), komm int4, rampe varchar(255), t_syn varchar(255), oppdatert timestamp, rampe_tilgj varchar(255), rampe_terskel float8, oppdat_app timestamp, t_rulle_auto varchar(255), t_rulle_backup varchar(255)
    -> PythonCaller
$(PG_DB_SCHEMA).parkeringsomrade_friluft (reader POSTGIS_1)
    attributes: forbed_forslag varchar(500), gid int4, kap_personbiler int4, kap_uu int4, registrert timestamp, kommentar varchar(500), userid varchar(255), opphav varchar(255), komm int4, bilde varchar(50), t_rulle varchar(255), dekke varchar(255), dekke_tilstand varchar(255), oppdatert timestamp, ogc_fid int4,PRIKEY, arstidbruk varchar(255), oppdat_app timestamp, t_rulle_auto varchar(255), t_rulle_backup varchar(255)
    -> PythonCaller
$(PG_DB_SCHEMA).sittegruppe (reader POSTGIS_1)
    attributes: ogc_fid serial,PRIKEY, bilde varchar(50), bord_hoyde int4, bord_utstikk int4, dekke varchar(255), forbed_forslag varchar(500), gid int4, helning float8, registrert timestamp, kommentar varchar(500), t_rulle varchar(255), userid varchar(255), opphav varchar(255), komm int4, t_syn varchar(255), oppdatert timestamp, dekke_tilstand varchar(255), oppdat_app timestamp, t_rulle_auto varchar(255), t_rulle_backup varchar(255)
    -> PythonCaller
$(PG_DB_SCHEMA).t_inngangbygg (reader POSTGIS_1)
    attributes: registrert timestamp, oppdatert timestamp, avstand_hc_park int4, dortype char(255), rampe char(255), hand_hoy_1 int4, adko_stig_grad float8, terskel_hoyde float8, ringeklokke char(255), ringekl_hoyde int4, man_knap_hoyde int4, inngang_bredde int4, rampe_bredde int4, handlist char(255), t_rulle_backup char(255), rampe_tilgjengelig char(255), bygg_funksjon varchar(255), t_syn char(255), dorapner char(255), kommentar varchar(500), objectid int4, avstand_park int4, kontrast char(255), hand_hoy_2 int4, opphav char(255), bilde char(50), komm int4, t_rulle_auto char(255), t_rulle char(255), ogc_fid serial,PRIKEY,
      rampe_stigning float8, rampe_terskel float8, bygging_pagar char(50), t_el_rulle_auto char(255), oppdat_app timestamp
    -> PythonCaller
$(PG_DB_SCHEMA).hc_parkering_friluft (reader POSTGIS_1)
    attributes: ogc_fid serial,PRIKEY, gid int4, userid varchar(255), komm int4, bilde varchar(50), registrert timestamp, avstand_serv_bygg int4, avgift varchar(255), tilgj_aut varchar(255), kommentar varchar(500), skiltet varchar(50), merket varchar(50), t_rulle varchar(255), opphav varchar(255), aut_hoyde int4, bredde int4, lengde int4, oppdatert timestamp, forbed_forslag varchar(255), oppdat_app timestamp, t_rulle_auto varchar(255), t_rulle_backup varchar(255)
    -> PythonCaller
$(PG_DB_SCHEMA).t_hc_parkering (reader POSTGIS_1)
    attributes: lengde int4, registrert timestamp, oppdatert timestamp, opphav char(255), avgift char(255), bilde char(50), aut_hoyde int4, objectid int4, merket char(255), avstand_servicebygg int4, tilgj_automat char(255), skiltet char(255), t_rulle_backup char(255), varmekabel char(255), bredde int4, kommentar varchar(500), overbygg char(255), komm int4, t_rulle_auto char(255), t_rulle char(255), ogc_fid serial,PRIKEY, bygging_pagar char(50), oppdat_app timestamp, t_el_rulle_auto varchar(255)
    -> PythonCaller
$(PG_DB_SCHEMA).grillballplass (reader POSTGIS_1)
    attributes: ogc_fid serial,PRIKEY, bilde varchar(50), dekke varchar(255), forbed_forslag varchar(500), gid int4, helning float8, registrert timestamp, kommentar varchar(500), t_rulle varchar(255), userid varchar(80), opphav varchar(255), komm int4, t_syn varchar(255), oppdatert timestamp, type char(50), dekke_tilstand varchar(255), oppdat_app timestamp, t_rulle_auto varchar(255), t_rulle_backup varchar(255)
    -> PythonCaller
$(PG_DB_SCHEMA).friluftsomrade (reader POSTGIS_1)
    attributes: bnr int4, forbed_forslag varchar(500), gid int4, gnr int4, naturbase_nr int4, navn varchar(50), userid varchar(80), opphav varchar(255), komm int4, bilde varchar(50), registrert timestamp, kommentar varchar(500), shape_area float8, shape_length float8, oppdatert timestamp, ogc_fid int4,PRIKEY, parkeringsomrade char(50), hc_parkeringsplass char(50), turvei char(50), toalett char(50), baderampe char(50), fiskeplasser char(50), grill_balplass char(50), sittegruppe char(50), gapahuk char(50), informasjon char(50), annen char(50), oppdat_app timestamp
    -> PythonCaller
$(PG_DB_SCHEMA).fiskeplass (reader POSTGIS_1)
    attributes: ogc_fid serial,PRIKEY, bilde varchar(50), dekke varchar(255), diameter int4, flytebrygge varchar(255), forbed_forslag varchar(500), gid int4, registrert timestamp, kommentar varchar(500), kontrast varchar(255), rampe_stigning float8, plankeavstand float8, rekkverk varchar(255), stoppka_hoyde float8, t_rulle varchar(255), userid varchar(80), opphav varchar(255), komm int4, t_syn varchar(255), stoppkant varchar(255), oppdatert timestamp, rampe char(255), rampe_bredde int4, handlist char(255), hand_hoy_1 int4, hand_hoy_2 int4, rampe_terskel float8, rampe_tilgj char(255), dekke_tilstand varchar(255), oppdat_app timestamp,
      t_rulle_auto varchar(255), t_el_rulle_auto varchar(255), t_rulle_backup varchar(255)
    -> PythonCaller

Bookmark: Fjerner "grums"
NullAttributeMapper
    OTHER_VALUE = 0
    SOURCE_ATTR_VAL = Empty
    ATTRCHOICE = Selected Attributes
    ATTRLIST = annen baderampe belysning bygging_pagar fiskeplass flytebrygge forbed_forslag gapahuk grill_balplass handlist hc_parkeringsplass informasjon kommentar led_lin_kontrast lydsignal lyssignal merket moteplass overbygg parkeringsomrade rampe rampe_tilgj rampe_tilgjengelig rekkverk sittegruppe skiltet sperrebom sperrebom_tilgj spesialfottyperute stoppkant tilgj_aut tilgj_automat toalett turvei varmekabel dorapner dortype ringeklokke
    NULL_TREATMENT = Null
    -> NullAttributeMapper_2
NullAttributeMapper_2
    REG_EXP = (bildemangler)|(xx)
    SOURCE_ATTR_VAL = Empty
    ATTRCHOICE = Selected Attributes
    ATTRLIST = bilde kommentar
    NULL_TREATMENT = Null
    -> AttributeCreator_17
AttributeCreator_17
    ATTR_LIST = rampe,"FME_CONDITIONAL:DEFAULT_VALUE'@Value(rampe)'BOOL_OP;COMPOSITE;COMPOSITE_TEST;1 AND (2 OR 3 OR 4 OR 5 OR 6 OR 7 OR 8 OR 9 OR 10);TEST @Value(rampe) NOT_IN Ja,Nei;TEST @Value(rampe_bredde) > 0;TEST @Value(rampe_stig) > 0;TEST @Value(rampe_stigning) > 0;TEST @Value(rampe_terskel) > 0;TEST rampe_tilgj NOT_ATTRIBUTE_VALUE_NULL _FME_BLANK_STRING_;TEST rampe_tilgjengelig NOT_ATTRIBUTE_VALUE_NULL _FME_BLANK_STRING_;TEST handlist NOT_ATTRIBUTE_VALUE_NULL _FME_BLANK_STRING_;TEST @Value(hand_hoy_1) > 0;TEST @Value(hand_hoy_2) > 0'Ja'FME_NUM_CONDITIONS2___"
    -> FeatureTypeFilter

Bookmark: Setter og mapper attributter
AttributeCreator
    ATTR_LIST = objid,@Evaluate(@Count(uufrilufthcparkering, 1)),avstandfasilitet,@Value(avstand_serv_bygg),automathoyde,@Value(aut_hoyde),tilgjengeligautomat,@Value(tilgj_aut),tilgjengvurderingrullestol,@Value(t_rulle),tilgjengvurderingelrullestol,@Value(t_rulle_auto),forbedringsforslag,@Value(forbed_forslag),kommune,@Value(komm),objtype,UUFriluftHCparkering,ogcfid,@Value(ogc_fid)
    -> uufriluftsomrader.uufrilufthcparkering (writer POSTGIS_2)
AttributeCreator_2
    ATTR_LIST = objid,@Evaluate(@Count(uufriluftgapahuk, 1)),objtype,UUFriluftGapahuk,rampebredde,@Value(rampe_bredde),rampestigning,@Value(rampe_stigning),handlisthoyde1,@Value(hand_hoy_1),handlisthoyde2,@Value(hand_hoy_2),rampeterskel,@Value(rampe_terskel),rampetilgjengelig,@Value(rampe_tilgj),breddeinngang,@Value(bredde_inngang),hoydeinngang,@Value(hoyde_inngang),terskelhoyde,@Value(terskel_hoyde),kontrastinngang,@Value(kontrast_inngang),diametersnusirkel,@Value(diameter),dekketilstand,@Value(dekke_tilstand),tilgjengvurderingrullestol,@Value(t_rulle),tilgjengvurderingelrullestol,@Value(t_el_rulle_auto),tilgjengvurderingsyn,@Value(t_syn),ogcfid,@Value(ogc_fid),kommune,@Value(komm),forbedringsforslag,@Value(forbed_forslag)
    -> uufriluftsomrader.uufriluftgapahuk (writer POSTGIS_2)
AttributeCreator_3
    ATTR_LIST = objid,@Evaluate(@Count(uufriluftturvei, 1)),objtype,UUFriluftTurvei,spesialfotrutetype,@Value(spesialfottyperute),arstidsbruk,@Value(arstidbruk),sperrebomtilgjengelig,@Value(sperrebom_tilgj),dekketilstand,@Value(dekke_tilstand),motehvileplass,@Value(mote_hvileplass),ledelinjekontrast,@Value(led_lin_kontrast),tilgjengvurderingrullestol,@Value(t_rulle),tilgjengvurderingelrullestol,@Value(t_rulle_auto),tilgjengvurderingsyn,@Value(t_syn),ogcfid,@Value(ogc_fid),kommune,@Value(komm),forbedringsforslag,@Value(forbed_forslag),antalltilstrekkelig,@Value(mote_hvile_tilstrekk)
    -> uufriluftsomrader.uufriluftturvei (writer POSTGIS_2)
AttributeCreator_4
    ATTR_LIST = objid,@Evaluate(@Count(uufriluftsittegruppe, 1)),objtype,UUFriluftSittegruppe,dekketilstand,@Value(dekke_tilstand),hoydebord,@Value(bord_hoyde),utstikkbord,@Value(bord_utstikk),tilgjengvurderingrullestol,@Value(t_rulle),ogcfid,@Value(ogc_fid),kommune,@Value(komm),forbedringsforslag,@Value(forbed_forslag)
    -> uufriluftsomrader.uufriluftsittegruppe (writer POSTGIS_2)
AttributeCreator_5
    ATTR_LIST = objid,@Evaluate(@Count(uufriluftbaderampe, 1)),objtype,UUFriluftBaderampe,rampebredde,@Value(rampe_bredde),rampestigning,@Value(rampe_stig),handlisthoyde1,@Value(hand_hoy_1),handlisthoyde2,@Value(hand_hoy_2),rampeterskel,@Value(rampe_terskel),rampetilgjengelig,@Value(rampe_tilgj),tilgjengvurderingrullestol,@Value(t_rulle),tilgjengvurderingelrullestol,@Value(t_rulle_auto),tilgjengvurderingsyn,@Value(t_syn),ogcfid,@Value(ogc_fid),kommune,@Value(komm),forbedringsforslag,@Value(forbed_forslag)
    -> uufriluftsomrader.uufriluftbaderampe (writer POSTGIS_2)
AttributeCreator_6
    ATTR_LIST = objid,@Evaluate(@Count(uufrilufttoalett, 1)),objtype,UUFriluftToalett,rampebredde,@Value(rampe_bredde),rampestigning,@Value(rampe_stigning),handlisthoyde1,@Value(hand_hoy_1),handlisthoyde2,@Value(hand_hoy_2),rampeterskel,@Value(rampe_terskel),rampetilgjengelighet,@Value(rampe_tilgj),manoverknapphoyde,@Value(man_knap_hoyde),breddeinngang,@Value(inngang_bredde),kontrastinngang,@Value(kontrast_inngang),terskelhoyde,@Value(terskel_hoyde),diametersnusirkel,@Value(diameter),omkledningtilgjengelig,@Value(omkledning_tilgj),servanttilgjengelig,@Value(servant_tilgj),wctilgjengelig,@Value(wc_tilgj),tilgjengvurderingrullestol,@Value(t_rulle),tilgjengvurderingelrullestol,@Value(t_el_rulle_auto),tilgjengvurderingsyn,@Value(t_syn),ogcfid,@Value(ogc_fid),kommune,@Value(komm),forbedringsforslag,@Value(forbed_forslag)
    -> uufriluftsomrader.uufrilufttoalett (writer POSTGIS_2)
AttributeCreator_7
    ATTR_LIST = objid,@Evaluate(@Count(uufriluftfriluftsomrade, 1)),objtype,UUFriluftFriluftsområde,hcparkeringsplass,@Value(hc_parkeringsplass),grillbalplass,@Value(grill_balplass),ogcfid,@Value(ogc_fid),kommune,@Value(komm),forbedringsforslag,@Value(forbed_forslag)
    -> uufriluftsomrader.uufriluftfriluftsomrade (writer POSTGIS_2)
AttributeCreator_8
    ATTR_LIST = objid,@Evaluate(@Count(uufriluftgrillbalplass, 1)),objtype,UUFriluftGrillBålplass,dekketilstand,@Value(dekke_tilstand),tilgjengvurderingrullestol,@Value(t_rulle),ogcfid,@Value(ogc_fid),kommune,@Value(komm),forbedringsforslag,@Value(forbed_forslag)
    -> uufriluftsomrader.uufriluftgrillbalplass (writer POSTGIS_2)
AttributeCreator_9
    ATTR_LIST = objid,@Evaluate(@Count(uufriluftfiskeplass, 1)),objtype,UUFriluftFiskeplass,rampebredde,@Value(rampe_bredde),rampestigning,@Value(rampe_stigning),handlisthoyde1,@Value(hand_hoy_1),handlisthoyde2,@Value(hand_hoy_2),rampeterskel,@Value(rampe_terskel),rampetilgjengelig,@Value(rampe_tilgj),dekketilstand,@Value(dekke_tilstand),diametersnusirkel,@Value(diameter),stoppkanthoyde,@Value(stoppka_hoyde),tilgjengvurderingrullestol,@Value(t_rulle),tilgjengvurderingelrullestol,@Value(t_el_rulle_auto),tilgjengvurderingsyn,@Value(t_syn),ogcfid,@Value(ogc_fid),kommune,@Value(komm),forbedringsforslag,@Value(forbed_forslag)
    -> uufriluftsomrader.uufriluftfiskeplass (writer POSTGIS_2)
AttributeCreator_10
    ATTR_LIST = objid,@Evaluate(@Count(uufriluftparkeringsomrade, 1)),objtype,UUFriluftParkeringsområde,kapasitetpersonbiler,@Value(kap_personbiler),kapasitetuu,@Value(kap_uu),arstidsbruk,@Value(arstidbruk),dekketilstand,@Value(dekke_tilstand),tilgjengvurderingrullestol,@Value(t_rulle),tilgjengvurderingelrullestol,@Value(t_rulle_auto),ogcfid,@Value(ogc_fid),kommune,@Value(komm),forbedringsforslag,@Value(forbed_forslag)
    -> uufriluftsomrader.uufriluftparkeringsomrade (writer POSTGIS_2)
AttributeCreator_15
    ATTR_LIST = objid,@Evaluate(@Count(uufrilufthyttertilrettelagt, 1)),objtype,UUFriluftHytterTilrettelagt,eier,@Value(eier_tekst),tilrettelagt,@Value(tilrettela),ogcfid,@Value(ogc_fid),kommune,@Value(komm),forbedringsforslag,@Value(forbed_forslag),oppdatert,"FME_CONDITIONAL:DEFAULT_VALUE'@Value(oppdatert)'BOOL_OP;OR;COMPOSITE_TEST;<Unused>;TEST @Value(oppdatert) < 1900-01-01 00:00:00'FME_NULL_VALUE'FME_NUM_CONDITIONS2___"
    -> uufriluftsomrader.uufrilufthyttertilrettelagt (writer POSTGIS_2)
AttributeCreator_16
    ATTR_LIST = objid,@Evaluate(@Count(uufriluftstatligsikrafriluftsomrader, 1)),objtype,UUFriluftStatligSikraFriluftsområder,linkbilde,@Value(link_bilde),linkskjema,@Value(link_skjema),ogcfid,@Value(ogc_fid),forbedringsforslag,@Value(forbed_forslag)
    -> uufriluftsomrader.uufriluftstatligsikrafriluftsomrader (writer POSTGIS_2)
AttributeCreator_11
    ATTR_LIST = objid,@Evaluate(@Count(uutettstedparkeringsomraade, 1)),objtype,UUTettstedParkeringsområde,kapasitetpersonbiler,@Value(kap_personbiler),kapasitetuu,@Value(kap_uu),dekketilstand,@Value(dekke_tilstand),tilgjengvurderingrullestol,@Value(t_rulle),tilgjengvurderingelrullestol,@Value(t_rulle_auto),ogcfid,@Value(ogc_fid),kommune,@Value(komm),byggingpagar,@Value(bygging_pagar),arstidsbruk,@Value(arstidbruk)
    -> uutettsted.uutettstedparkeringsomrade (writer POSTGIS_3)
AttributeCreator_12
    ATTR_LIST = objid,@Evaluate(@Count(uutettstedinngangbygg, 1)),objtype,UUTettstedInngangBygg,byggfunksjon,@Value(bygg_funksjon),avstandvanligparkering,@Value(avstand_park),avstandhc,@Value(avstand_hc_park),rampebredde,@Value(rampe_bredde),rampestigning,@Value(rampe_stigning),handlisthoyde1,@Value(hand_hoy_1),handlisthoyde2,@Value(hand_hoy_2),rampeterskel,@Value(rampe_terskel),rampetilgjengelig,@Value(rampe_tilgjengelig),manoverknapphoyde,@Value(man_knap_hoyde),inngangbredde,@Value(inngang_bredde),terskelhoyde,@Value(terskel_hoyde),ringeklokkehoyde,@Value(ringekl_hoyde),stigningadkomstvei,@Value(adko_stig_grad),tilgjengvurderingrullestol,@Value(t_rulle),tilgjengvurderingelrullestol,@Value(t_el_rulle_auto),tilgjengvurderingsyn,@Value(t_syn),ogcfid,@Value(ogc_fid),kommune,@Value(komm),byggingpagar,@Value(bygging_pagar)
    -> uutettsted.uutettstedinngangbygg (writer POSTGIS_3)
AttributeCreator_13
    ATTR_LIST = objid,@Evaluate(@Count(uutettstedhcparkering, 1)),objtype,UUTettstedHCparkering,avstandservicebygg,@Value(avstand_servicebygg),automathoyde,@Value(aut_hoyde),tilgjengeligautomat,@Value(tilgj_automat),tilgjengvurderingrullestol,@Value(t_rulle),tilgjengvurderingelrullestol,@Value(t_el_rulle_auto),ogcfid,@Value(ogc_fid),kommune,@Value(komm),byggingpagar,@Value(bygging_pagar)
    -> uutettsted.uutettstedhcparkering (writer POSTGIS_3)
AttributeCreator_14
    ATTR_LIST = objid,@Evaluate(@Count(uutettstedvei, 1)),objtype,UUTettstedVei,gatetype,@Value(gate_type),dekketilstand,@Value(dekke_tilstand),nedsenk1,@Value(nedsenk_1),nedsenk2,@Value(nedsenk_2),ledelinjekontrast,@Value(led_lin_kontrast),tilgjengvurderingrullestol,@Value(t_rulle),tilgjengvurderingelrullestol,@Value(t_el_rulle_auto),tilgjengvurderingsyn,@Value(t_syn),ogcfid,@Value(ogc_fid),kommune,@Value(komm),byggingpagar,@Value(bygging_pagar)
    -> uutettsted.uutettstedvei (writer POSTGIS_3)

Bookmark: Friluftsområder - PostGIS
uufriluftsomrader.uufrilufthcparkering (writer POSTGIS_2)
    attributes: objid int4,PRIKEY, objtype varchar(32), skiltet varchar(80), merket varchar(80), bredde int4, lengde int4, avstandfasilitet int4, avgift varchar(80), automathoyde int4, tilgjengeligautomat varchar(80), tilgjengvurderingrullestol varchar(80), tilgjengvurderingelrullestol varchar(80), ogcfid int4, opphav varchar(80), kommune varchar(80), bilde varchar(80), registrert timestamp, oppdatert timestamp, kommentar varchar(500), forbedringsforslag varchar(255)
uufriluftsomrader.uufriluftgapahuk (writer POSTGIS_2)
    attributes: objid int4,PRIKEY, objtype varchar(32), rampe varchar(80), rampebredde int4, rampestigning float8, handlist varchar(80), handlisthoyde1 int4, handlisthoyde2 int4, rampeterskel float8, rampetilgjengelig varchar(80), breddeinngang int4, hoydeinngang int4, terskelhoyde float8, kontrastinngang varchar(80), diametersnusirkel int4, dekke varchar(80), dekketilstand varchar(80), tilgjengvurderingrullestol varchar(80), tilgjengvurderingelrullestol varchar(80), tilgjengvurderingsyn varchar(80), ogcfid int4, opphav varchar(80), kommune varchar(80), bilde varchar(80), registrert timestamp, oppdatert timestamp, kommentar varchar(500), forbedringsforslag varchar(255)
uufriluftsomrader.uufriluftturvei (writer POSTGIS_2)
    attributes: objid int4,PRIKEY, objtype varchar(32), veitype varchar(80), spesialfotrutetype varchar(80), arstidsbruk varchar(80), sperrebom varchar(80), sperrebomtilgjengelig varchar(80), dekke varchar(80), dekketilstand varchar(80), motehvileplass varchar(80), antalltilstrekkelig varchar(80), belysning varchar(80), bredde int4, stigning float8, tverrfall float8, frihoyde varchar(80), ledelinje varchar(80), ledelinjekontrast varchar(80), tilgjengvurderingrullestol varchar(80), tilgjengvurderingelrullestol varchar(80), tilgjengvurderingsyn varchar(80), ogcfid int4, opphav varchar(80), kommune varchar(80), bilde varchar(80), registrert timestamp, oppdatert timestamp, kommentar varchar(500), forbedringsforslag varchar(255)
uufriluftsomrader.uufriluftsittegruppe (writer POSTGIS_2)
    attributes: objid int4,PRIKEY, objtype varchar(32), dekke varchar(80), dekketilstand varchar(80), helning float8, hoydebord int4, utstikkbord int4, tilgjengvurderingrullestol varchar(80), ogcfid int4, opphav varchar(80), kommune varchar(80), bilde varchar(80), registrert timestamp, oppdatert timestamp, kommentar varchar(500), forbedringsforslag varchar(255)
uufriluftsomrader.uufriluftbaderampe (writer POSTGIS_2)
    attributes: objid int4,PRIKEY, objtype varchar(32), rampe varchar(80), rampebredde int4, rampestigning float8, handlist varchar(80), handlisthoyde1 int4, handlisthoyde2 int4, rampeterskel float8, rampetilgjengelig varchar(80), tilgjengvurderingrullestol varchar(80), tilgjengvurderingsyn varchar(80), ogcfid int4, opphav varchar(80), kommune varchar(80), bilde varchar(80), registrert timestamp, oppdatert timestamp, kommentar varchar(500), forbedringsforslag varchar(500)
uufriluftsomrader.uufrilufttoalett (writer POSTGIS_2)
    attributes: objid int4,PRIKEY, objtype varchar(32), byggtype varchar(80), rampe varchar(80), rampebredde int4, rampestigning float8, handlist varchar(80), handlisthoyde1 int4, handlisthoyde2 int4, rampeterskel float8, rampetilgjengelighet varchar(80), avstandhc int4, dortype varchar(80), dorapner varchar(80), manoverknapphoyde int4, breddeinngang int4, kontrastinngang varchar(80), terskelhoyde float8, diametersnusirkel int4, belysning varchar(80), omkledningtilgjengelig varchar(80), servanttilgjengelig varchar(80), wctilgjengelig varchar(80), tilgjengvurderingrullestol varchar(80), tilgjengvurderingelrullestol varchar(80), tilgjengvurderingsyn varchar(80), ogcfid int4, opphav varchar(80), kommune varchar(80), bilde varchar(80),
      registrert timestamp, oppdatert timestamp, kommentar varchar(500), forbedringsforslag varchar(500)
uufriluftsomrader.uufriluftfriluftsomrade (writer POSTGIS_2)
    attributes: objid int4,PRIKEY, objtype varchar(32), navn varchar(80), naturbasenr int4, parkeringsomrade varchar(80), hcparkeringsplass varchar(80), toalett varchar(80), turvei varchar(80), baderampe varchar(80), fiskeplass varchar(80), grillbalplass varchar(80), sittegruppe varchar(80), gapahuk varchar(80), informasjon varchar(80), annen varchar(80), ogcfid int4, opphav varchar(80), kommune varchar(80), bilde varchar(80), registrert timestamp, oppdatert timestamp, kommentar varchar(500), forbedringsforslag varchar(500)
uufriluftsomrader.uufriluftgrillbalplass (writer POSTGIS_2)
    attributes: objid int4,PRIKEY, objtype varchar(32), dekke varchar(80), dekketilstand varchar(80), helning float8, tilgjengvurderingrullestol varchar(80), ogcfid int4, opphav varchar(80), kommune varchar(80), bilde varchar(80), registrert timestamp, oppdatert timestamp, kommentar varchar(500), forbedringsforslag varchar(500)
uufriluftsomrader.uufriluftfiskeplass (writer POSTGIS_2)
    attributes: objid int4,PRIKEY, objtype varchar(32), flytebrygge varchar(80), rampe varchar(80), rampebredde int4, rampestigning float8, handlist varchar(80), handlisthoyde1 int4, handlisthoyde2 int4, rampeterskel float8, rampetilgjengelig varchar(80), dekke varchar(80), plankeavstand float8, dekketilstand varchar(80), diametersnusirkel int4, rekkverk varchar(80), stoppkant varchar(80), stoppkanthoyde float8, tilgjengvurderingrullestol varchar(80), tilgjengvurderingelrullestol varchar(80), tilgjengvurderingsyn varchar(80), ogcfid int4, opphav varchar(80), kommune varchar(80), bilde varchar(80), registrert timestamp, oppdatert timestamp, kommentar varchar(500), forbedringsforslag varchar(500)
uufriluftsomrader.uufriluftparkeringsomrade (writer POSTGIS_2)
    attributes: objid int4,PRIKEY, objtype varchar(32), kapasitetpersonbiler int4, kapasitetuu int4, arstidsbruk varchar(80), dekke varchar(80), dekketilstand varchar(80), tilgjengvurderingrullestol varchar(80), tilgjengvurderingelrullestol varchar(80), ogcfid int4, opphav varchar(80), kommune varchar(80), bilde varchar(80), registrert timestamp, oppdatert timestamp, kommentar varchar(500), forbedringsforslag varchar(500)
uufriluftsomrader.uufrilufthyttertilrettelagt (writer POSTGIS_2)
    attributes: objid int4,PRIKEY, objtype varchar(32), eier varchar(80), lenke varchar(255), navn varchar(80), tilrettelagt varchar(80), ogcfid int4, opphav varchar(80), kommune varchar(80), bilde varchar(80), registrert timestamp, oppdatert timestamp, kommentar varchar(500), forbedringsforslag varchar(500)
uufriluftsomrader.uufriluftstatligsikrafriluftsomrader (writer POSTGIS_2)
    attributes: objid int4,PRIKEY, objtype varchar(80), linkbilde varchar(255), linkskjema varchar(255), naturbasenr varchar(80), navn varchar(80), ogcfid int4, opphav varchar(80), kommune varchar(80), bilde varchar(80), registrert timestamp, oppdatert timestamp, kommentar varchar(2000), forbedringsforslag varchar(2000)

Bookmark: Tettsted - PostGIS
uutettsted.uutettstedparkeringsomrade (writer POSTGIS_3)
    attributes: objid int4,PRIKEY, objtype varchar(32), kapasitetpersonbiler int4, kapasitetuu int4, eierforhold varchar(80), arstidsbruk varchar(80), overbygg varchar(80), varmekabel varchar(80), dekke varchar(80), dekketilstand varchar(80), tilgjengvurderingrullestol varchar(80), tilgjengvurderingelrullestol varchar(80), ogcfid int4, kommune varchar(80), opphav varchar(80), registrert timestamp, oppdatert timestamp, byggingpagar varchar(80), bilde varchar(80), kommentar varchar(500)
uutettsted.uutettstedinngangbygg (writer POSTGIS_3)
    attributes: objid int4,PRIKEY, objtype varchar(32), byggfunksjon varchar(80), avstandvanligparkering int4, avstandhc int4, rampe varchar(80), rampebredde int4, rampestigning float8, handlist varchar(80), handlisthoyde1 int4, handlisthoyde2 int4, rampeterskel float8, rampetilgjengelig varchar(80), dortype varchar(80), dorapner varchar(80), manoverknapphoyde int4, inngangbredde int4, terskelhoyde float8, ringeklokke varchar(80), ringeklokkehoyde int4, stigningadkomstvei float8, kontrast varchar(80), tilgjengvurderingrullestol varchar(80), tilgjengvurderingelrullestol varchar(80), tilgjengvurderingsyn varchar(80), ogcfid int4, kommune varchar(80), opphav varchar(80), registrert timestamp, oppdatert timestamp,
      byggingpagar varchar(80), bilde varchar(80), kommentar varchar(500)
uutettsted.uutettstedhcparkering (writer POSTGIS_3)
    attributes: objid int4,PRIKEY, objtype varchar(32), overbygg varchar(80), varmekabel varchar(80), skiltet varchar(80), merket varchar(80), bredde int4, lengde int4, avstandservicebygg int4, avgift varchar(80), automathoyde int4, tilgjengeligautomat varchar(80), tilgjengvurderingrullestol varchar(80), tilgjengvurderingelrullestol varchar(80), ogcfid int4, kommune varchar(80), opphav varchar(80), registrert timestamp, oppdatert timestamp, byggingpagar varchar(80), bilde varchar(80), kommentar varchar(500)
uutettsted.uutettstedvei (writer POSTGIS_3)
    attributes: objid int4,PRIKEY, objtype varchar(32), gatetype varchar(80), dekke varchar(80), dekketilstand varchar(80), bredde int4, nedsenk1 float8, nedsenk2 float8, stigning float8, tverrfall float8, moteplass varchar(80), varmekabel varchar(80), lyssignal varchar(80), lydsignal varchar(80), ledelinje varchar(80), ledelinjekontrast varchar(80), tilgjengvurderingrullestol varchar(80), tilgjengvurderingelrullestol varchar(80), tilgjengvurderingsyn varchar(80), ogcfid int4, kommune varchar(80), opphav varchar(80), registrert timestamp, oppdatert timestamp, byggingpagar varchar(80), bilde varchar(80), kommentar varchar(500)
