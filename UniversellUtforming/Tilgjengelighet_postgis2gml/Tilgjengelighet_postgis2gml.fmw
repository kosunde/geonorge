FME workspace Tilgjengelighet_postgis2gml.fmw
Shutdown Python:
      # -*- coding: utf-8 -*-
      #-------------------------------------------------------------------------------
      # Name:        zipfiles.py
      # Purpose:     Pakker filer i output folderen
      #
      # Author:      xsunknu
      #
      # Created:     18.09.2015
      # Copyright:   (c) xsunknu 2015
      # Licence:     <your licence>
      #-------------------------------------------------------------------------------

      import sys, os, zipfile, fme

      def zip(gmlfile, zfile):
          from os.path import basename

          # Lager korresponderende zip-fil av SOSI-fil
          if os.path.isfile(zfile):
              os.remove(zfile)

          zf = zipfile.ZipFile(zfile, "w", zipfile.ZIP_DEFLATED)

          # Ønsker ikke full sti inn i ZIP-filen
          arcname = basename(gmlfile)

          # ZIP-formatet støtter ikke non-ascii tegn
          # Erstatter AØÅæøå med ascii-tegn
          arcname = arcname.replace('\xc6', 'E')
          arcname = arcname.replace('\xd8', 'O')
          arcname = arcname.replace('\xc5', 'A')
          arcname = arcname.replace('\xe6', 'e')
          arcname = arcname.replace('\xf8', 'o')
          arcname = arcname.replace('\xe5', 'a')

          zf.write(gmlfile, arcname)
          zf.close()
          os.remove(gmlfile)

          return

      def main():

          # Kjøres ikke på FME Server, da FME Server selv sørger for pakkingen
          if not 'FME_SERVER_DEST_DIR' in fme.macroValues:
              if 'FANOUT_FOLDER' in fme.macroValues:
                  path = fme.macroValues['FANOUT_FOLDER']
                  for dirpath, dnames, fnames in os.walk(path):
                      for f in fnames:
                          if f.endswith(".gml"):
                              # Scanner gjennom alle GML-filer
                              gmlfile = os.path.join(path, f)
                              zfile = os.path.splitext(gmlfile)[0] + '.zip'
                              if os.path.isfile(zfile):

                                  # Korresponderende ZIP-fil finnes, sjekker timestamps
                                  gmltstamp = os.stat(gmlfile).st_mtime
                                  ziptstamp = os.stat(zfile).st_mtime

                                  if gmltstamp > ziptstamp:
                                      # SOSI-fil er nyere enn ZIP-fila, ZIP-fila oppdateres
                                      # SOSI-fila slettes
                                      try:
                                          zip(gmlfile, zfile)
                                      except:
                                          print 'Kunne ikke pakke: ' + gmlfile
                                  else:
                                      # SOSI-fila er eldre enn ZIP-fila
                                      # SOSI-fila slettes
                                      try:
                                          os.remove(gmlfile)
                                      except:
                                          print 'Kunne ikke slette: ' + gmlfile
                              else:
                                  # ZIP-fila eksisterer ikke og lages
                                  # SOSI-fila slettes
                                  try:
                                      zip(gmlfile, zfile)
                                  except:
                                      print 'Kunne ikke pakke: ' + gmlfile


      if __name__ == '__main__':
          main()

Parameters:
- KNR =   # Kommune(r)
- FNR =   # Fylke(r)
- CLIPPERCOORDS =   # Clipper coordinates
- CLIPPER_EPSG_CODE =   # Clipper coordinate system
- CLIPPER_FILE =   # "" Clipper file (any format)
- OUTPUT_EPSG_CODE = 25833   # Destination coordinate system
- FANOUT =   # Fanout områder
- CONFIG_FILE:   # Python Script
      #-------------------------------------------------------------------------------
      # Name:        GetConfigFile
      # Purpose:
      #
      # Author:      xsunknu
      #
      # Created:     21.08.2015
      # Copyright:   (c) xsunknu 2015
      # Licence:     <your licence>
      #-------------------------------------------------------------------------------
      
      import os, fme
      
      fmwdir = fme.macroValues['FME_MF_DIR']
      fmwfile = fme.macroValues['FME_MF_NAME']
      
      fmwfile = os.path.join(fmwdir, fmwfile)
      configfile = os.path.splitext(fmwfile)[0] + '_config.xml'
      
      return configfile
- CLIPPERCOORDSYS:   # Python Script
      #-------------------------------------------------------------------------------
      # Name:        SetCoordinateSystem
      # Purpose:
      #
      # Author:      xsunknu
      #
      # Created:     21.08.2015
      # Copyright:   (c) xsunknu 2015
      # Licence:     <your licence>
      #-------------------------------------------------------------------------------
      
      import os, fme
      
      EPSGvalue = fme.macroValues['CLIPPER_EPSG_CODE']
      EPSGcode  = 'EPSG:' + EPSGvalue
      
      return EPSGcode
- DESTCOORDSYS:   # Python Script
      #-------------------------------------------------------------------------------
      # Name:        SetCoordinateSystem
      # Purpose:
      #
      # Author:      xsunknu
      #
      # Created:     21.08.2015
      # Copyright:   (c) xsunknu 2015
      # Licence:     <your licence>
      #-------------------------------------------------------------------------------
      
      import os, fme
      
      EPSGvalue = fme.macroValues['OUTPUT_EPSG_CODE']
      EPSGcode  = 'EPSG:' + EPSGvalue
      
      return EPSGcode
- SPATIAL_FILTER:   # Python Script
      #-------------------------------------------------------------------------------
      # Name:        SetSpatialFilter
      # Purpose:
      #
      # Author:      xsunknu
      #
      # Created:     21.08.2015
      # Copyright:   (c) xsunknu 2015
      # Licence:     <your licence>
      #-------------------------------------------------------------------------------
      
      import fme
      
      spatialfilter = 'Intersects'
      
      knr = fme.macroValues['KNR']
      fnr = fme.macroValues['FNR']
      coords = fme.macroValues['CLIPPERCOORDS']
      file = fme.macroValues['CLIPPER_FILE']
      
      if knr == '' and fnr == '' and coords == '' and file == '':
          spatialfilter = '<No Spatial Filter>'
      
      return spatialfilter
- FIXEDCLIPPERCOORDS:   # Python Script
      #-------------------------------------------------------------------------------
      # Name:        FixClipperCoords
      # Purpose:
      #
      # Author:      xsunknu
      #
      # Created:     21.08.2015
      # Copyright:   (c) xsunknu 2015
      # Licence:     <your licence>
      #-------------------------------------------------------------------------------
      
      import fme
      clippercoords = fme.macroValues['CLIPPERCOORDS']
      
      if clippercoords == '':
          clippercoords = '1 1'
      
      return clippercoords
- HOVEDTEMA = UniversellUtforming   # Hovedtema
- UNDERTEMA = Tilgjengelighet   # Undertema
- PG_DB:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgdb').text
      
      return value
- PG_HOST:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pghost').text
      
      return value
- PG_PORT:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgport').text
      
      return value
- PG_USER:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pguser').text
      
      return value
- PG_PWD:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgpwd').text
      
      return value
- FANOUT_FOLDER:   # Python Script
      #-------------------------------------------------------------------------------
      # Name:        GetConfigFile
      # Purpose:
      #
      # Author:      xsunknu
      #
      # Created:     21.08.2015
      # Copyright:   (c) xsunknu 2015
      # Licence:     <your licence>
      #-------------------------------------------------------------------------------
      
      import os, fme
      from xml.etree import ElementTree as ET
      
      if 'FME_SERVER_DEST_DIR' in fme.macroValues:
          value = fme.macroValues['FME_SERVER_DEST_DIR']
      else:
          #Read XML config file
          configtree = ET.parse(fme.macroValues['CONFIG_FILE'])
          configdoc = configtree.getroot()
          value = configdoc.find('destdir').text
      
      return value
- XSD_FRILUFTSOMRADER:   # Python Script
      #
      # Author:      xsunknu
      #
      # Created:     21.08.2015
      # Copyright:   (c) xsunknu 2015
      # Licence:     <your licence>
      #-------------------------------------------------------------------------------
      
      import fme, os
      from xml.etree import ElementTree as ET
      
      #Read XML config file
      configtree = ET.parse(fme.macroValues['CONFIG_FILE'])
      configdoc = configtree.getroot()
      
      value = os.path.join(fme.macroValues['FME_MF_DIR'], configdoc.find('xsdfriluft').text)
      
      return value
- XSD_TETTSTED:   # Python Script
      #
      # Author:      xsunknu
      #
      # Created:     21.08.2015
      # Copyright:   (c) xsunknu 2015
      # Licence:     <your licence>
      #-------------------------------------------------------------------------------
      
      import fme, os
      from xml.etree import ElementTree as ET
      
      #Read XML config file
      configtree = ET.parse(fme.macroValues['CONFIG_FILE'])
      configdoc = configtree.getroot()
      
      value = os.path.join(fme.macroValues['FME_MF_DIR'], configdoc.find('xsdtettsted').text)
      
      return value
- LOG_FILE:   # Python Script
      #-------------------------------------------------------------------------------
      # Name:        GetConfigFile
      # Purpose:
      #
      # Author:      xsunknu
      #
      # Created:     21.08.2015
      # Copyright:   (c) xsunknu 2015
      # Licence:     <your licence>
      #-------------------------------------------------------------------------------
      
      import os, uuid, fme
      
      fmwdir = fme.macroValues['FME_MF_DIR']
      fmwfile = fme.macroValues['FME_MF_NAME']
      
      logdir = os.path.join(fmwdir, 'log')
      if not os.path.isdir(logdir):
          os.mkdir(logdir)
      
      logfile = os.path.splitext(fmwfile)[0] + '_' + str(uuid.uuid1()).replace('-','') + '.log'
      logfile = os.path.join(logdir, logfile)
      
      return logfile

Readers:
- POSTGIS_1: POSTGIS from $(PG_DB)

Writers:
- GML_1: GML to D:\scratch\tilgjengelighet.gml
- GML_2: GML to D:\scratch\tilgjengelighet2.gml

CreateClipper
    DESTCOORDSYS = $(DESTCOORDSYS)
    CLIPPERCOORDSYS = $(CLIPPERCOORDSYS)
    CLIPPERCOORDS = $(FIXEDCLIPPERCOORDS)
    -> Clipper [input 1]
    -> FeatureReader_3
FeatureTypeFilter
    ATTRIBUTES = uufriluftsomrader.uufriluftbaderampe,uufriluftsomrader.uufriluftfiskeplass,uufriluftsomrader.uufriluftfriluftsomrade,uufriluftsomrader.uufriluftgapahuk,uufriluftsomrader.uufriluftgrillbalplass,uufriluftsomrader.uufrilufthcparkering,uufriluftsomrader.uufriluftparkeringsomrade,uufriluftsomrader.uufriluftsittegruppe,uufriluftsomrader.uufrilufttoalett,uufriluftsomrader.uufriluftturvei,uufriluftsomrader.uufrilufthyttertilrettelagt,uufriluftsomrader.uufriluftstatligsikrafriluftsomrader,uutettsted.uutettstedhcparkering,uutettsted.uutettstedinngangbygg,uutettsted.uutettstedparkeringsomrade,uutettsted.uutettstedvei,<BLANK>,<UNFILTERED>
    uufriluftsomrader.uufriluftturvei -> AttributeCreator_2
    uufriluftsomrader.uufriluftstatligsikrafriluftsomrader -> AttributeCreator_4
    uufriluftsomrader.uufriluftsittegruppe -> AttributeCreator_5
    uufriluftsomrader.uufriluftparkeringsomrade -> AttributeCreator_6
    uufriluftsomrader.uufrilufthyttertilrettelagt -> AttributeCreator_7
    uufriluftsomrader.uufrilufthcparkering -> AttributeCreator_9
    uufriluftsomrader.uufriluftgrillbalplass -> AttributeCreator_10
    uufriluftsomrader.uufriluftgapahuk -> AttributeCreator_11
    uufriluftsomrader.uufriluftfriluftsomrade -> AttributeCreator_13
    uufriluftsomrader.uufriluftbaderampe -> AttributeCreator_14
    uutettsted.uutettstedvei -> AttributeCreator_15
    uutettsted.uutettstedhcparkering -> AttributeCreator_16
    uutettsted.uutettstedparkeringsomrade -> AttributeCreator_17
    uutettsted.uutettstedinngangbygg -> AttributeCreator_18
    uufriluftsomrader.uufriluftfiskeplass -> AttributeCreator_19
    uufriluftsomrader.uufrilufttoalett -> AttributeCreator_3

Bookmark: Fylke and/or kommune clippers
admingrense.fylkeflate (reader POSTGIS_1)
    attributes: fylkeid int4, navn varchar(80)
    -> Tester
    -> AttributeCreator_8
AttributeCreator_8
    ATTR_LIST = _clippercoords,$(CLIPPERCOORDS),_clipper_file,$(CLIPPER_FILE),_fnr,$(FNR),_knr,$(KNR)
    -> Tester_4
Tester_4
    TEST_DESCRIPTION = ""
    TEST_MODE = Automatic
    BOOL_OP = AND
    TEST_CLAUSE:
      TEST _clipper_file ATTRIBUTE_IS_EMPTY ""
      TEST _clippercoords ATTRIBUTE_IS_EMPTY ""
      TEST _fnr ATTRIBUTE_IS_EMPTY ""
      TEST _knr ATTRIBUTE_IS_EMPTY ""
    PASSED -> Reprojector_2
Tester
    TEST_DESCRIPTION = ""
    TEST_MODE = Automatic
    BOOL_OP = OR
    TEST_CLAUSE = TEST @Value(fylkeid) IN $(FNR)
    PASSED -> Reprojector_2
admingrense.kommuneflate (reader POSTGIS_1)
    attributes: kommuneid int4, navn varchar(80)
    -> Tester_2
Tester_2
    TEST_DESCRIPTION = ""
    TEST_MODE = Automatic
    BOOL_OP = OR
    TEST_CLAUSE = TEST @Value(kommuneid) IN $(KNR)
    PASSED -> Reprojector_2
Note: Sender inn hele landet som initiator / dersom alle klippeparametrene er / blanke
Reprojector_2
    INTERPOLATION_TYPE_NAME = Nearest Neighbor
    RASTER_CELL_SIZE = Preserve Cells
    SOURCE = Read from feature
    DEST = EPSG:4258
    REPROJECTED -> Clipper [input 1]
    REPROJECTED -> Dissolver

Bookmark: Clipper file (any format)
Creator
    GEOMTYPE = Geometry Object
    NUM = 1
    CREATED -> FeatureReader
FeatureReader
    ATTRIBUTES = NewFeatureType,
    INTERACT = $(SPATIAL_FILTER)
    DATASET = $(CLIPPER_FILE)
    ATTR_ACCUM_MODE = Only Use Result
    GENERIC_REAL_FORMAT = GUESS_FROM_EXTENSION
    FEATURETYPES_RADIO = FEATURETYPES
    FORMAT = GENERIC
    OUTPUT_FEATURES_DISPLAY = Based on Connections
    COMBINE_GEOM = Use Result
    <OTHER> -> Reprojector_3
Reprojector_3
    INTERPOLATION_TYPE_NAME = Nearest Neighbor
    RASTER_CELL_SIZE = Preserve Cells
    SOURCE = Read from feature
    DEST = EPSG:4258
    REPROJECTED -> Clipper [input 1]
    REPROJECTED -> Dissolver
DateFormatter
    FMT = FME Date/Time (%Y%m%d%H%M%S)
    INVALID_DATE_VALUE = _FME_NO_OP_

Bookmark: Leser features
Dissolver
    ACCUM_INPUT_ATTRS = No
    NO_OVRLP = No
    AREA -> FeatureReader_3
FeatureReader_3
    DATASET = $(PG_DB)
    POSTGIS_USE_SEARCH_ENVELOPE = NO
    POSTGIS_HOST = $(PG_HOST)
    OUTPUT_FEATURES_DISPLAY = Based on Connections
    POSTGIS_SCHEMALIST = uufriluftsomrader uutettsted
    ATTRIBUTES = uufriluftsomrader.uufriluftbaderampe,"objid,objtype,rampe,rampebredde,rampestigning,handlist,handlisthoyde1,handlisthoyde2,rampeterskel,rampetilgjengelig,tilgjengvurderingrullestol,tilgjengvurderingsyn,ogcfid,opphav,kommune,bilde,registrert,oppdatert,kommentar,forbedringsforslag",uufriluftsomrader.uufriluftfiskeplass,"objid,objtype,flytebrygge,rampe,rampebredde,rampestigning,handlist,handlisthoyde1,handlisthoyde2,rampeterskel,rampetilgjengelig,dekke,plankeavstand,dekketilstand,diametersnusirkel,rekkverk,stoppkant,stoppkanthoyde,tilgjengvurderingrullestol,tilgjengvurderingelrullestol,tilgjengvurderingsyn,ogcfid,opphav,kommune,bilde,registrert,oppdatert,kommentar,forbedringsforslag",uufriluftsomrader.uufriluftfriluftsomrade,"objid,objtype,navn,naturbasenr,parkeringsomrade,hcparkeringsplass,toalett,turvei,baderampe,fiskeplass,grillbalplass,sittegruppe,gapahuk,informasjon,annen,ogcfid,opphav,kommune,bilde,registrert,oppdatert,kommentar,forbedringsforslag",uufriluftsomrader.uufriluftgapahuk,"objid,objtype,rampe,rampebredde,rampestigning,handlist,handlisthoyde1,handlisthoyde2,rampeterskel,rampetilgjengelig,breddeinngang,hoydeinngang,terskelhoyde,kontrastinngang,diametersnusirkel,dekke,dekketilstand,tilgjengvurderingrullestol,tilgjengvurderingelrullestol,tilgjengvurderingsyn,ogcfid,opphav,kommune,bilde,registrert,oppdatert,kommentar,forbedringsforslag",uufriluftsomrader.uufriluftgrillbalplass,"objid,objtype,dekke,dekketilstand,helning,tilgjengvurderingrullestol,ogcfid,opphav,kommune,bilde,registrert,oppdatert,kommentar,forbedringsforslag",uufriluftsomrader.uufrilufthcparkering,"objid,objtype,skiltet,merket,bredde,lengde,avstandfasilitet,avgift,automathoyde,tilgjengeligautomat,tilgjengvurderingrullestol,tilgjengvurderingelrullestol,ogcfid,opphav,kommune,bilde,registrert,oppdatert,kommentar,forbedringsforslag",uufriluftsomrader.uufrilufthyttertilrettelagt,"objid,objtype,eier,lenke,navn,tilrettelagt,ogcfid,opphav,kommune,bilde,registrert,oppdatert,kommentar,forbedringsforslag",uufriluftsomrader.uufriluftparkeringsomrade,"objid,objtype,kapasitetpersonbiler,kapasitetuu,arstidsbruk,dekke,dekketilstand,tilgjengvurderingrullestol,tilgjengvurderingelrullestol,ogcfid,opphav,kommune,bilde,registrert,oppdatert,kommentar,forbedringsforslag",uufriluftsomrader.uufriluftsittegruppe,"objid,objtype,dekke,dekketilstand,helning,hoydebord,utstikkbord,tilgjengvurderingrullestol,ogcfid,opphav,kommune,bilde,registrert,oppdatert,kommentar,forbedringsforslag",uufriluftsomrader.uufriluftstatligsikrafriluftsomrader,"objid,objtype,linkbilde,linkskjema,naturbasenr,navn,ogcfid,opphav,kommune,bilde,registrert,oppdatert,kommentar,forbedringsforslag",uufriluftsomrader.uufrilufttoalett,"objid,objtype,byggtype,rampe,rampebredde,rampestigning,handlist,handlisthoyde1,handlisthoyde2,rampeterskel,rampetilgjengelighet,avstandhc,dortype,dorapner,manoverknapphoyde,breddeinngang,kontrastinngang,terskelhoyde,diametersnusirkel,belysning,omkledningtilgjengelig,servanttilgjengelig,wctilgjengelig,tilgjengvurderingrullestol,tilgjengvurderingelrullestol,tilgjengvurderingsyn,ogcfid,opphav,kommune,bilde,registrert,oppdatert,kommentar,forbedringsforslag",uufriluftsomrader.uufriluftturvei,"objid,objtype,veitype,spesialfotrutetype,arstidsbruk,sperrebom,sperrebomtilgjengelig,dekke,dekketilstand,motehvileplass,antalltilstrekkelig,belysning,bredde,stigning,tverrfall,frihoyde,ledelinje,ledelinjekontrast,tilgjengvurderingrullestol,tilgjengvurderingelrullestol,tilgjengvurderingsyn,ogcfid,opphav,kommune,bilde,registrert,oppdatert,kommentar,forbedringsforslag",uutettsted.uutettstedhcparkering,"objid,objtype,overbygg,varmekabel,skiltet,merket,bredde,lengde,avstandservicebygg,avgift,automathoyde,tilgjengeligautomat,tilgjengvurderingrullestol,tilgjengvurderingelrullestol,ogcfid,kommune,opphav,registrert,oppdatert,byggingpagar,bilde,kommentar",uutettsted.uutettstedinngangbygg,"objid,objtype,byggfunksjon,avstandvanligparkering,avstandhc,rampe,rampebredde,rampestigning,handlist,handlisthoyde1,handlisthoyde2,rampeterskel,rampetilgjengelig,dortype,dorapner,manoverknapphoyde,inngangbredde,terskelhoyde,ringeklokke,ringeklokkehoyde,stigningadkomstvei,kontrast,tilgjengvurderingrullestol,tilgjengvurderingelrullestol,tilgjengvurderingsyn,ogcfid,kommune,opphav,registrert,oppdatert,byggingpagar,bilde,kommentar",uutettsted.uutettstedparkeringsomrade,"objid,objtype,kapasitetpersonbiler,kapasitetuu,eierforhold,arstidsbruk,overbygg,varmekabel,dekke,dekketilstand,tilgjengvurderingrullestol,tilgjengvurderingelrullestol,ogcfid,kommune,opphav,registrert,oppdatert,byggingpagar,bilde,kommentar",uutettsted.uutettstedvei,"objid,objtype,gatetype,dekke,dekketilstand,bredde,nedsenk1,nedsenk2,stigning,tverrfall,moteplass,varmekabel,lyssignal,lydsignal,ledelinje,ledelinjekontrast,tilgjengvurderingrullestol,tilgjengvurderingelrullestol,tilgjengvurderingsyn,ogcfid,kommune,opphav,registrert,oppdatert,byggingpagar,bilde,kommentar"
    FEATURETYPES = uufriluftsomrader.uufriluftbaderampe uufriluftsomrader.uufriluftfiskeplass uufriluftsomrader.uufriluftfriluftsomrade uufriluftsomrader.uufriluftgapahuk uufriluftsomrader.uufriluftgrillbalplass uufriluftsomrader.uufrilufthcparkering uufriluftsomrader.uufriluftparkeringsomrade uufriluftsomrader.uufriluftsittegruppe uufriluftsomrader.uufrilufttoalett uufriluftsomrader.uufriluftturvei uutettsted.uutettstedhcparkering uutettsted.uutettstedinngangbygg uutettsted.uutettstedparkeringsomrade uutettsted.uutettstedvei uufriluftsomrader.uufrilufthyttertilrettelagt uufriluftsomrader.uufriluftstatligsikrafriluftsomrader
    POSTGIS_PASSWORD = $(PG_PWD)
    FORMAT = POSTGIS
    POSTGIS_USER_NAME = $(PG_USER)
    POSTGIS_USE_TRUE_POSTGIS_TYPES = yes
    POSTGIS_QUERY_FEATURE_TYPES_FOR_MERGE_FILTERS = Yes
    POSTGIS_PORT = $(PG_PORT)
    FEATURETYPES_RADIO = FEATURETYPES
    POSTGIS_CLIP_TO_ENVELOPE = NO
    POSTGIS_DISABLE_COLLECTION_SPLITTING = yes
    COMBINE_GEOM = Use Result
    INTERACT = Intersects
    ATTR_ACCUM_MODE = Only Use Result
    uufriluftsomrader.uufriluftbaderampe -> AttributeCreator_12
    uufriluftsomrader.uufriluftfiskeplass -> AttributeCreator_12
    uufriluftsomrader.uufriluftfriluftsomrade -> AttributeCreator_12
    uufriluftsomrader.uufriluftstatligsikrafriluftsomrader -> AttributeCreator_12
    uufriluftsomrader.uufrilufthyttertilrettelagt -> AttributeCreator_12
    uutettsted.uutettstedparkeringsomrade -> AttributeCreator_12
    uutettsted.uutettstedvei -> AttributeCreator_12
    uutettsted.uutettstedhcparkering -> AttributeCreator_12
    uutettsted.uutettstedinngangbygg -> AttributeCreator_12
    uufriluftsomrader.uufrilufttoalett -> AttributeCreator_12
    uufriluftsomrader.uufriluftturvei -> AttributeCreator_12
    uufriluftsomrader.uufriluftsittegruppe -> AttributeCreator_12
    uufriluftsomrader.uufriluftparkeringsomrade -> AttributeCreator_12
    uufriluftsomrader.uufrilufthcparkering -> AttributeCreator_12
    uufriluftsomrader.uufriluftgapahuk -> AttributeCreator_12
    uufriluftsomrader.uufriluftgrillbalplass -> AttributeCreator_12
AttributeCreator_12
    ATTR_LIST = _clippercoords,$(CLIPPERCOORDS),_clipper_file,$(CLIPPER_FILE),_fnr,$(FNR),_knr,$(KNR)
    -> TestFilter
TestFilter
    TEST_LIST:
      BOOL_OP,AND,COMPOSITE_TEST,<Unused>,TEST_CLAUSE,"TEST _clipper_file ATTRIBUTE_IS_EMPTY """"
      TEST _clippercoords ATTRIBUTE_IS_EMPTY """"
      TEST _fnr ATTRIBUTE_IS_EMPTY """"
      TEST _knr ATTRIBUTE_IS_EMPTY """"",Landsdekkende,BOOL_OP,AND,COMPOSITE_TEST,<Unused>,TEST_CLAUSE,"TEST _clipper_file ATTRIBUTE_IS_EMPTY """"
      TEST _clippercoords ATTRIBUTE_IS_EMPTY """"
      TEST _fnr NOT_ATTRIBUTE_IS_EMPTY """"
      TEST _knr ATTRIBUTE_IS_EMPTY """"",Fylkesvis,BOOL_OP,AND,COMPOSITE_TEST,<Unused>,TEST_CLAUSE,"TEST _clipper_file ATTRIBUTE_IS_EMPTY """"
      TEST _clippercoords ATTRIBUTE_IS_EMPTY """"
      TEST _fnr ATTRIBUTE_IS_EMPTY """"
      TEST _knr NOT_ATTRIBUTE_IS_EMPTY """"",Kommunevis
    DEFAULT_VALUE = <UNFILTERED>
    Fylkesvis -> Clipper [input 2]
    Kommunevis -> Clipper [input 2]
    <UNFILTERED> -> Clipper [input 2]
    Landsdekkende -> SosiFilenameSetter

Bookmark: Klipper
Clipper
    CLIPPED_ATTR = _clipped
    PRESERVE_CLIPPEE_EXTENTS = No
    ATTR_CONFLICT_RES = Use Clippee
    CREATE_AGGREGATES = No
    CLIP_TYPE = Multiple Clippers
    BOUNDARY_CASES = Treat as Inside
    ATTR_ACCUM_MODE = Merge Clipper
    INSIDE -> SosiFilenameSetter

Bookmark: Tagger og reprojiserer
SosiFilenameSetter
    SERVANTTILGJENGELIG = @Value(servanttilgjengelig)
    TILGJENGVURDERINGSYN = @Value(tilgjengvurderingsyn)
    INFORMASJON = @Value(informasjon)
    SPESIALFOTRUTETYPE = @Value(spesialfotrutetype)
    _CREATION_INSTANCE = @Value(_creation_instance)
    DEKKETILSTAND = @Value(dekketilstand)
    AVSTANDSERVICEBYGG = @Value(avstandservicebygg)
    KOMMENTAR = @Value(kommentar)
    KAPASITETUU = @Value(kapasitetuu)
    TILGJENGVURDERINGRULLESTOL = @Value(tilgjengvurderingrullestol)
    MANOVERKNAPPHOYDE = @Value(manoverknapphoyde)
    FANOUT = $(FANOUT)
    FISKEPLASS = @Value(fiskeplass)
    DEKKE = @Value(dekke)
    RAMPEBREDDE = @Value(rampebredde)
    HOYDEINNGANG = @Value(hoydeinngang)
    FORBEDRINGSFORSLAG = @Value(forbedringsforslag)
    RINGEKLOKKEHOYDE = @Value(ringeklokkehoyde)
    ANNEN = @Value(annen)
    PLANKEAVSTAND = @Value(plankeavstand)
    RINGEKLOKKE = @Value(ringeklokke)
    TILGJENGVURDERINGELRULLESTOL = @Value(tilgjengvurderingelrullestol)
    LEDELINJE = @Value(ledelinje)
    RAMPETILGJENGELIGHET = @Value(rampetilgjengelighet)
    LENGDE = @Value(lengde)
    VEITYPE = @Value(veitype)
    RAMPE = @Value(rampe)
    DORAPNER = @Value(dorapner)
    BREDDE = @Value(bredde)
    BADERAMPE = @Value(baderampe)
    _CLIPPERCOORDS = @Value(_clippercoords)
    KOMMUNEID = @Value(kommuneid)
    MOTEHVILEPLASS = @Value(motehvileplass)
    BYGGFUNKSJON = @Value(byggfunksjon)
    NATURBASENR = @Value(naturbasenr)
    OPPDATERT = @Value(oppdatert)
    HELNING = @Value(helning)
    KONTRAST = @Value(kontrast)
    SPERREBOMTILGJENGELIG = @Value(sperrebomtilgjengelig)
    AVGIFT = @Value(avgift)
    _KNR = @Value(_knr)
    UNDERTEMA = $(UNDERTEMA)
    TILGJENGELIGAUTOMAT = @Value(tilgjengeligautomat)
    PG_DB:
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------

      import fme
      from xml.etree import ElementTree as ET

      #Read XML config file
      configtree = ET.parse(fme.macroValues['CONFIG_FILE'])
      configdoc = configtree.getroot()
      value = configdoc.find('pgdb').text

      return value
    OUTPUT_EPSG_CODE = $(OUTPUT_EPSG_CODE)
    TVERRFALL = @Value(tverrfall)
    HANDLISTHOYDE1 = @Value(handlisthoyde1)
    GRILLBALPLASS = @Value(grillbalplass)
    NEDSENK1 = @Value(nedsenk1)
    HANDLISTHOYDE2 = @Value(handlisthoyde2)
    NEDSENK2 = @Value(nedsenk2)
    KONTRASTINNGANG = @Value(kontrastinngang)
    STOPPKANTHOYDE = @Value(stoppkanthoyde)
    AVSTANDVANLIGPARKERING = @Value(avstandvanligparkering)
    DIAMETERSNUSIRKEL = @Value(diametersnusirkel)
    AVSTANDHC = @Value(avstandhc)
    WCTILGJENGELIG = @Value(wctilgjengelig)
    PG_HOST:
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------

      import fme
      from xml.etree import ElementTree as ET

      #Read XML config file
      configtree = ET.parse(fme.macroValues['CONFIG_FILE'])
      configdoc = configtree.getroot()
      value = configdoc.find('pghost').text

      return value
    LYDSIGNAL = @Value(lydsignal)
    ANTALLTILSTREKKELIG = @Value(antalltilstrekkelig)
    OGCFID = @Value(ogcfid)
    EIERFORHOLD = @Value(eierforhold)
    AUTOMATHOYDE = @Value(automathoyde)
    _CLIPPED = @Value(_clipped)
    HCPARKERINGSPLASS = @Value(hcparkeringsplass)
    INNGANGBREDDE = @Value(inngangbredde)
    PG_PORT:
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------

      import fme
      from xml.etree import ElementTree as ET

      #Read XML config file
      configtree = ET.parse(fme.macroValues['CONFIG_FILE'])
      configdoc = configtree.getroot()
      value = configdoc.find('pgport').text

      return value
    STIGNING = @Value(stigning)
    BYGGTYPE = @Value(byggtype)
    HOYDEBORD = @Value(hoydebord)
    GAPAHUK = @Value(gapahuk)
    BELYSNING = @Value(belysning)
    AVSTANDFASILITET = @Value(avstandfasilitet)
    DORTYPE = @Value(dortype)
    PARKERINGSOMRADE = @Value(parkeringsomrade)
    OBJID = @Value(objid)
    FLYTEBRYGGE = @Value(flytebrygge)
    _FNR = @Value(_fnr)
    OBJTYPE = @Value(objtype)
    FRIHOYDE = @Value(frihoyde)
    _CLIPPER_FILE = @Value(_clipper_file)
    LYSSIGNAL = @Value(lyssignal)
    GATETYPE = @Value(gatetype)
    MERKET = @Value(merket)
    REGISTRERT = @Value(registrert)
    LEDELINJEKONTRAST = @Value(ledelinjekontrast)
    TURVEI = @Value(turvei)
    FYLKEID = @Value(fylkeid)
    RAMPESTIGNING = @Value(rampestigning)
    VARMEKABEL = @Value(varmekabel)
    BYGGINGPAGAR = @Value(byggingpagar)
    RAMPETERSKEL = @Value(rampeterskel)
    MOTEPLASS = @Value(moteplass)
    OPPHAV = @Value(opphav)
    UTSTIKKBORD = @Value(utstikkbord)
    KAPASITETPERSONBILER = @Value(kapasitetpersonbiler)
    OMKLEDNINGTILGJENGELIG = @Value(omkledningtilgjengelig)
    RAMPETILGJENGELIG = @Value(rampetilgjengelig)
    SKILTET = @Value(skiltet)
    NAVN = @Value(navn)
    PG_PWD:
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------

      import fme
      from xml.etree import ElementTree as ET

      #Read XML config file
      configtree = ET.parse(fme.macroValues['CONFIG_FILE'])
      configdoc = configtree.getroot()
      value = configdoc.find('pgpwd').text

      return value
    STOPPKANT = @Value(stoppkant)
    PG_USER:
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------

      import fme
      from xml.etree import ElementTree as ET

      #Read XML config file
      configtree = ET.parse(fme.macroValues['CONFIG_FILE'])
      configdoc = configtree.getroot()
      value = configdoc.find('pguser').text

      return value
    TERSKELHOYDE = @Value(terskelhoyde)
    BILDE = @Value(bilde)
    REKKVERK = @Value(rekkverk)
    TOALETT = @Value(toalett)
    ARSTIDSBRUK = @Value(arstidsbruk)
    BREDDEINNGANG = @Value(breddeinngang)
    HOVEDTEMA = $(HOVEDTEMA)
    OVERBYGG = @Value(overbygg)
    STIGNINGADKOMSTVEI = @Value(stigningadkomstvei)
    KOMMUNE = @Value(kommune)
    HANDLIST = @Value(handlist)
    SITTEGRUPPE = @Value(sittegruppe)
    SPERREBOM = @Value(sperrebom)
    -> Reprojector
Reprojector
    INTERPOLATION_TYPE_NAME = Nearest Neighbor
    RASTER_CELL_SIZE = Preserve Cells
    SOURCE = Read from feature
    DEST = $(DESTCOORDSYS)
    REPROJECTED -> AttributeCreator
AttributeCreator
    ATTR_LIST = ogc_fid,@Value(ogcfid),wkb_geometry,posisjon,kommune,"FME_CONDITIONAL:DEFAULT_VALUE''BOOL_OP;AND;COMPOSITE_TEST;<Unused>;TEST @Value(kommune) IN 0100-2099'@PadLeft(@Value(kommune), 4,  0)'BOOL_OP;AND;COMPOSITE_TEST;<Unused>;TEST @Value(kommuneid) IN 100-2099'@PadLeft(@Value(kommuneid), 4,  0)'FME_NUM_CONDITIONS3___"
    -> DateFormatter_2
DateFormatter_2
    SRCFMT = Unknown - Automatic Detection
    FMT = ISO DateTime (%Y-%m-%dT%H:%M:%S)
    DATE_ATTR = oppdatert,registrert
    -> NullAttributeMapper
NullAttributeMapper
    ATTRLIST = _clipped _clipper_file _clippercoords annen antalltilstrekkelig arstidsbruk automathoyde avgift avstandfasilitet avstandhc avstandservicebygg avstandvanligparkering baderampe belysning bilde bredde breddeinngang byggfunksjon byggingpagar byggtype dekke dekketilstand diametersnusirkel dorapner dortype eier eierforhold fiskeplass flytebrygge forbedringsforslag frihoyde fylkeid gapahuk gatetype grillbalplass handlist handlisthoyde1 handlisthoyde2 hcparkeringsplass helning hoydebord hoydeinngang informasjon inngangbredde kapasitetpersonbiler kapasitetuu kommentar kommune kommuneid kontrast kontrastinngang ledelinje ledelinjekontrast lengde lenke linkbilde linkskjema lydsignal lyssignal manoverknapphoyde merket motehvileplass moteplass naturbasenr navn nedsenk1 nedsenk2 objid objtype ogc_fid ogcfid omkledningtilgjengelig oppdatert opphav overbygg parkeringsomrade plankeavstand rampe rampebredde rampestigning rampeterskel rampetilgjengelig rampetilgjengelighet registrert rekkverk ringeklokke ringeklokkehoyde servanttilgjengelig sittegruppe skiltet sosifile sperrebom sperrebomtilgjengelig spesialfotrutetype stigning stigningadkomstvei stoppkant stoppkanthoyde terskelhoyde tilgjengeligautomat tilgjengvurderingelrullestol tilgjengvurderingrullestol tilgjengvurderingsyn tilrettelagt toalett turvei tverrfall undertema utstikkbord varmekabel veitype wctilgjengelig wkb_geometry
    ATTRCHOICE = Selected Attributes
    SOURCE_ATTR_VAL = Null Empty
    NULL_TREATMENT = Missing
    -> AttributeTrimmer
AttributeTrimmer
    TRIM_TO_NONE = Yes
    TRIM_TYPE = Both
    SRC_ATTRS = _matched_records,annen,antalltilstrekkelig,arstidsbruk,automathoyde,avgift,avstandfasilitet,avstandhc,avstandservicebygg,avstandvanligparkering,baderampe,belysning,bilde,bredde,breddeinngang,byggfunksjon,byggingpagar,byggtype,dekke,dekketilstand,diametersnusirkel,dorapner,dortype,eier,eierforhold,fiskeplass,flytebrygge,forbedringsforslag,frihoyde,fylkeid,gapahuk,gatetype,grillbalplass,handlist,handlisthoyde1,handlisthoyde2,hcparkeringsplass,helning,hoydebord,hoydeinngang,informasjon,inngangbredde,kapasitetpersonbiler,kapasitetuu,kommentar,kommune,kommuneid,kontrast,kontrastinngang,ledelinje,ledelinjekontrast,lengde,lenke,linkbilde,linkskjema,lydsignal,lyssignal,manoverknapphoyde,merket,motehvileplass,moteplass,naturbasenr,navn,nedsenk1,nedsenk2,objid,objtype,ogc_fid,ogcfid,omkledningtilgjengelig,oppdatert,opphav,overbygg,parkeringsomrade,plankeavstand,rampe,rampebredde,rampestigning,rampeterskel,rampetilgjengelig,rampetilgjengelighet,registrert,rekkverk,ringeklokke,ringeklokkehoyde,servanttilgjengelig,sittegruppe,skiltet,sosifile,sperrebom,sperrebomtilgjengelig,spesialfotrutetype,stigning,stigningadkomstvei,stoppkant,stoppkanthoyde,terskelhoyde,tilgjengeligautomat,tilgjengvurderingelrullestol,tilgjengvurderingrullestol,tilgjengvurderingsyn,tilrettelagt,toalett,turvei,tverrfall,undertema,utstikkbord,varmekabel,veitype,wctilgjengelig
    -> GeometryFilter
GeometryFilter
    BREAK_AGG = No
    GEOM_PORT_NAMES = Point Line Area
    POINT -> GeometryPropertySetter
    LINE -> GeometryPropertySetter_2
    AREA -> GeometryPropertySetter_3
GeometryPropertySetter
    OVERWRITE_CHOICE = Yes
    SETTYPE_PARAM = Geometry Name
    GEOM_NAME_FIELD = posisjon
    SET -> FeatureTypeFilter
GeometryPropertySetter_2
    OVERWRITE_CHOICE = Yes
    SETTYPE_PARAM = Geometry Name
    GEOM_NAME_FIELD = posisjon
    SET -> FeatureTypeFilter
GeometryPropertySetter_3
    OVERWRITE_CHOICE = Yes
    SETTYPE_PARAM = Geometry Name
    GEOM_NAME_FIELD = posisjon
    SET -> FeatureTypeFilter

Bookmark: Mapper attributter
AttributeCreator_2
    ATTR_LIST = spesialFotrutetype,@Value(spesialfotrutetype),årstidsbruk,@Value(arstidsbruk),sperrebomTilgjengelig,@Value(sperrebomtilgjengelig),dekkeTilstand,@Value(dekketilstand),møteHvileplass,@Value(motehvileplass),antallTilstrekkelig,@Value(antalltilstrekkelig),friHøyde,@Value(frihoyde),ledelinjeKontrast,@Value(ledelinjekontrast),tilgjengvurderingRullestol,@Value(tilgjengvurderingrullestol),tilgjengvurderingElRullestol,@Value(tilgjengvurderingelrullestol),tilgjengvurderingSyn,@Value(tilgjengvurderingsyn)
    -> UUFriluftTurvei (writer GML_1)
AttributeCreator_3
    ATTR_LIST = tilgjengvurderingRullestol,@Value(tilgjengvurderingrullestol),tilgjengvurderingElRullestol,@Value(tilgjengvurderingelrullestol),tilgjengvurderingSyn,@Value(tilgjengvurderingsyn),rampeBredde,@Value(rampebredde),rampeStigning,@Value(rampestigning),håndlist,@Value(handlist),håndlistHøyde1,@Value(handlisthoyde1),håndlistHøyde2,@Value(handlisthoyde2),rampeTerskel,@Value(rampeterskel),rampeTilgjengelig,@Value(rampetilgjengelig),avstandHC,@Value(avstandhc),dørtype,@Value(dortype),døråpner,@Value(dorapner),manøverknappHøyde,@Value(manoverknapphoyde),breddeInngang,@Value(breddeinngang),kontrastInngang,@Value(kontrastinngang),terskelHøyde,@Value(terskelhoyde),diameter,@Value(diametersnusirkel),omkledningTilgjengelig,@Value(omkledningtilgjengelig),servantTilgjengelig,@Value(servanttilgjengelig),wcTilgjengelig,@Value(wctilgjengelig)
    -> UUFriluftToalett (writer GML_1)
AttributeCreator_4
    ATTR_LIST = naturbaseNr,@Value(naturbasenr),linkBilde,@Value(linkbilde),linkSkjema,@Value(linkskjema)
    -> UUFriluftStatligSikraFriluftsområder (writer GML_1)
AttributeCreator_5
    ATTR_LIST = høydeBord,@Value(hoydebord),utstikkBord,@Value(utstikkbord),tilgjengvurderingRullestol,@Value(tilgjengvurderingrullestol)
    -> UUFriluftSittegruppe (writer GML_1)
AttributeCreator_6
    ATTR_LIST = kapasitetPersonbiler,@Value(kapasitetpersonbiler),kapasitetUU,@Value(kapasitetuu),årstidsbruk,@Value(arstidsbruk),dekkeTilstand,@Value(dekketilstand),tilgjengvurderingRullestol,@Value(tilgjengvurderingrullestol),tilgjengvurderingElRullestol,@Value(tilgjengvurderingelrullestol)
    -> UUFriluftParkeringsområde (writer GML_1)
AttributeCreator_7
    NUM_PRIOR_FEATURES = 0
    NUM_SUBSEQUENT_FEATURES = 0
    -> UUFriluftHytterTilrettelagt (writer GML_1)
AttributeCreator_9
    ATTR_LIST = avstandFasilitet,@Value(avstandfasilitet),automatHøyde,@Value(automathoyde),tilgjengeligAutomat,@Value(tilgjengeligautomat),tilgjengvurderingRullestol,@Value(tilgjengvurderingrullestol),tilgjengvurderingElRullestol,@Value(tilgjengvurderingelrullestol)
    -> UUFriluftHCparkering (writer GML_1)
AttributeCreator_10
    ATTR_LIST = tilgjengvurderingRullestol,@Value(tilgjengvurderingrullestol)
    -> UUFriluftGrillBålplass (writer GML_1)
AttributeCreator_19
    ATTR_LIST = tilgjengvurderingRullestol,@Value(tilgjengvurderingrullestol),rampeBredde,@Value(rampebredde),rampeStigning,@Value(rampestigning),håndlist,@Value(handlist),håndlistHøyde1,@Value(handlisthoyde1),håndlistHøyde2,@Value(handlisthoyde2),rampeTerskel,@Value(rampeterskel),rampeTilgjengelig,@Value(rampetilgjengelig),dekkeTilstand,@Value(dekketilstand),diameter,@Value(diametersnusirkel),stoppkantHøyde,@Value(stoppkanthoyde),tilgjengvurderingElRullestol,@Value(tilgjengvurderingelrullestol),tilgjengvurderingSyn,@Value(tilgjengvurderingsyn)
    -> UUFriluftFiskeplass (writer GML_1)
AttributeCreator_11
    ATTR_LIST = rampeBredde,@Value(rampebredde),rampeStigning,@Value(rampestigning),håndlist,@Value(handlist),håndlistHøyde1,@Value(handlisthoyde1),håndlistHøyde2,@Value(handlisthoyde2),rampeTerskel,@Value(rampeterskel),rampeTilgjengelig,@Value(rampetilgjengelig),dekkeTilstand,@Value(dekketilstand),diameter,@Value(diametersnusirkel),stoppkantHøyde,@Value(stoppkanthoyde),tilgjengvurderingRullestol,@Value(tilgjengvurderingrullestol),tilgjengvurderingElRullestol,@Value(tilgjengvurderingelrullestol),tilgjengvurderingSyn,@Value(tilgjengvurderingsyn)
    -> UUFriluftGapahuk (writer GML_1)
AttributeCreator_13
    ATTR_LIST = naturbaseNr,@Value(naturbasenr),parkeringsområde,@Value(parkeringsomrade),hcParkeringsplass,@Value(hcparkeringsplass),grillBålplass,@Value(grillbalplass)
    -> UUFriluftFriluftsområde (writer GML_1)
AttributeCreator_14
    ATTR_LIST = rampeBredde,@Value(rampebredde),rampeStigning,@Value(rampestigning),håndlist,@Value(handlist),håndlistHøyde1,@Value(handlisthoyde1),håndlistHøyde2,@Value(handlisthoyde2),rampeTerskel,@Value(rampeterskel),rampeTilgjengelig,@Value(rampetilgjengelig),tilgjengvurderingRullestol,@Value(tilgjengvurderingrullestol),tilgjengvurderingSyn,@Value(tilgjengvurderingsyn)
    -> UUFriluftBaderampe (writer GML_1)
AttributeCreator_15
    ATTR_LIST = byggingPågår,@Value(byggingpagar),dekkeTilstand,@Value(dekketilstand),møteplass,@Value(moteplass),ledelinjeKontrast,@Value(ledelinjekontrast),tilgjengvurderingRullestol,@Value(tilgjengvurderingrullestol),tilgjengvurderingElRullestol,@Value(tilgjengvurderingelrullestol),tilgjengvurderingSyn,@Value(tilgjengvurderingsyn)
    -> UUTettstedVei (writer GML_2)
AttributeCreator_16
    ATTR_LIST = byggingPågår,@Value(byggingpagar),avstandServicebygg,@Value(avstandservicebygg),automatHøyde,@Value(automathoyde),tilgjengeligAutomat,@Value(tilgjengeligautomat),tilgjengvuderingElRull,@Value(tilgjengvurderingelrullestol),tilgjengvurderingRullestol,@Value(tilgjengvurderingrullestol)
    -> UUTettstedHCparkering (writer GML_2)
AttributeCreator_17
    ATTR_LIST = byggingPågår,@Value(byggingpagar),tilgjengvurderingRullestol,@Value(tilgjengvurderingrullestol),tilgjengvuderingElRull,@Value(tilgjengvurderingelrullestol),kapasitetPersonbiler,@Value(kapasitetpersonbiler),kapasitetUU,@Value(kapasitetuu),årstidsbruk,@Value(arstidsbruk),dekkeTilstand,@Value(dekketilstand)
    -> UUTettstedParkeringsområde (writer GML_2)
AttributeCreator_18
    ATTR_LIST = tilgjengvurderingRullestol,@Value(tilgjengvurderingrullestol),tilgjengvuderingElRull,@Value(tilgjengvurderingelrullestol),byggFunksjon,@Value(byggfunksjon),avstandVanligParkering,@Value(avstandvanligparkering),avstandHC,@Value(avstandhc),rampeBredde,@Value(rampebredde),rampeStigning,@Value(rampestigning),håndlist,@Value(handlist),håndlistHøyde1,@Value(handlisthoyde1),håndlistHøyde2,@Value(handlisthoyde2),rampeTerskel,@Value(rampeterskel),rampeTilgjengelig,@Value(rampetilgjengelig),dørtype,@Value(dortype),døråpner,@Value(dorapner),manøverknappHøyde,@Value(manoverknapphoyde),inngangBredde,@Value(inngangbredde),terskelHøyde,@Value(terskelhoyde),ringeklokkeHøyde,@Value(ringeklokkehoyde),stigningAdkomstvei,@Value(stigningadkomstvei),tilgjengvurderingelrullestol,@Value(tilgjengvurderingsyn)
    -> UUTettstedInngangBygg (writer GML_2)

Bookmark: GML UUFriluftsOmråde
UUFriluftTurvei (writer GML_1)
    attributes: ogc_fid xml_int64, opphav xml_buffer, kommune xml_buffer, bilde xml_buffer, registrert xml_datetime, oppdatert xml_datetime, kommentar xml_buffer, forbedringsforslag xml_buffer, posisjon xml_geometry, veitype xml_buffer, spesialFotrutetype xml_buffer, årstidsbruk xml_buffer, sperrebom xml_buffer, sperrebomTilgjengelig xml_buffer, dekke xml_buffer, dekkeTilstand xml_buffer, møteHvileplass xml_buffer, antallTilstrekkelig xml_buffer, belysning xml_buffer, bredde xml_int64, stigning xml_real64, tverrfall xml_real64, friHøyde xml_buffer, ledelinje xml_buffer, ledelinjeKontrast xml_buffer, tilgjengvurderingRullestol xml_buffer, tilgjengvurderingElRullestol xml_buffer, tilgjengvurderingSyn xml_buffer
UUFriluftToalett (writer GML_1)
    attributes: ogc_fid xml_int64, opphav xml_buffer, kommune xml_buffer, bilde xml_buffer, registrert xml_datetime, oppdatert xml_datetime, kommentar xml_buffer, forbedringsforslag xml_buffer, posisjon xml_geometry, byggtype xml_buffer, rampe xml_buffer, rampeBredde xml_int64, rampeStigning xml_real64, håndlist xml_buffer, håndlistHøyde1 xml_int64, håndlistHøyde2 xml_int64, rampeTerskel xml_real64, rampeTilgjengelig xml_buffer, avstandHC xml_int64, dørtype xml_buffer, døråpner xml_buffer, manøverknappHøyde xml_int64, breddeInngang xml_int64, kontrastInngang xml_buffer, terskelhøyde xml_real64, diameter xml_int64, belysning xml_buffer, omkledningTilgjengelig xml_buffer, servantTilgjengelig xml_buffer, wcTilgjengelig xml_buffer,
      tilgjengvurderingRullestol xml_buffer, tilgjengvurderingElRullestol xml_buffer, tilgjengvurderingSyn xml_buffer
UUFriluftStatligSikraFriluftsområder (writer GML_1)
    attributes: ogc_fid xml_int64, opphav xml_buffer, kommune xml_buffer, bilde xml_buffer, registrert xml_datetime, oppdatert xml_datetime, kommentar xml_buffer, forbedringsforslag xml_buffer, posisjon xml_geometry, navn xml_buffer, naturbaseNr xml_buffer, linkBilde xml_buffer, linkSkjema xml_buffer
UUFriluftSittegruppe (writer GML_1)
    attributes: ogc_fid xml_int64, opphav xml_buffer, kommune xml_buffer, bilde xml_buffer, registrert xml_datetime, oppdatert xml_datetime, kommentar xml_buffer, forbedringsforslag xml_buffer, posisjon xml_geometry, dekke xml_buffer, dekketilstand xml_buffer, helning xml_real64, høydeBord xml_int64, utstikkBord xml_int64, tilgjengvurderingRullestol xml_buffer
UUFriluftParkeringsområde (writer GML_1)
    attributes: ogc_fid xml_int64, opphav xml_buffer, kommune xml_buffer, bilde xml_buffer, registrert xml_datetime, oppdatert xml_datetime, kommentar xml_buffer, forbedringsforslag xml_buffer, posisjon xml_geometry, kapasitetPersonbiler xml_int64, kapasitetUU xml_int64, årstidsbruk xml_buffer, dekke xml_buffer, dekkeTilstand xml_buffer, tilgjengvurderingRullestol xml_buffer, tilgjengvurderingElRullestol xml_buffer
UUFriluftHytterTilrettelagt (writer GML_1)
    attributes: ogc_fid xml_int64, opphav xml_buffer, kommune xml_buffer, bilde xml_buffer, registrert xml_datetime, oppdatert xml_datetime, kommentar xml_buffer, forbedringsforslag xml_buffer, posisjon xml_geometry, navn xml_buffer, eier xml_buffer, lenke xml_buffer, tilrettelagt xml_buffer
UUFriluftHCparkering (writer GML_1)
    attributes: ogc_fid xml_int64, opphav xml_buffer, kommune xml_buffer, bilde xml_buffer, registrert xml_datetime, oppdatert xml_datetime, kommentar xml_buffer, forbedringsforslag xml_buffer, posisjon xml_geometry, skiltet xml_buffer, merket xml_buffer, bredde xml_int64, lengde xml_int64, avstandFasilitet xml_int64, avgift xml_buffer, automatHøyde xml_int64, tilgjengeligAutomat xml_buffer, tilgjengvurderingRullestol xml_buffer, tilgjengvurderingElRullestol xml_buffer
UUFriluftGrillBålplass (writer GML_1)
    attributes: ogc_fid xml_int64, opphav xml_buffer, kommune xml_buffer, bilde xml_buffer, registrert xml_datetime, oppdatert xml_datetime, kommentar xml_buffer, forbedringsforslag xml_buffer, posisjon xml_geometry, dekke xml_buffer, dekketilstand xml_buffer, helning xml_real64, tilgjengvurderingRullestol xml_buffer
UUFriluftFiskeplass (writer GML_1)
    attributes: ogc_fid xml_int64, opphav xml_buffer, kommune xml_buffer, bilde xml_buffer, registrert xml_datetime, oppdatert xml_datetime, kommentar xml_buffer, forbedringsforslag xml_buffer, posisjon xml_geometry, flytebrygge xml_buffer, rampe xml_buffer, rampeBredde xml_int64, rampeStigning xml_real64, håndlist xml_buffer, håndlistHøyde1 xml_int64, håndlistHøyde2 xml_int64, rampeTerskel xml_real64, rampeTilgjengelig xml_buffer, dekke xml_buffer, plankeavstand xml_real64, dekkeTilstand xml_buffer, diameter xml_int64, rekkverk xml_buffer, stoppkant xml_buffer, stoppkantHøyde xml_real64, tilgjengvurderingRullestol xml_buffer, tilgjengvurderingElRullestol xml_buffer, tilgjengvurderingSyn xml_buffer
UUFriluftGapahuk (writer GML_1)
    attributes: ogc_fid xml_int64, opphav xml_buffer, kommune xml_buffer, bilde xml_buffer, registrert xml_datetime, oppdatert xml_datetime, kommentar xml_buffer, forbedringsforslag xml_buffer, posisjon xml_geometry, rampe xml_buffer, rampeBredde xml_int64, rampeStigning xml_real64, håndlist xml_buffer, håndlistHøyde1 xml_int64, håndlistHøyde2 xml_int64, rampeTerskel xml_real64, rampeTilgjengelig xml_buffer, breddeInngang xml_int64, høydeInngang xml_int64, terskelhøyde xml_real64, kontrastInngang xml_buffer, diameter xml_int64, dekke xml_buffer, dekkeTilstand xml_buffer, tilgjengvurderingRullestol xml_buffer, tilgjengvurderingElRullestol xml_buffer, tilgjengvurderingSyn xml_buffer
UUFriluftFriluftsområde (writer GML_1)
    attributes: ogc_fid xml_int64, opphav xml_buffer, kommune xml_buffer, bilde xml_buffer, registrert xml_datetime, oppdatert xml_datetime, kommentar xml_buffer, forbedringsforslag xml_buffer, posisjon xml_geometry, navn xml_buffer, naturbaseNr xml_int64, parkeringsområde xml_buffer, hcParkeringsplass xml_buffer, toalett xml_buffer, turvei xml_buffer, baderampe xml_buffer, fiskeplass xml_buffer, grillBålplass xml_buffer, sittegruppe xml_buffer, gapahuk xml_buffer, informasjon xml_buffer, annen xml_buffer
UUFriluftBaderampe (writer GML_1)
    attributes: ogc_fid xml_int64, opphav xml_buffer, kommune xml_buffer, bilde xml_buffer, registrert xml_datetime, oppdatert xml_datetime, kommentar xml_buffer, forbedringsforslag xml_buffer, posisjon xml_geometry, rampe xml_buffer, rampeBredde xml_int64, rampeStigning xml_real64, håndlist xml_buffer, håndlistHøyde1 xml_int64, håndlistHøyde2 xml_int64, rampeTerskel xml_real64, rampeTilgjengelig xml_buffer, tilgjengvurderingRullestol xml_buffer, tilgjengvurderingSyn xml_buffer

Bookmark: GML UUTettsted
UUTettstedVei (writer GML_2)
    attributes: ogc_fid xml_int64, kommune xml_buffer, opphav xml_buffer, registrert xml_datetime, oppdatert xml_datetime, byggingPågår xml_buffer, bilde xml_buffer, kommentar xml_buffer, tilgjengvurderingRullestol xml_buffer, posisjon xml_geometry, gatetype xml_buffer, dekke xml_buffer, dekkeTilstand xml_buffer, bredde xml_int64, nedsenk1 xml_real64, nedsenk2 xml_real64, stigning xml_real64, tverrfall xml_real64, møteplass xml_buffer, varmekabel xml_buffer, lyssignal xml_buffer, lydsignal xml_buffer, ledelinje xml_buffer, ledelinjeKontrast xml_buffer, tilgjengvuderingElRull xml_buffer, tilgjengvuderingSyn xml_buffer
UUTettstedHCparkering (writer GML_2)
    attributes: ogc_fid xml_int64, kommune xml_buffer, opphav xml_buffer, registrert xml_datetime, oppdatert xml_datetime, byggingPågår xml_buffer, bilde xml_buffer, kommentar xml_buffer, tilgjengvurderingRullestol xml_buffer, posisjon xml_geometry, overbygg xml_buffer, varmekabel xml_buffer, skiltet xml_buffer, merket xml_buffer, bredde xml_int64, lengde xml_int64, avstandServicebygg xml_int64, avgift xml_buffer, automatHøyde xml_int64, tilgjengeligAutomat xml_buffer, tilgjengvuderingElRull xml_buffer
UUTettstedParkeringsområde (writer GML_2)
    attributes: ogc_fid xml_int64, kommune xml_buffer, opphav xml_buffer, registrert xml_datetime, oppdatert xml_datetime, byggingPågår xml_buffer, bilde xml_buffer, kommentar xml_buffer, tilgjengvurderingRullestol xml_buffer, posisjon xml_geometry, kapasitetPersonbiler xml_int64, kapasitetUU xml_int64, eierforhold xml_buffer, årstidsbruk xml_buffer, overbygg xml_buffer, varmekabel xml_buffer, dekke xml_buffer, dekkeTilstand xml_buffer, tilgjengvuderingElRull xml_buffer
UUTettstedInngangBygg (writer GML_2)
    attributes: ogc_fid xml_int64, kommune xml_buffer, opphav xml_buffer, registrert xml_datetime, oppdatert xml_datetime, byggingPågår xml_buffer, bilde xml_buffer, kommentar xml_buffer, tilgjengvurderingRullestol xml_buffer, posisjon xml_geometry, byggFunksjon xml_buffer, avstandVanligParkering xml_int64, avstandHC xml_int64, rampe xml_buffer, rampeBredde xml_int64, rampeStigning xml_real64, håndlist xml_buffer, håndlistHøyde1 xml_int64, håndlistHøyde2 xml_int64, rampeTerskel xml_real64, rampeTilgjengelig xml_buffer, dørtype xml_buffer, døråpner xml_buffer, manøverknappHøyde xml_int64, inngangBredde xml_int64, terskelHøyde xml_real64, ringeklokke xml_buffer, ringeklokkeHøyde xml_int64, stigningAdkomstvei xml_real64, kontrast xml_buffer,
      tilgjengvuderingElRull xml_buffer, tilgjengvuderingtSyn xml_buffer

FME custom transformer SosiFilenameSetter

Parameters:
- OUTPUT_EPSG_CODE = 25832   # Destination coordinate system
- FANOUT = Kommuner   # Fanout områder
- UNDERTEMA =   # Undertema
- HOVEDTEMA =   # Hovedtema
- _CLIPPED = @Value(_clipped)   # Clipped
- _CLIPPER_FILE = @Value(_clipper_file)   # Clipper File
- _CLIPPERCOORDS = @Value(_clippercoords)   # Clippercoords
- _CREATION_INSTANCE = @Value(_creation_instance)   # Creation Instance
- _FNR = @Value(_fnr)   # Fnr
- _KNR = @Value(_knr)   # Knr
- ANNEN = @Value(annen)   # annen
- ANTALLTILSTREKKELIG = @Value(antalltilstrekkelig)   # antalltilstrekkelig
- ARSTIDSBRUK = @Value(arstidsbruk)   # arstidsbruk
- AUTOMATHOYDE = @Value(automathoyde)   # automathoyde
- AVGIFT = @Value(avgift)   # avgift
- AVSTANDFASILITET = @Value(avstandfasilitet)   # avstandfasilitet
- AVSTANDHC = @Value(avstandhc)   # avstandhc
- AVSTANDSERVICEBYGG = @Value(avstandservicebygg)   # avstandservicebygg
- AVSTANDVANLIGPARKERING = @Value(avstandvanligparkering)   # avstandvanligparkering
- BADERAMPE = @Value(baderampe)   # baderampe
- BELYSNING = @Value(belysning)   # belysning
- BILDE = @Value(bilde)   # bilde
- BREDDE = @Value(bredde)   # bredde
- BREDDEINNGANG = @Value(breddeinngang)   # breddeinngang
- BYGGFUNKSJON = @Value(byggfunksjon)   # byggfunksjon
- BYGGINGPAGAR = @Value(byggingpagar)   # byggingpagar
- BYGGTYPE = @Value(byggtype)   # byggtype
- DEKKE = @Value(dekke)   # dekke
- DEKKETILSTAND = @Value(dekketilstand)   # dekketilstand
- DIAMETERSNUSIRKEL = @Value(diametersnusirkel)   # diametersnusirkel
- DORAPNER = @Value(dorapner)   # dorapner
- DORTYPE = @Value(dortype)   # dortype
- EIERFORHOLD = @Value(eierforhold)   # eierforhold
- FISKEPLASS = @Value(fiskeplass)   # fiskeplass
- FLYTEBRYGGE = @Value(flytebrygge)   # flytebrygge
- FORBEDRINGSFORSLAG = @Value(forbedringsforslag)   # forbedringsforslag
- FRIHOYDE = @Value(frihoyde)   # frihoyde
- FYLKEID = @Value(fylkeid)   # fylkeid
- GAPAHUK = @Value(gapahuk)   # gapahuk
- GATETYPE = @Value(gatetype)   # gatetype
- GRILLBALPLASS = @Value(grillbalplass)   # grillbalplass
- HANDLIST = @Value(handlist)   # handlist
- HANDLISTHOYDE1 = @Value(handlisthoyde1)   # handlisthoyde1
- HANDLISTHOYDE2 = @Value(handlisthoyde2)   # handlisthoyde2
- HCPARKERINGSPLASS = @Value(hcparkeringsplass)   # hcparkeringsplass
- HELNING = @Value(helning)   # helning
- HOYDEBORD = @Value(hoydebord)   # hoydebord
- HOYDEINNGANG = @Value(hoydeinngang)   # hoydeinngang
- INFORMASJON = @Value(informasjon)   # informasjon
- INNGANGBREDDE = @Value(inngangbredde)   # inngangbredde
- KAPASITETPERSONBILER = @Value(kapasitetpersonbiler)   # kapasitetpersonbiler
- KAPASITETUU = @Value(kapasitetuu)   # kapasitetuu
- KOMMENTAR = @Value(kommentar)   # kommentar
- KOMMUNE = @Value(kommune)   # kommune
- KOMMUNEID = @Value(kommuneid)   # kommuneid
- KONTRAST = @Value(kontrast)   # kontrast
- KONTRASTINNGANG = @Value(kontrastinngang)   # kontrastinngang
- LEDELINJE = @Value(ledelinje)   # ledelinje
- LEDELINJEKONTRAST = @Value(ledelinjekontrast)   # ledelinjekontrast
- LENGDE = @Value(lengde)   # lengde
- LYDSIGNAL = @Value(lydsignal)   # lydsignal
- LYSSIGNAL = @Value(lyssignal)   # lyssignal
- MANOVERKNAPPHOYDE = @Value(manoverknapphoyde)   # manoverknapphoyde
- MERKET = @Value(merket)   # merket
- MOTEHVILEPLASS = @Value(motehvileplass)   # motehvileplass
- MOTEPLASS = @Value(moteplass)   # moteplass
- NATURBASENR = @Value(naturbasenr)   # naturbasenr
- NAVN = @Value(navn)   # navn
- NEDSENK1 = @Value(nedsenk1)   # nedsenk1
- NEDSENK2 = @Value(nedsenk2)   # nedsenk2
- OBJID = @Value(objid)   # objid
- OBJTYPE = @Value(objtype)   # objtype
- OGCFID = @Value(ogcfid)   # ogcfid
- OMKLEDNINGTILGJENGELIG = @Value(omkledningtilgjengelig)   # omkledningtilgjengelig
- OPPDATERT = @Value(oppdatert)   # oppdatert
- OPPHAV = @Value(opphav)   # opphav
- OVERBYGG = @Value(overbygg)   # overbygg
- PARKERINGSOMRADE = @Value(parkeringsomrade)   # parkeringsomrade
- PLANKEAVSTAND = @Value(plankeavstand)   # plankeavstand
- RAMPE = @Value(rampe)   # rampe
- RAMPEBREDDE = @Value(rampebredde)   # rampebredde
- RAMPESTIGNING = @Value(rampestigning)   # rampestigning
- RAMPETERSKEL = @Value(rampeterskel)   # rampeterskel
- RAMPETILGJENGELIG = @Value(rampetilgjengelig)   # rampetilgjengelig
- RAMPETILGJENGELIGHET = @Value(rampetilgjengelighet)   # rampetilgjengelighet
- REGISTRERT = @Value(registrert)   # registrert
- REKKVERK = @Value(rekkverk)   # rekkverk
- RINGEKLOKKE = @Value(ringeklokke)   # ringeklokke
- RINGEKLOKKEHOYDE = @Value(ringeklokkehoyde)   # ringeklokkehoyde
- SERVANTTILGJENGELIG = @Value(servanttilgjengelig)   # servanttilgjengelig
- SITTEGRUPPE = @Value(sittegruppe)   # sittegruppe
- SKILTET = @Value(skiltet)   # skiltet
- SPERREBOM = @Value(sperrebom)   # sperrebom
- SPERREBOMTILGJENGELIG = @Value(sperrebomtilgjengelig)   # sperrebomtilgjengelig
- SPESIALFOTRUTETYPE = @Value(spesialfotrutetype)   # spesialfotrutetype
- STIGNING = @Value(stigning)   # stigning
- STIGNINGADKOMSTVEI = @Value(stigningadkomstvei)   # stigningadkomstvei
- STOPPKANT = @Value(stoppkant)   # stoppkant
- STOPPKANTHOYDE = @Value(stoppkanthoyde)   # stoppkanthoyde
- TERSKELHOYDE = @Value(terskelhoyde)   # terskelhoyde
- TILGJENGELIGAUTOMAT = @Value(tilgjengeligautomat)   # tilgjengeligautomat
- TILGJENGVURDERINGELRULLESTOL = @Value(tilgjengvurderingelrullestol)   # tilgjengvurderingelrullestol
- TILGJENGVURDERINGRULLESTOL = @Value(tilgjengvurderingrullestol)   # tilgjengvurderingrullestol
- TILGJENGVURDERINGSYN = @Value(tilgjengvurderingsyn)   # tilgjengvurderingsyn
- TOALETT = @Value(toalett)   # toalett
- TURVEI = @Value(turvei)   # turvei
- TVERRFALL = @Value(tverrfall)   # tverrfall
- UTSTIKKBORD = @Value(utstikkbord)   # utstikkbord
- VARMEKABEL = @Value(varmekabel)   # varmekabel
- VEITYPE = @Value(veitype)   # veitype
- WCTILGJENGELIG = @Value(wctilgjengelig)   # wctilgjengelig
- PG_DB:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgdb').text
      
      return value
- PG_HOST:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pghost').text
      
      return value
- PG_PORT:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgport').text
      
      return value
- PG_PWD:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgpwd').text
      
      return value
- PG_USER:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pguser').text
      
      return value

Input (input)
    -> ParameterFetcher
ParameterFetcher
    ATTR_LIST = _output_epsg_code {$(OUTPUT_EPSG_CODE)} _fanout {$(FANOUT)}
    -> AttributeValueMapper
Note: Fikser kjente feil i kommunenummer
AttributeValueMapper
    LUT = 1901,1903
    SRC = kommuneid
    DEFAULT_VALUE = @Value(kommuneid)
    VAL_ATTR = kommuneid
    DIRECTION = Forward (Source To Destination)
    -> TestFilter_2
TestFilter_2
    TEST_LIST = BOOL_OP,OR,COMPOSITE_TEST,<Unused>,TEST_CLAUSE,"TEST $(FANOUT) = Kommuner",Kommuner,BOOL_OP,OR,COMPOSITE_TEST,<Unused>,TEST_CLAUSE,"TEST $(FANOUT) = Fylker",Fylker
    DEFAULT_VALUE = Ufiltrert
    Kommuner -> Joiner
    Fylker -> Joiner_2
    Ufiltrert -> FeatureTypeExtractor
Joiner
    POSTGIS_PORT = $(PG_PORT)
    JOIN_KEYS = kommuneid kommuneid
    DATASET = $(PG_DB)
    POSTGIS_DISABLE_COLLECTION_SPLITTING = yes
    POSTGIS_QUERY_FEATURE_TYPES_FOR_MERGE_FILTERS = Yes
    PREFETCH_EXHAUSTIVE = Yes
    TABLE = admingrense.kommuner
    POSTGIS_HOST = $(PG_HOST)
    POSTGIS_USE_TRUE_POSTGIS_TYPES = yes
    ADDED_FIELDS = navn
    MATCH_RULE_DISPLAY = Must Match Exactly One (1:1)
    POSTGIS_USER_NAME = $(PG_USER)
    POSTGIS_PASSWORD = $(PG_PWD)
    FORMAT = POSTGIS
    CACHE_SIZE = 5000
    JOINED -> StringReplacer_2
Joiner_2
    POSTGIS_PORT = $(PG_PORT)
    JOIN_KEYS = fylkeid fylkeid
    DATASET = $(PG_DB)
    POSTGIS_DISABLE_COLLECTION_SPLITTING = yes
    POSTGIS_QUERY_FEATURE_TYPES_FOR_MERGE_FILTERS = Yes
    PREFETCH_EXHAUSTIVE = Yes
    TABLE = admingrense.fylkeflate
    POSTGIS_HOST = $(PG_HOST)
    POSTGIS_USE_TRUE_POSTGIS_TYPES = yes
    ADDED_FIELDS = navn
    MATCH_RULE_DISPLAY = Must Match Exactly One (1:1)
    POSTGIS_USER_NAME = $(PG_USER)
    POSTGIS_PASSWORD = $(PG_PWD)
    FORMAT = POSTGIS
    CACHE_SIZE = 5000
    JOINED -> StringReplacer_2
FeatureTypeExtractor
    DEST_ATTR = _feature_type
    -> AttributeSplitter
AttributeSplitter
    ATTR_NAME = _feature_type
    DELIMITER = .
    DROP_EMPTY_PARTS = No
    TRIM_OPTION = Both
    LIST_NAME = _feature_type
    -> AttributeCreator
AttributeCreator
    ATTR_LIST = undertema,"FME_CONDITIONAL:DEFAULT_VALUE'Tilgjengelighet'BOOL_OP;OR;COMPOSITE_TEST;<Unused>;TEST @Value(_feature_type{0}) = uutettsted'Tettsted'BOOL_OP;OR;COMPOSITE_TEST;<Unused>;TEST @Value(_feature_type{0}) = uufriluftsomrader'Friluftsomrader'FME_NUM_CONDITIONS3___"
    -> AttributeCreator_13
AttributeCreator_13
    ATTR_LIST = sosifile,"FME_CONDITIONAL:DEFAULT_VALUE'$(HOVEDTEMA)_$(OUTPUT_EPSG_CODE)_@Value(undertema)_GML'BOOL_OP;OR;COMPOSITE_TEST;<Unused>;TEST $(FANOUT) LIKE Kommuner'$(HOVEDTEMA)_@PadLeft(@Value(kommuneid),4,0)_@Value(navn)_$(OUTPUT_EPSG_CODE)_@Value(undertema)_GML'BOOL_OP;OR;COMPOSITE_TEST;<Unused>;TEST $(FANOUT) LIKE Fylker'$(HOVEDTEMA)_@PadLeft(@Value(fylkeid),2,0)_@Value(navn)_$(OUTPUT_EPSG_CODE)_@Value(undertema)_GML'BOOL_OP;OR;COMPOSITE_TEST;<Unused>;TEST $(FANOUT) LIKE Norge'$(HOVEDTEMA)_0000_Norge_$(OUTPUT_EPSG_CODE)_@Value(undertema)_GML'FME_NUM_CONDITIONS4___"
    -> Output (output)
Output (output)

Bookmark: Substituerer ÆØÅ og mellomrom
StringReplacer_2
    FIND_TEXT = " "
    REPLACE_TEXT = _
    REGEXP = no
    CASE = no
    SRC_ATTRS = navn
    NO_MATCH = _FME_NO_OP_
    -> StringReplacer_3
StringReplacer_3
    FIND_TEXT = Æ
    REPLACE_TEXT = E
    REGEXP = no
    CASE = yes
    SRC_ATTRS = navn
    NO_MATCH = _FME_NO_OP_
    -> StringReplacer_4
StringReplacer_4
    FIND_TEXT = Ø
    REPLACE_TEXT = O
    REGEXP = no
    CASE = yes
    SRC_ATTRS = navn
    NO_MATCH = _FME_NO_OP_
    -> StringReplacer_5
StringReplacer_5
    FIND_TEXT = Å
    REPLACE_TEXT = A
    REGEXP = no
    CASE = yes
    SRC_ATTRS = navn
    NO_MATCH = _FME_NO_OP_
    -> StringReplacer_6
StringReplacer_6
    FIND_TEXT = æ
    REPLACE_TEXT = e
    REGEXP = no
    CASE = yes
    SRC_ATTRS = navn
    NO_MATCH = _FME_NO_OP_
    -> StringReplacer_7
StringReplacer_7
    FIND_TEXT = ø
    REPLACE_TEXT = o
    REGEXP = no
    CASE = yes
    SRC_ATTRS = navn
    NO_MATCH = _FME_NO_OP_
    -> StringReplacer_8
StringReplacer_8
    FIND_TEXT = å
    REPLACE_TEXT = a
    REGEXP = no
    CASE = yes
    SRC_ATTRS = navn
    NO_MATCH = _FME_NO_OP_
    -> FeatureTypeExtractor

FME custom transformer CreateClipper

Parameters:
- CLIPPERCOORDS = 253577 6650999 253577 6651246 253763 6651246 253763 6650999 253577 6650999   # Clipper Coordinate List
- CLIPPERCOORDSYS = EPSG:25833   # Clipper Coordinate System
- DESTCOORDSYS = "ESRIWKT|ETRS_1989_UTM_Zone_35N|PROJCS["ETRS_1989_UTM_Zone_35N",GEOGCS["GCS_ETRS_1989",DATUM["D_ETRS_1989",SPHEROID["GRS_1980",6378137.0,298.257222101]],PRIMEM["Greenwich",0.0],UNIT["Degree",0.0174532925199433]],PROJECTION["Transverse_Mercator"],PARAMETER["False_Easting",500000.0],PARAMETER["False_Northing",0.0],PARAMETER["Central_Meridian",27.0],PARAMETER["Scale_Factor",0.9996],PARAMETER["Latitude_Of_Origin",0.0],UNIT["Meter",1.0]]"   # Destination Coordinate System

Note: Creating geometry from / the Clipper coords
Creator
    GEOMTYPE = 2D Coordinate List
    COORDSYS = $(CLIPPERCOORDSYS)
    COORDS = $(CLIPPERCOORDS)
    NUM = 1
    CREATED -> BoundingBoxAccumulator
Note: Calculating the bounding / box (envelope) from the geometry
BoundingBoxAccumulator
    TOPFER_INDEX = No
    BOUNDING_BOX -> SpatialFilter [input 1]
    ORIGINAL -> SpatialFilter [input 2]
Note: If the geometry is equal to its / own bounding box - it is a rectangle!
SpatialFilter
    PREDICATES = EQUALS
    USE_BOUNDING_BOX = No
    CURVE_BOUNDARY_RULE_PARAM = Default Rule
    BASE_TYPE = Single Base
    PASS_CRITERIA = Pass Against One Base
    MERGE_ATTRS = No
    PREDATTR = _predicate
    PASSED -> Reprojector
    FAILED -> Reprojector_2
Note: If rectangle, reproject the / geometry to the destination / coordinate system
Reprojector
    INTERPOLATION_TYPE_NAME = Nearest Neighbor
    STROKE_ARCS = Yes
    RASTER_CELL_SIZE = Preserve Cells
    SOURCE = Read from feature
    DEST = $(DESTCOORDSYS)
    REPROJECTED -> BoundingBoxAccumulator_2
Note: Then calculate the bounding / box from the projected geoemtry
BoundingBoxAccumulator_2
    TOPFER_INDEX = No
    BOUNDING_BOX -> Reprojector_3
Note: Reproject the geometry back to / the DB coordsys (LL/EUREF89)
Reprojector_3
    INTERPOLATION_TYPE_NAME = Nearest Neighbor
    STROKE_ARCS = Yes
    RASTER_CELL_SIZE = Preserve Cells
    SOURCE = Read from feature
    DEST = EPSG:4258
    REPROJECTED -> GeometryFilter
Note: Reproject clipper to / the DB coordsys (LL/EUREF89)
Reprojector_2
    INTERPOLATION_TYPE_NAME = Nearest Neighbor
    STROKE_ARCS = Yes
    RASTER_CELL_SIZE = Preserve Cells
    SOURCE = Read from feature
    DEST = EPSG:4258
    REPROJECTED -> GeometryFilter
Note: Getting rid of dummies
GeometryFilter
    BREAK_AGG = No
    GEOM_PORT_NAMES = Area
    AREA -> Output (output)
Output (output)
