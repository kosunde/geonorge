FME workspace Brannsmitteomrader_sosi2postgis.fmw

Parameters:
- CONFIG_FILE:   # Python Script
      #-------------------------------------------------------------------------------
      # Name:        GetConfigFile
      # Purpose:
      #
      # Author:      xsunknu
      #
      # Created:     21.08.2015
      # Copyright:   (c) xsunknu 2015
      # Licence:     <your licence>
      #-------------------------------------------------------------------------------
      
      import os, fme
      
      fmwdir = fme.macroValues['FME_MF_DIR']
      fmwfile = fme.macroValues['FME_MF_NAME']
      
      fmwfile = os.path.join(fmwdir, fmwfile)
      configfile = os.path.splitext(fmwfile)[0] + '_config.xml'
      
      return configfile
- FTP_URL:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('ftpurl').text
      
      return value
- FTP_USER:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('ftpuser').text
      
      return value
- FTP_PWD:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('ftppwd').text
      
      return value
- SOSI_IN:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('sosiin').text
      
      return value
- LOG_FILE:   # Python Script
      #-------------------------------------------------------------------------------
      # Name:        GetConfigFile
      # Purpose:
      #
      # Author:      xsunknu
      #
      # Created:     21.08.2015
      # Copyright:   (c) xsunknu 2015
      # Licence:     <your licence>
      #-------------------------------------------------------------------------------
      
      import os, uuid, fme
      
      fmwdir = fme.macroValues['FME_MF_DIR']
      fmwfile = fme.macroValues['FME_MF_NAME']
      
      logdir = os.path.join(fmwdir, 'log')
      if not os.path.isdir(logdir):
          os.mkdir(logdir)
      
      logfile = os.path.splitext(fmwfile)[0] + '_' + str(uuid.uuid1()).replace('-','') + '.log'
      logfile = os.path.join(logdir, logfile)
      
      return logfile
- PG_DB:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgdb').text
      
      return value

Writers:
- POSTGIS_1: POSTGIS to $(PG_DB)

Creator
    GEOMTYPE = Geometry Object
    NUM = 1
    CREATED -> FTPCaller
Note: Laster ned SOSI-fil med FTP / til en attributt
FTPCaller
    FTP_PASSWORD = $(FTP_PWD)
    ERROR_ATTR = _error
    TARGET_ATTR_ENCODING = utf-8
    TRANSFER_TYPE = Download to an Attribute
    MODE = Binary
    TARGET_ATTR = _file_contents
    FTP_USERNAME = $(FTP_USER)
    VERIFY_SSL_CERTIFICATES = Yes
    REMOTE_URL = $(FTP_URL)
    -> PythonCaller
Note: Fjerner uønskede tegn / i SOSI-fila
PythonCaller
    PYTHONSOURCE:
      import fme
      import fmeobjects

      def SosiVasker(feature):
          # Removing unvanted character in the SOSI-file
          sosi = unicode(feature.getAttribute("_file_contents"))
          sosi = sosi.replace(chr(26), '')
          feature.setAttribute("_file_contents", sosi)
    NEW_ATTRIBUTES = _file_contents
    PYTHONSYMBOL = SosiVasker
    -> AttributeFileWriter
Note: Lagrer SOSI-fila / til disk.
AttributeFileWriter
    FILE_NAME = $(SOSI_IN)
    OVERWRITE_FILE = Overwrite file
    SOURCE_ATTR = _file_contents
    CHAR_ENCODING = utf-8
    -> FeatureReader
Note: Leser SOSI-fil
FeatureReader
    SOSI_READER_LOG_ERRORS = yes
    OUTPUT_FEATURES_DISPLAY = Based on Connections
    SOSI_READER_MISSING_Z_VALUE = -9999
    SOSI_READER_ALLOW_MISSING_MANDATORY_ATTRS = yes
    INTERACT = <No Spatial Filter>
    COMBINE_GEOM = Use Result
    SOSI_READER_REFERENCE_SCALE = 1
    DATASET = $(SOSI_IN)
    ATTR_ACCUM_MODE = Only Use Result
    SOSI_READER_ENFORCE_Z_VALUES = Auto-detect
    ATTRIBUTES = BrannfareomradeGrense,"fme_geometry{0},SOSI_id",Trehusmiljo,"fme_geometry{0},SOSI_id"
    SOSI_READER_ATTRIBUTE_VALIDATION_LEVEL = Basic
    SOSI_READER_LOG_WARNINGS = no
    FORMAT = SOSI
    FEATURETYPES = Trehusmiljo BrannfareomradeGrense
    FEATURETYPES_RADIO = FEATURETYPES
    Trehusmiljo -> AttributeExposer
    BrannfareomradeGrense -> AttributeExposer
Note: Eksponerer attributtene
AttributeExposer
    ATTR_LIST = DATAUTTAKSDATO,FORSTEDIGITALISERINGSDATO,INFORMASJON,KOMM,LINK,LOKALID,MALEMETODE,NAVN,NAVNEROM,NOYAKTIGHET,OBJTYPE,OPPHAV,SOSI_id,VERSJONID
    -> BulkAttributeRenamer
Note: Renamer attributtene til / lowercase
BulkAttributeRenamer
    PATTERN_ACTION_DISP = Change Case
    CASE_CHANGE_TYPE = lowercase
    ATTRCHOICE = All Attributes
    -> AttributeCreator
Note: Setter ID'er
AttributeCreator
    ATTR_LIST = objid,@Value(sosi_id)
    -> Reprojector
Note: Reprojiserer
Reprojector
    SOURCE = Read from feature
    DEST = EPSG:4258
    RASTER_CELL_SIZE = Preserve Cells
    INTERPOLATION_TYPE_NAME = Nearest Neighbor
    REPROJECTED -> GeometryFilter
Note: Skiller flater og linjer
GeometryFilter
    GEOM_PORT_NAMES = Point Line Arc Area
    BREAK_AGG = No
    AREA -> UUIDGenerator
    LINE -> brannsmitteomrader.brannfareomradegrense (writer POSTGIS_1)
UUIDGenerator
    UUID_ATTR = lokalid
    -> AttributeCreator_2
AttributeCreator_2
    ATTR_LIST = navnerom,@Value(navnerom),objtype,"FME_CONDITIONAL:DEFAULT_VALUE'@Value(objtype)'BOOL_OP;OR;COMPOSITE_TEST;<Unused>;TEST @Value(objtype) = Trehusmiljø'Brannfareområde'FME_NUM_CONDITIONS2___"
    -> brannsmitteomrader.brannfareomrade (writer POSTGIS_1)

Bookmark: PostGIS
brannsmitteomrader.brannfareomradegrense (writer POSTGIS_1)
    attributes: objid int4,PRIKEY, objtype varchar(32)
brannsmitteomrader.brannfareomrade (writer POSTGIS_1)
    attributes: objid int4,PRIKEY, objtype varchar(32), navn varchar(80), datauttaksdato timestamp, forstedigitaliseringsdato timestamp, lokalid varchar(80), navnerom varchar(80), versjonid varchar(80), informasjon varchar(80), komm varchar(80), malemetode varchar(80), noyaktighet int4, oppdateringsdato timestamp, opphav varchar(80), link varchar(255)
