FME workspace Trehusmiljoer_sosi2postgis.fmw

Parameters:
- CONFIG_FILE:   # Python Script
      #-------------------------------------------------------------------------------
      # Name:        GetConfigFile
      # Purpose:
      #
      # Author:      xsunknu
      #
      # Created:     21.08.2015
      # Copyright:   (c) xsunknu 2015
      # Licence:     <your licence>
      #-------------------------------------------------------------------------------
      
      import os, fme
      
      fmwdir = fme.macroValues['FME_MF_DIR']
      fmwfile = fme.macroValues['FME_MF_NAME']
      
      fmwfile = os.path.join(fmwdir, fmwfile)
      configfile = os.path.splitext(fmwfile)[0] + '_config.xml'
      
      return configfile
- FTP_URL:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('ftpurl').text
      
      return value
- FTP_USER:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('ftpuser').text
      
      return value
- FTP_PWD:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('ftppwd').text
      
      return value
- SOSI_IN:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('sosiin').text
      
      return value
- LOG_FILE:   # Python Script
      #-------------------------------------------------------------------------------
      # Name:        GetConfigFile
      # Purpose:
      #
      # Author:      xsunknu
      #
      # Created:     21.08.2015
      # Copyright:   (c) xsunknu 2015
      # Licence:     <your licence>
      #-------------------------------------------------------------------------------
      
      import os, uuid, fme
      
      fmwdir = fme.macroValues['FME_MF_DIR']
      fmwfile = fme.macroValues['FME_MF_NAME']
      
      logdir = os.path.join(fmwdir, 'log')
      if not os.path.isdir(logdir):
          os.mkdir(logdir)
      
      logfile = os.path.splitext(fmwfile)[0] + '_' + str(uuid.uuid1()).replace('-','') + '.log'
      logfile = os.path.join(logdir, logfile)
      
      return logfile
- PG_DB:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgdb').text
      
      return value

Writers:
- POSTGIS_1: POSTGIS to $(PG_DB)

Creator
    GEOMTYPE = Geometry Object
    NUM = 1
    CREATED -> FTPCaller
Note: Laster ned SOSI-fil med FTP / til en attributt
FTPCaller
    FTP_PASSWORD = $(FTP_PWD)
    VERIFY_SSL_CERTIFICATES = Yes
    TARGET_ATTR_ENCODING = utf-8
    TARGET_ATTR = _file_contents
    REMOTE_URL = $(FTP_URL)
    FTP_USERNAME = $(FTP_USER)
    MODE = Binary
    ERROR_ATTR = _error
    TRANSFER_TYPE = Download to an Attribute
    -> PythonCaller
Note: Fjerner uønskede tegn / i SOSI-fila
PythonCaller
    NEW_ATTRIBUTES = _file_contents
    PYTHONSOURCE:
      import fme
      import fmeobjects

      def SosiVasker(feature):
          # Removing unvanted character in the SOSI-file
          sosi = unicode(feature.getAttribute("_file_contents"))
          sosi = sosi.replace(chr(26), '')
          feature.setAttribute("_file_contents", sosi)
    PYTHONSYMBOL = SosiVasker
    -> AttributeFileWriter
Note: Lagrer SOSI-fila / til disk.
AttributeFileWriter
    FILE_NAME = $(SOSI_IN)
    SOURCE_ATTR = _file_contents
    CHAR_ENCODING = utf-8
    OVERWRITE_FILE = Overwrite file
    -> FeatureReader
Note: Leser SOSI-fil
FeatureReader
    FEATURETYPES_RADIO = FEATURETYPES
    ATTRIBUTES = Trehusmiljo,"fme_geometry{0},SOSI_id",TrehusmiljoGrense,"fme_geometry{0},SOSI_id"
    ATTR_ACCUM_MODE = Only Use Result
    FEATURETYPES = Trehusmiljo TrehusmiljoGrense
    FORMAT = SOSI
    SOSI_READER_LOG_WARNINGS = no
    SOSI_READER_ENFORCE_Z_VALUES = Auto-detect
    DATASET = $(SOSI_IN)
    SOSI_READER_REFERENCE_SCALE = 1
    SOSI_READER_LOG_ERRORS = yes
    COMBINE_GEOM = Use Result
    SOSI_READER_ALLOW_MISSING_MANDATORY_ATTRS = yes
    SOSI_READER_ATTRIBUTE_VALIDATION_LEVEL = Basic
    OUTPUT_FEATURES_DISPLAY = Based on Connections
    SOSI_READER_MISSING_Z_VALUE = -9999
    INTERACT = <No Spatial Filter>
    Trehusmiljo -> AttributeExposer
    TrehusmiljoGrense -> AttributeExposer
Note: Eksponerer attributtene
AttributeExposer
    ATTR_LIST = DATAUTTAKSDATO,FORSTEDIGITALISERINGSDATO,INFORMASJON,KOMM,LINK,LOKALID,MALEMETODE,NAVN,NAVNEROM,NOYAKTIGHET,OBJTYPE,OPPHAV,SOSI_id,VERN_LOV,VERSJONID
    -> BulkAttributeRenamer
Note: Renamer attributtene til / lowercase
BulkAttributeRenamer
    PATTERN_ACTION_DISP = Change Case
    CASE_CHANGE_TYPE = lowercase
    ATTRCHOICE = All Attributes
    -> AttributeCreator
Note: Setter ID'er
AttributeCreator
    ATTR_LIST = objid,@Value(sosi_id)
    -> Reprojector
Note: Reprojiserer
Reprojector
    DEST = EPSG:4258
    INTERPOLATION_TYPE_NAME = Nearest Neighbor
    RASTER_CELL_SIZE = Preserve Cells
    SOURCE = Read from feature
    REPROJECTED -> GeometryFilter
Note: Skiller flater og linjer
GeometryFilter
    GEOM_PORT_NAMES = Point Line Arc Area
    BREAK_AGG = No
    LINE -> trehusmiljo.trehusmiljogrense (writer POSTGIS_1)
    ARC -> trehusmiljo.trehusmiljogrense (writer POSTGIS_1)
    AREA -> UUIDGenerator
UUIDGenerator
    UUID_ATTR = lokalid
    -> AttributeCreator_2
AttributeCreator_2
    ATTR_LIST = navnerom,RA_Trehusmiljoer_DOK
    -> trehusmiljo.trehusmiljo (writer POSTGIS_1)

Bookmark: PostGIS
trehusmiljo.trehusmiljogrense (writer POSTGIS_1)
    attributes: objid int4,PRIKEY, objtype varchar(32)
trehusmiljo.trehusmiljo (writer POSTGIS_1)
    attributes: objid int4,PRIKEY, objtype varchar(32), navn varchar(80), vern_lov varchar(80), lokalid varchar(80), navnerom varchar(80), versjonid varchar(80), forstedigitaliseringsdato timestamp, oppdateringsdato timestamp, datauttaksdato timestamp, malemetode varchar(80), noyaktighet int4, opphav varchar(80), komm varchar(80), informasjon varchar(255), link varchar(255)
