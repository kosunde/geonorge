FME workspace Trehusmiljoer_postgis2gml.fmw
Shutdown Python:
      # -*- coding: utf-8 -*-
      #-------------------------------------------------------------------------------
      # Name:        zipfiles.py
      # Purpose:     Pakker filer i output folderen
      #
      # Author:      xsunknu
      #
      # Created:     18.09.2015
      # Copyright:   (c) xsunknu 2015
      # Licence:     <your licence>
      #-------------------------------------------------------------------------------

      import sys, os, zipfile, fme

      def zip(gmlfile, zfile):
          from os.path import basename

          # Lager korresponderende zip-fil av gml-fil
          if os.path.isfile(zfile):
              os.remove(zfile)

          zf = zipfile.ZipFile(zfile, "w", zipfile.ZIP_DEFLATED)

          # Ønsker ikke full sti inn i ZIP-filen
          arcname = basename(gmlfile)

          # ZIP-formatet støtter ikke non-ascii tegn
          # Erstatter AØÅæøå med ascii-tegn
          arcname = arcname.replace(u'\xc6', 'E')
          arcname = arcname.replace(u'\xd8', 'O')
          arcname = arcname.replace(u'\xc5', 'A')
          arcname = arcname.replace(u'\xe6', 'e')
          arcname = arcname.replace(u'\xf8', 'o')
          arcname = arcname.replace(u'\xe5', 'a')

          zf.write(gmlfile, arcname)
          zf.close()
          os.remove(gmlfile)

          return

      def main():

          # Kjøres ikke på FME Server, da FME Server selv sørger for pakkingen
          if not 'FME_SERVER_DEST_DIR' in fme.macroValues:
              if 'FANOUT_FOLDER' in fme.macroValues:
                  path = fme.macroValues['FANOUT_FOLDER']
                  for dirpath, dnames, fnames in os.walk(path):
                      for f in fnames:
                          if f.endswith(".gml"):
                              # Scanner gjennom alle gml-filer
                              gmlfile = os.path.join(path, f)
                              zfile = os.path.splitext(gmlfile)[0] + '.zip'
                              if os.path.isfile(zfile):

                                  # Korresponderende ZIP-fil finnes, sjekker timestamps
                                  gmltstamp = os.stat(gmlfile).st_mtime
                                  ziptstamp = os.stat(zfile).st_mtime

                                  if gmltstamp > ziptstamp:
                                      # gml-fil er nyere enn ZIP-fila, ZIP-fila oppdateres
                                      # gml-fila slettes
                                      try:
                                          zip(gmlfile, zfile)
                                      except:
                                          print 'Kunne ikke pakke: ' + gmlfile
                                  else:
                                      # gml-fila er eldre enn ZIP-fila
                                      # gml-fila slettes
                                      try:
                                          os.remove(gmlfile)
                                      except:
                                          print 'Kunne ikke slette: ' + gmlfile
                              else:
                                  # ZIP-fila eksisterer ikke og lages
                                  # gml-fila slettes
                                  try:
                                      zip(gmlfile, zfile)
                                  except:
                                      print 'Kunne ikke pakke: ' + gmlfile


      if __name__ == '__main__':
          main()

Parameters:
- KNR =   # Kommune(r)
- FNR =   # Fylke(r)
- CLIPPERCOORDS =   # Clipper coordinates
- CLIPPER_EPSG_CODE =   # Clipper coordinate system
- CLIPPER_FILE =   # "" Clipper file (any format)
- OUTPUT_EPSG_CODE = 25833   # Destination coordinate system
- FANOUT = Norge   # Fanout områder
- CONFIG_FILE:   # Python Script
      #-------------------------------------------------------------------------------
      # Name:        GetConfigFile
      # Purpose:
      #
      # Author:      xsunknu
      #
      # Created:     21.08.2015
      # Copyright:   (c) xsunknu 2015
      # Licence:     <your licence>
      #-------------------------------------------------------------------------------
      
      import os, fme
      
      fmwdir = fme.macroValues['FME_MF_DIR']
      fmwfile = fme.macroValues['FME_MF_NAME']
      
      fmwfile = os.path.join(fmwdir, fmwfile)
      configfile = os.path.splitext(fmwfile)[0] + '_config.xml'
      
      return configfile
- CLIPPERCOORDSYS:   # Python Script
      #-------------------------------------------------------------------------------
      # Name:        SetCoordinateSystem
      # Purpose:
      #
      # Author:      xsunknu
      #
      # Created:     21.08.2015
      # Copyright:   (c) xsunknu 2015
      # Licence:     <your licence>
      #-------------------------------------------------------------------------------
      
      import os, fme
      
      EPSGvalue = fme.macroValues['CLIPPER_EPSG_CODE']
      EPSGcode  = 'EPSG:' + EPSGvalue
      
      return EPSGcode
- DESTCOORDSYS:   # Python Script
      #-------------------------------------------------------------------------------
      # Name:        SetCoordinateSystem
      # Purpose:
      #
      # Author:      xsunknu
      #
      # Created:     21.08.2015
      # Copyright:   (c) xsunknu 2015
      # Licence:     <your licence>
      #-------------------------------------------------------------------------------
      
      import os, fme
      
      EPSGvalue = fme.macroValues['OUTPUT_EPSG_CODE']
      EPSGcode  = 'EPSG:' + EPSGvalue
      
      return EPSGcode
- SPATIAL_FILTER:   # Python Script
      #-------------------------------------------------------------------------------
      # Name:        SetSpatialFilter
      # Purpose:
      #
      # Author:      xsunknu
      #
      # Created:     21.08.2015
      # Copyright:   (c) xsunknu 2015
      # Licence:     <your licence>
      #-------------------------------------------------------------------------------
      
      import fme
      
      spatialfilter = 'Intersects'
      
      knr = fme.macroValues['KNR']
      fnr = fme.macroValues['FNR']
      coords = fme.macroValues['CLIPPERCOORDS']
      file = fme.macroValues['CLIPPER_FILE']
      
      if knr == '' and fnr == '' and coords == '' and file == '':
          spatialfilter = '<No Spatial Filter>'
      
      return spatialfilter
- FIXEDCLIPPERCOORDS:   # Python Script
      #-------------------------------------------------------------------------------
      # Name:        FixClipperCoords
      # Purpose:
      #
      # Author:      xsunknu
      #
      # Created:     21.08.2015
      # Copyright:   (c) xsunknu 2015
      # Licence:     <your licence>
      #-------------------------------------------------------------------------------
      
      import fme
      clippercoords = fme.macroValues['CLIPPERCOORDS']
      
      if clippercoords == '':
          clippercoords = '1 1'
      
      return clippercoords
- HOVEDTEMA = Kulturminner   # Hovedtema
- UNDERTEMA = Trehusmiljoer   # Undertema
- PG_DB:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgdb').text
      
      return value
- PG_HOST:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pghost').text
      
      return value
- PG_PORT:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgport').text
      
      return value
- PG_USER:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pguser').text
      
      return value
- PG_PWD:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgpwd').text
      
      return value
- XSD_FILE:   # Python Script
      #
      # Author:      xsunknu
      #
      # Created:     21.08.2015
      # Copyright:   (c) xsunknu 2015
      # Licence:     <your licence>
      #-------------------------------------------------------------------------------
      
      import fme, os
      from xml.etree import ElementTree as ET
      
      #Read XML config file
      configtree = ET.parse(fme.macroValues['CONFIG_FILE'])
      configdoc = configtree.getroot()
      
      value = os.path.join(fme.macroValues['FME_MF_DIR'], configdoc.find('xsd').text)
      
      return value
- LOG_FILE:   # Python Script
      #-------------------------------------------------------------------------------
      # Name:        GetConfigFile
      # Purpose:
      #
      # Author:      xsunknu
      #
      # Created:     21.08.2015
      # Copyright:   (c) xsunknu 2015
      # Licence:     <your licence>
      #-------------------------------------------------------------------------------
      
      import os, uuid, fme
      
      fmwdir = fme.macroValues['FME_MF_DIR']
      fmwfile = fme.macroValues['FME_MF_NAME']
      
      logdir = os.path.join(fmwdir, 'log')
      if not os.path.isdir(logdir):
          os.mkdir(logdir)
      
      logfile = os.path.splitext(fmwfile)[0] + '_' + str(uuid.uuid1()).replace('-','') + '.log'
      logfile = os.path.join(logdir, logfile)
      
      return logfile
- FANOUT_FOLDER:   # Python Script
      #-------------------------------------------------------------------------------
      # Name:        GetConfigFile
      # Purpose:
      #
      # Author:      xsunknu
      #
      # Created:     21.08.2015
      # Copyright:   (c) xsunknu 2015
      # Licence:     <your licence>
      #-------------------------------------------------------------------------------
      
      import os, fme
      from xml.etree import ElementTree as ET
      
      if 'FME_SERVER_DEST_DIR' in fme.macroValues:
          value = fme.macroValues['FME_SERVER_DEST_DIR']
      else:
          #Read XML config file
          configtree = ET.parse(fme.macroValues['CONFIG_FILE'])
          configdoc = configtree.getroot()
          value = configdoc.find('destdir').text
      
      return value

Readers:
- POSTGIS_1: POSTGIS from $(PG_DB)

Writers:
- GML_1: GML to D:\scratch\Trehusmiljoer.gml

CreateClipper
    CLIPPERCOORDSYS = $(CLIPPERCOORDSYS)
    DESTCOORDSYS = $(DESTCOORDSYS)
    CLIPPERCOORDS = $(FIXEDCLIPPERCOORDS)
    -> Clipper [input 1]
    -> FeatureReader_3
FeatureTypeFilter
    ATTRIBUTES = trehusmiljo.trehusmiljo,trehusmiljo.trehusmiljogrense,<BLANK>,<UNFILTERED>
    trehusmiljo.trehusmiljo -> AttributeCreator
    trehusmiljo.trehusmiljogrense -> TrehusmiljøGrense (writer GML_1)
Note: Mapper attributter
AttributeCreator
    ATTR_LIST = førsteDigitaliseringsdato,@Value(forstedigitaliseringsdato),link{0},@Value(link),vern.Vern.vernelov,@Value(vern_lov),identifikasjon.Identifikasjon.lokalId,@Value(lokalid),identifikasjon.Identifikasjon.navnerom,@Value(navnerom),identifikasjon.Identifikasjon.versjonId,@Value(versjonid),kvalitet.Posisjonskvalitet.målemetode,@Value(malemetode),kvalitet.Posisjonskvalitet.nøyaktighet,@Value(noyaktighet),kommune{0},@Value(komm),link{0},@Value(link)
    -> Trehusmiljø (writer GML_1)

Bookmark: Fylke and/or kommune clippers
admingrense.fylkeflate (reader POSTGIS_1)
    attributes: fylkeid int4, navn varchar(80)
    -> Tester
    -> AttributeCreator_8
AttributeCreator_8
    ATTR_LIST = _clippercoords,$(CLIPPERCOORDS),_clipper_file,$(CLIPPER_FILE),_fnr,$(FNR),_knr,$(KNR)
    -> Tester_4
Tester_4
    TEST_MODE = Automatic
    BOOL_OP = AND
    TEST_DESCRIPTION = ""
    TEST_CLAUSE:
      TEST _clipper_file ATTRIBUTE_IS_EMPTY ""
      TEST _clippercoords ATTRIBUTE_IS_EMPTY ""
      TEST _fnr ATTRIBUTE_IS_EMPTY ""
      TEST _knr ATTRIBUTE_IS_EMPTY ""
    PASSED -> Reprojector_2
Tester
    TEST_MODE = Automatic
    BOOL_OP = OR
    TEST_DESCRIPTION = ""
    TEST_CLAUSE = TEST @Value(fylkeid) IN $(FNR)
    PASSED -> Reprojector_2
admingrense.kommuneflate (reader POSTGIS_1)
    attributes: kommuneid int4, navn varchar(80)
    -> Tester_2
Tester_2
    TEST_MODE = Automatic
    BOOL_OP = OR
    TEST_DESCRIPTION = ""
    TEST_CLAUSE = TEST @Value(kommuneid) IN $(KNR)
    PASSED -> Reprojector_2
Note: Sender inn hele landet som initiator / dersom alle klippeparametrene er / blanke
Reprojector_2
    DEST = EPSG:4258
    SOURCE = Read from feature
    INTERPOLATION_TYPE_NAME = Nearest Neighbor
    RASTER_CELL_SIZE = Preserve Cells
    REPROJECTED -> Clipper [input 1]
    REPROJECTED -> Dissolver

Bookmark: Clipper file (any format)
Creator
    NUM = 1
    GEOMTYPE = Geometry Object
    CREATED -> FeatureReader
FeatureReader
    FORMAT = GENERIC
    OUTPUT_FEATURES_DISPLAY = Based on Connections
    ATTRIBUTES = NewFeatureType,
    FEATURETYPES_RADIO = FEATURETYPES
    ATTR_ACCUM_MODE = Only Use Result
    GENERIC_REAL_FORMAT = GUESS_FROM_EXTENSION
    COMBINE_GEOM = Use Result
    INTERACT = $(SPATIAL_FILTER)
    DATASET = $(CLIPPER_FILE)
    <OTHER> -> Reprojector_3
Reprojector_3
    DEST = EPSG:4258
    SOURCE = Read from feature
    INTERPOLATION_TYPE_NAME = Nearest Neighbor
    RASTER_CELL_SIZE = Preserve Cells
    REPROJECTED -> Clipper [input 1]
    REPROJECTED -> Dissolver

Bookmark: Leser features
Dissolver
    NO_OVRLP = No
    ACCUM_INPUT_ATTRS = No
    AREA -> FeatureReader_3
FeatureReader_3
    COMBINE_GEOM = Use Result
    POSTGIS_CLIP_TO_ENVELOPE = NO
    POSTGIS_USER_NAME = $(PG_USER)
    POSTGIS_QUERY_FEATURE_TYPES_FOR_MERGE_FILTERS = Yes
    FORMAT = POSTGIS
    POSTGIS_DISABLE_COLLECTION_SPLITTING = yes
    INTERACT = Intersects
    POSTGIS_USE_TRUE_POSTGIS_TYPES = yes
    POSTGIS_HOST = $(PG_HOST)
    POSTGIS_USE_SEARCH_ENVELOPE = NO
    ATTRIBUTES = trehusmiljo.trehusmiljo,"objid,objtype,navn,vern_lov,lokalid,navnerom,versjonid,forstedigitaliseringsdato,oppdateringsdato,datauttaksdato,malemetode,noyaktighet,opphav,komm,informasjon,link",trehusmiljo.trehusmiljogrense,"objid,objtype"
    FEATURETYPES_RADIO = FEATURETYPES
    POSTGIS_SCHEMALIST = trehusmiljo
    OUTPUT_FEATURES_DISPLAY = Based on Connections
    DATASET = $(PG_DB)
    FEATURETYPES = trehusmiljo.trehusmiljo trehusmiljo.trehusmiljogrense
    ATTR_ACCUM_MODE = Only Use Result
    POSTGIS_PASSWORD = $(PG_PWD)
    POSTGIS_PORT = $(PG_PORT)
    trehusmiljo.trehusmiljo -> AttributeCreator_12
    trehusmiljo.trehusmiljogrense -> AttributeCreator_12
AttributeCreator_12
    ATTR_LIST = _clippercoords,$(CLIPPERCOORDS),_clipper_file,$(CLIPPER_FILE),_fnr,$(FNR),_knr,$(KNR)
    -> TestFilter
TestFilter
    DEFAULT_VALUE = <UNFILTERED>
    TEST_LIST:
      BOOL_OP,AND,COMPOSITE_TEST,<Unused>,TEST_CLAUSE,"TEST _clipper_file ATTRIBUTE_IS_EMPTY """"
      TEST _clippercoords ATTRIBUTE_IS_EMPTY """"
      TEST _fnr ATTRIBUTE_IS_EMPTY """"
      TEST _knr ATTRIBUTE_IS_EMPTY """"",Landsdekkende,BOOL_OP,AND,COMPOSITE_TEST,<Unused>,TEST_CLAUSE,"TEST _clipper_file ATTRIBUTE_IS_EMPTY """"
      TEST _clippercoords ATTRIBUTE_IS_EMPTY """"
      TEST _fnr NOT_ATTRIBUTE_IS_EMPTY """"
      TEST _knr ATTRIBUTE_IS_EMPTY """"",Fylkesvis,BOOL_OP,AND,COMPOSITE_TEST,<Unused>,TEST_CLAUSE,"TEST _clipper_file ATTRIBUTE_IS_EMPTY """"
      TEST _clippercoords ATTRIBUTE_IS_EMPTY """"
      TEST _fnr ATTRIBUTE_IS_EMPTY """"
      TEST _knr NOT_ATTRIBUTE_IS_EMPTY """"",Kommunevis
    Fylkesvis -> Clipper [input 2]
    Kommunevis -> Clipper [input 2]
    <UNFILTERED> -> Clipper [input 2]
    Landsdekkende -> SosiFilenameSetter

Bookmark: Klipper
Clipper
    CLIP_TYPE = Multiple Clippers
    CLIPPED_ATTR = _clipped
    CREATE_AGGREGATES = No
    ATTR_ACCUM_MODE = Merge Clipper
    BOUNDARY_CASES = Treat as Inside
    PRESERVE_CLIPPEE_EXTENTS = No
    ATTR_CONFLICT_RES = Use Clippee
    INSIDE -> SosiFilenameSetter

Bookmark: Tagger og reprojiserer
SosiFilenameSetter
    DATAUTTAKSDATO = @Value(datauttaksdato)
    _KNR = @Value(_knr)
    FORSTEDIGITALISERINGSDATO = @Value(forstedigitaliseringsdato)
    OBJID = @Value(objid)
    PG_DB:
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------

      import fme
      from xml.etree import ElementTree as ET

      #Read XML config file
      configtree = ET.parse(fme.macroValues['CONFIG_FILE'])
      configdoc = configtree.getroot()
      value = configdoc.find('pgdb').text

      return value
    NAVN = @Value(navn)
    _FNR = @Value(_fnr)
    INFORMASJON = @Value(informasjon)
    UNDERTEMA = $(UNDERTEMA)
    PG_PWD:
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------

      import fme
      from xml.etree import ElementTree as ET

      #Read XML config file
      configtree = ET.parse(fme.macroValues['CONFIG_FILE'])
      configdoc = configtree.getroot()
      value = configdoc.find('pgpwd').text

      return value
    _CREATION_INSTANCE = @Value(_creation_instance)
    VERN_LOV = @Value(vern_lov)
    VERSJONID = @Value(versjonid)
    PG_HOST:
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------

      import fme
      from xml.etree import ElementTree as ET

      #Read XML config file
      configtree = ET.parse(fme.macroValues['CONFIG_FILE'])
      configdoc = configtree.getroot()
      value = configdoc.find('pghost').text

      return value
    OBJTYPE = @Value(objtype)
    _CLIPPED = @Value(_clipped)
    MALEMETODE = @Value(malemetode)
    OPPHAV = @Value(opphav)
    FYLKEID = @Value(fylkeid)
    PG_USER:
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------

      import fme
      from xml.etree import ElementTree as ET

      #Read XML config file
      configtree = ET.parse(fme.macroValues['CONFIG_FILE'])
      configdoc = configtree.getroot()
      value = configdoc.find('pguser').text

      return value
    KOMMUNEID = @Value(kommuneid)
    KOMM = @Value(komm)
    NAVNEROM = @Value(navnerom)
    FANOUT = $(FANOUT)
    _CLIPPERCOORDS = @Value(_clippercoords)
    OPPDATERINGSDATO = @Value(oppdateringsdato)
    _CLIPPER_FILE = @Value(_clipper_file)
    HOVEDTEMA = $(HOVEDTEMA)
    LINK = @Value(link)
    LOKALID = @Value(lokalid)
    OUTPUT_EPSG_CODE = $(OUTPUT_EPSG_CODE)
    NOYAKTIGHET = @Value(noyaktighet)
    PG_PORT:
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------

      import fme
      from xml.etree import ElementTree as ET

      #Read XML config file
      configtree = ET.parse(fme.macroValues['CONFIG_FILE'])
      configdoc = configtree.getroot()
      value = configdoc.find('pgport').text

      return value
    -> Reprojector
Reprojector
    DEST = $(DESTCOORDSYS)
    SOURCE = Read from feature
    INTERPOLATION_TYPE_NAME = Nearest Neighbor
    RASTER_CELL_SIZE = Preserve Cells
    REPROJECTED -> NullAttributeMapper

Bookmark: GML-spesifikk koding
NullAttributeMapper
    ATTRLIST = datauttaksdato forstedigitaliseringsdato fylkeid kommuneid link navn objid objtype oppdateringsdato opphav sosifile vern_lov informasjon lokalid malemetode navnerom noyaktighet versjonid
    SOURCE_ATTR_VAL = Empty Null
    NULL_TREATMENT = Missing
    ATTRCHOICE = Selected Attributes
    -> DateFormatter_2
DateFormatter_2
    DATE_ATTR = datauttaksdato,forstedigitaliseringsdato,oppdateringsdato
    SRCFMT = Unknown - Automatic Detection
    FMT = ISO DateTime (%Y-%m-%dT%H:%M:%S)
    -> GeometryFilter
GeometryFilter
    GEOM_PORT_NAMES = Line Area
    BREAK_AGG = No
    LINE -> GeometryPropertySetter
    AREA -> GeometryPropertySetter_2
GeometryPropertySetter
    SETTYPE_PARAM = Geometry Name
    OVERWRITE_CHOICE = Yes
    GEOM_NAME_FIELD = grense
    SET -> FeatureTypeFilter
GeometryPropertySetter_2
    SETTYPE_PARAM = Geometry Name
    OVERWRITE_CHOICE = Yes
    GEOM_NAME_FIELD = område
    SET -> FeatureTypeFilter

Bookmark: GML output
Trehusmiljø (writer GML_1)
    attributes: identifikasjon.Identifikasjon.lokalId xml_buffer, identifikasjon.Identifikasjon.navnerom xml_buffer, identifikasjon.Identifikasjon.versjonId xml_buffer, førsteDigitaliseringsdato xml_datetime, oppdateringsdato xml_datetime, datauttaksdato xml_datetime, kvalitet.Posisjonskvalitet.målemetode xml_buffer, kvalitet.Posisjonskvalitet.nøyaktighet xml_int64, opphav xml_buffer, kommune{} xml_buffer, informasjon{} xml_buffer, link{} xml_buffer, område xml_geometry, posisjon xml_geometry, navn xml_buffer, vern{}.Vern.vernelov xml_buffer
TrehusmiljøGrense (writer GML_1)
    attributes: grense xml_geometry

FME custom transformer SosiFilenameSetter

Parameters:
- OUTPUT_EPSG_CODE = 25832   # Destination coordinate system
- FANOUT = Kommuner   # Fanout områder
- UNDERTEMA =   # Undertema
- HOVEDTEMA =   # Hovedtema
- _CLIPPED = @Value(_clipped)   # Clipped
- _CLIPPER_FILE = @Value(_clipper_file)   # Clipper File
- _CLIPPERCOORDS = @Value(_clippercoords)   # Clippercoords
- _CREATION_INSTANCE = @Value(_creation_instance)   # Creation Instance
- _FNR = @Value(_fnr)   # Fnr
- _KNR = @Value(_knr)   # Knr
- DATAUTTAKSDATO = @Value(datauttaksdato)   # datauttaksdato
- FORSTEDIGITALISERINGSDATO = @Value(forstedigitaliseringsdato)   # forstedigitaliseringsdato
- FYLKEID = @Value(fylkeid)   # fylkeid
- INFORMASJON = @Value(informasjon)   # informasjon
- KOMM = @Value(komm)   # komm
- KOMMUNEID = @Value(kommuneid)   # kommuneid
- LINK = @Value(link)   # link
- LOKALID = @Value(lokalid)   # lokalid
- MALEMETODE = @Value(malemetode)   # malemetode
- NAVN = @Value(navn)   # navn
- NAVNEROM = @Value(navnerom)   # navnerom
- NOYAKTIGHET = @Value(noyaktighet)   # noyaktighet
- OBJID = @Value(objid)   # objid
- OBJTYPE = @Value(objtype)   # objtype
- OPPDATERINGSDATO = @Value(oppdateringsdato)   # oppdateringsdato
- OPPHAV = @Value(opphav)   # opphav
- VERN_LOV = @Value(vern_lov)   # Vern Lov
- VERSJONID = @Value(versjonid)   # versjonid
- PG_DB:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgdb').text
      
      return value
- PG_HOST:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pghost').text
      
      return value
- PG_PORT:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgport').text
      
      return value
- PG_PWD:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgpwd').text
      
      return value
- PG_USER:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pguser').text
      
      return value

Input (input)
    -> ParameterFetcher
ParameterFetcher
    ATTR_LIST = _output_epsg_code {$(OUTPUT_EPSG_CODE)} _fanout {$(FANOUT)}
    -> AttributeValueMapper
Note: Fikser kjente feil i kommunenummer
AttributeValueMapper
    DEFAULT_VALUE = @Value(kommuneid)
    LUT = 1901,1903
    VAL_ATTR = kommuneid
    DIRECTION = Forward (Source To Destination)
    SRC = kommuneid
    -> TestFilter_2
TestFilter_2
    DEFAULT_VALUE = Ufiltrert
    TEST_LIST = BOOL_OP,OR,COMPOSITE_TEST,<Unused>,TEST_CLAUSE,"TEST $(FANOUT) = Kommuner",Kommuner,BOOL_OP,OR,COMPOSITE_TEST,<Unused>,TEST_CLAUSE,"TEST $(FANOUT) = Fylker",Fylker
    Kommuner -> Joiner
    Fylker -> Joiner_2
    Ufiltrert -> AttributeCreator_13
Joiner
    POSTGIS_QUERY_FEATURE_TYPES_FOR_MERGE_FILTERS = Yes
    FORMAT = POSTGIS
    POSTGIS_PASSWORD = $(PG_PWD)
    POSTGIS_DISABLE_COLLECTION_SPLITTING = yes
    CACHE_SIZE = 5000
    POSTGIS_HOST = $(PG_HOST)
    ADDED_FIELDS = navn
    MATCH_RULE_DISPLAY = Must Match Exactly One (1:1)
    PREFETCH_EXHAUSTIVE = Yes
    POSTGIS_USE_TRUE_POSTGIS_TYPES = yes
    POSTGIS_USER_NAME = $(PG_USER)
    POSTGIS_PORT = $(PG_PORT)
    TABLE = admingrense.kommuner
    DATASET = $(PG_DB)
    JOIN_KEYS = kommuneid kommuneid
    JOINED -> StringReplacer_2
Joiner_2
    POSTGIS_QUERY_FEATURE_TYPES_FOR_MERGE_FILTERS = Yes
    FORMAT = POSTGIS
    POSTGIS_PASSWORD = $(PG_PWD)
    POSTGIS_DISABLE_COLLECTION_SPLITTING = yes
    CACHE_SIZE = 5000
    POSTGIS_HOST = $(PG_HOST)
    ADDED_FIELDS = navn
    MATCH_RULE_DISPLAY = Must Match Exactly One (1:1)
    PREFETCH_EXHAUSTIVE = Yes
    POSTGIS_USE_TRUE_POSTGIS_TYPES = yes
    POSTGIS_USER_NAME = $(PG_USER)
    POSTGIS_PORT = $(PG_PORT)
    TABLE = admingrense.fylkeflate
    DATASET = $(PG_DB)
    JOIN_KEYS = fylkeid fylkeid
    JOINED -> StringReplacer_2
AttributeCreator_13
    ATTR_LIST = sosifile,"FME_CONDITIONAL:DEFAULT_VALUE'$(HOVEDTEMA)_$(OUTPUT_EPSG_CODE)_$(UNDERTEMA)_GML'BOOL_OP;OR;COMPOSITE_TEST;<Unused>;TEST $(FANOUT) LIKE Kommuner'$(HOVEDTEMA)_@PadLeft(@Value(kommuneid),4,0)_@Value(navn)_$(OUTPUT_EPSG_CODE)_$(UNDERTEMA)_GML'BOOL_OP;OR;COMPOSITE_TEST;<Unused>;TEST $(FANOUT) LIKE Fylker'$(HOVEDTEMA)_@PadLeft(@Value(fylkeid),2,0)_@Value(navn)_$(OUTPUT_EPSG_CODE)_$(UNDERTEMA)_GML'BOOL_OP;OR;COMPOSITE_TEST;<Unused>;TEST $(FANOUT) LIKE Norge'$(HOVEDTEMA)_0000_Norge_$(OUTPUT_EPSG_CODE)_$(UNDERTEMA)_GML'FME_NUM_CONDITIONS4___"
    -> Output (output)
Output (output)

Bookmark: Substituerer ÆØÅ og mellomrom
StringReplacer_2
    REGEXP = no
    SRC_ATTRS = navn
    REPLACE_TEXT = _
    FIND_TEXT = " "
    NO_MATCH = _FME_NO_OP_
    CASE = no
    -> StringReplacer_3
StringReplacer_3
    REGEXP = no
    SRC_ATTRS = navn
    REPLACE_TEXT = E
    FIND_TEXT = Æ
    NO_MATCH = _FME_NO_OP_
    CASE = yes
    -> StringReplacer_4
StringReplacer_4
    REGEXP = no
    SRC_ATTRS = navn
    REPLACE_TEXT = O
    FIND_TEXT = Ø
    NO_MATCH = _FME_NO_OP_
    CASE = yes
    -> StringReplacer_5
StringReplacer_5
    REGEXP = no
    SRC_ATTRS = navn
    REPLACE_TEXT = A
    FIND_TEXT = Å
    NO_MATCH = _FME_NO_OP_
    CASE = yes
    -> StringReplacer_6
StringReplacer_6
    REGEXP = no
    SRC_ATTRS = navn
    REPLACE_TEXT = e
    FIND_TEXT = æ
    NO_MATCH = _FME_NO_OP_
    CASE = yes
    -> StringReplacer_7
StringReplacer_7
    REGEXP = no
    SRC_ATTRS = navn
    REPLACE_TEXT = o
    FIND_TEXT = ø
    NO_MATCH = _FME_NO_OP_
    CASE = yes
    -> StringReplacer_8
StringReplacer_8
    REGEXP = no
    SRC_ATTRS = navn
    REPLACE_TEXT = a
    FIND_TEXT = å
    NO_MATCH = _FME_NO_OP_
    CASE = yes
    -> AttributeCreator_13

FME custom transformer CreateClipper

Parameters:
- CLIPPERCOORDS = 253577 6650999 253577 6651246 253763 6651246 253763 6650999 253577 6650999   # Clipper Coordinate List
- CLIPPERCOORDSYS = EPSG:25833   # Clipper Coordinate System
- DESTCOORDSYS = "ESRIWKT|ETRS_1989_UTM_Zone_35N|PROJCS["ETRS_1989_UTM_Zone_35N",GEOGCS["GCS_ETRS_1989",DATUM["D_ETRS_1989",SPHEROID["GRS_1980",6378137.0,298.257222101]],PRIMEM["Greenwich",0.0],UNIT["Degree",0.0174532925199433]],PROJECTION["Transverse_Mercator"],PARAMETER["False_Easting",500000.0],PARAMETER["False_Northing",0.0],PARAMETER["Central_Meridian",27.0],PARAMETER["Scale_Factor",0.9996],PARAMETER["Latitude_Of_Origin",0.0],UNIT["Meter",1.0]]"   # Destination Coordinate System

Note: Creating geometry from / the Clipper coords
Creator
    COORDS = $(CLIPPERCOORDS)
    NUM = 1
    GEOMTYPE = 2D Coordinate List
    COORDSYS = $(CLIPPERCOORDSYS)
    CREATED -> BoundingBoxAccumulator
Note: Calculating the bounding / box (envelope) from the geometry
BoundingBoxAccumulator
    TOPFER_INDEX = No
    BOUNDING_BOX -> SpatialFilter [input 1]
    ORIGINAL -> SpatialFilter [input 2]
Note: If the geometry is equal to its / own bounding box - it is a rectangle!
SpatialFilter
    BASE_TYPE = Single Base
    PASS_CRITERIA = Pass Against One Base
    PREDICATES = EQUALS
    USE_BOUNDING_BOX = No
    CURVE_BOUNDARY_RULE_PARAM = Default Rule
    MERGE_ATTRS = No
    PREDATTR = _predicate
    PASSED -> Reprojector
    FAILED -> Reprojector_2
Note: If rectangle, reproject the / geometry to the destination / coordinate system
Reprojector
    DEST = $(DESTCOORDSYS)
    SOURCE = Read from feature
    STROKE_ARCS = Yes
    INTERPOLATION_TYPE_NAME = Nearest Neighbor
    RASTER_CELL_SIZE = Preserve Cells
    REPROJECTED -> BoundingBoxAccumulator_2
Note: Then calculate the bounding / box from the projected geoemtry
BoundingBoxAccumulator_2
    TOPFER_INDEX = No
    BOUNDING_BOX -> Reprojector_3
Note: Reproject the geometry back to / the DB coordsys (LL/EUREF89)
Reprojector_3
    DEST = EPSG:4258
    SOURCE = Read from feature
    STROKE_ARCS = Yes
    INTERPOLATION_TYPE_NAME = Nearest Neighbor
    RASTER_CELL_SIZE = Preserve Cells
    REPROJECTED -> GeometryFilter
Note: Reproject clipper to / the DB coordsys (LL/EUREF89)
Reprojector_2
    DEST = EPSG:4258
    SOURCE = Read from feature
    STROKE_ARCS = Yes
    INTERPOLATION_TYPE_NAME = Nearest Neighbor
    RASTER_CELL_SIZE = Preserve Cells
    REPROJECTED -> GeometryFilter
Note: Getting rid of dummies
GeometryFilter
    GEOM_PORT_NAMES = Area
    BREAK_AGG = No
    AREA -> Output (output)
Output (output)
