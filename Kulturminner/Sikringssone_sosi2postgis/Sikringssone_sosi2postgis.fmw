FME workspace Sikringssone_sosi2postgis.fmw

Parameters:
- CONFIG_FILE:   # Python Script
      #-------------------------------------------------------------------------------
      # Name:        GetConfigFile
      # Purpose:
      #
      # Author:      xsunknu
      #
      # Created:     21.08.2015
      # Copyright:   (c) xsunknu 2015
      # Licence:     <your licence>
      #-------------------------------------------------------------------------------
      
      import os, fme
      
      fmwdir = fme.macroValues['FME_MF_DIR']
      fmwfile = fme.macroValues['FME_MF_NAME']
      
      fmwfile = os.path.join(fmwdir, fmwfile)
      configfile = os.path.splitext(fmwfile)[0] + '_config.xml'
      
      return configfile
- FTP_URL:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('ftpurl').text
      
      return value
- FTP_USER:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('ftpuser').text
      
      return value
- FTP_PWD:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('ftppwd').text
      
      return value
- SOSI_IN:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('sosiin').text
      
      return value
- PG_DB:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgdb').text
      
      return value
- LOG_FILE:   # Python Script
      #-------------------------------------------------------------------------------
      # Name:        GetConfigFile
      # Purpose:
      #
      # Author:      xsunknu
      #
      # Created:     21.08.2015
      # Copyright:   (c) xsunknu 2015
      # Licence:     <your licence>
      #-------------------------------------------------------------------------------
      
      import os, uuid, fme
      
      fmwdir = fme.macroValues['FME_MF_DIR']
      fmwfile = fme.macroValues['FME_MF_NAME']
      
      logdir = os.path.join(fmwdir, 'log')
      if not os.path.isdir(logdir):
          os.mkdir(logdir)
      
      logfile = os.path.splitext(fmwfile)[0] + '_' + str(uuid.uuid1()).replace('-','') + '.log'
      logfile = os.path.join(logdir, logfile)
      
      return logfile

Writers:
- POSTGIS_1: POSTGIS to $(PG_DB)

Creator
    NUM = 1
    GEOMTYPE = Geometry Object
    CREATED -> FTPCaller
Note: Laster ned SOSI-fil med FTP / til en attributt
FTPCaller
    TARGET_ATTR_ENCODING = utf-8
    VERIFY_SSL_CERTIFICATES = Yes
    REMOTE_URL = $(FTP_URL)
    MODE = Binary
    FTP_USERNAME = $(FTP_USER)
    ERROR_ATTR = _error
    TRANSFER_TYPE = Download to an Attribute
    TARGET_ATTR = _file_contents
    FTP_PASSWORD = $(FTP_PWD)
    -> PythonCaller
Note: Fjerner uønskede tegn / i SOSI-fila
PythonCaller
    PYTHONSOURCE:
      import fme
      import fmeobjects

      def SosiVasker(feature):
          # Removing unvanted character in the SOSI-file
          sosi = unicode(feature.getAttribute("_file_contents"))
          sosi = sosi.replace(chr(26), '')
          feature.setAttribute("_file_contents", sosi)
    PYTHONSYMBOL = SosiVasker
    NEW_ATTRIBUTES = _file_contents
    -> AttributeFileWriter
Note: Lagrer SOSI-fila / til disk.
AttributeFileWriter
    SOURCE_ATTR = _file_contents
    FILE_NAME = $(SOSI_IN)
    OVERWRITE_FILE = Overwrite file
    CHAR_ENCODING = utf-8
    -> FeatureReader
Note: Leser SOSI-fil
FeatureReader
    SOSI_READER_ALLOW_MISSING_MANDATORY_ATTRS = yes
    SOSI_READER_ENFORCE_Z_VALUES = Auto-detect
    SOSI_READER_MISSING_Z_VALUE = -9999
    INTERACT = <No Spatial Filter>
    ATTR_ACCUM_MODE = Only Use Result
    COMBINE_GEOM = Use Result
    SOSI_READER_LOG_WARNINGS = no
    SOSI_READER_LOG_ERRORS = yes
    FEATURETYPES_RADIO = FEATURETYPES
    DATASET = D:\scratch\sikringssoner.sos
    OUTPUT_FEATURES_DISPLAY = Based on Connections
    SOSI_READER_ATTRIBUTE_VALIDATION_LEVEL = Basic
    SOSI_READER_REFERENCE_SCALE = 1
    ATTRIBUTES = DATAUTTAKSDATO_SOSI,fme_geometry{0},FORSTEDIGITALISERINGSDATO_SOSI,fme_geometry{0},IDENT_SOSI,fme_geometry{0},KM_KATEGORI_SOSI,fme_geometry{0},KVALITET_SOSI,fme_geometry{0},KulturminneSikringssone,"fme_geometry{0},SOSI_id",KulturminneSikringssoneGr,"fme_geometry{0},SOSI_id",KulturminneSikringssoneGr_1,"fme_geometry{0},SOSI_id",KulturminneSikringssone_1,"fme_geometry{0},SOSI_id",KulturminneSikringssone_2,fme_geometry{0},LINK_SOSI,fme_geometry{0},NAVN_SOSI,fme_geometry{0},OBJTYPE_SOSI,fme_geometry{0},SOSI_RelationshipClasses,fme_geometry{0}
    FORMAT = SOSI
    KulturminneSikringssone -> AttributeExposer
    KulturminneSikringssoneGr -> AttributeExposer
    KulturminneSikringssoneGr_1 -> AttributeExposer
    KulturminneSikringssone_1 -> AttributeExposer
    KulturminneSikringssone_2 -> AttributeExposer
Note: Eksponerer attributtene
AttributeExposer
    ATTR_LIST = DATAUTTAKSDATO,FeatureClass,FORSTEDIGITALISERINGSDATO,GeometryType,KM_KATEGORI,LINK,LOKALID,MALEMETODE,NAVN,NAVNEROM,NOYAKTIGHET,OBJTYPE,OPPDATERINGSDATO,SOSI_guid,SOSI_id,SOSI_parent_guid,Table,VERN_LOV,VERN_PARA,VERNTYPE,VERSJONID
    -> BulkAttributeRenamer
Note: Renamer attributtene til / lowercase
BulkAttributeRenamer
    PATTERN_ACTION_DISP = Change Case
    ATTRCHOICE = All Attributes
    CASE_CHANGE_TYPE = lowercase
    -> AttributeCreator
Note: Setter ID'er
AttributeCreator
    ATTR_LIST = objid,@Value(sosi_id)
    -> Reprojector
Note: Reprojiserer
Reprojector
    SOURCE = Read from feature
    DEST = EPSG:4258
    RASTER_CELL_SIZE = Preserve Cells
    INTERPOLATION_TYPE_NAME = Nearest Neighbor
    REPROJECTED -> GeometryFilter
Note: Skiller flater og linjer
GeometryFilter
    BREAK_AGG = No
    GEOM_PORT_NAMES = Point Line Arc Area
    LINE -> sikringssoner.kulturminnesikringssonegr (writer POSTGIS_1)
    AREA -> sikringssoner.kulturminnesikringssone (writer POSTGIS_1)
    ARC -> sikringssoner.kulturminnesikringssonegr (writer POSTGIS_1)

Bookmark: PostGIS
sikringssoner.kulturminnesikringssonegr (writer POSTGIS_1)
    attributes: objid int4,PRIKEY, objtype varchar(32)
sikringssoner.kulturminnesikringssone (writer POSTGIS_1)
    attributes: objid int4,PRIKEY, objtype varchar(32), navn varchar(80), vern_lov varchar(80), vern_para varchar(80), verntype varchar(80), vernedato date, km_kategori varchar(80), forstedigitaliseringsdato timestamp, oppdateringsdato timestamp, datauttaksdato timestamp, opphav varchar(80), kommune varchar(80), link varchar(255)
