FME workspace postgis2Sosi.fmw

Parameters:
- SourceDataset_POSTGIS = geonortst@Nnridb504:5432/geonor01tst   # Connection
- DestDataset_SOSI = C:\Users\xmaland\Documents\SOSIfiler\DSB.SOS   # Destination SOSI File

Readers:
- POSTGIS_1: POSTGIS from $(SourceDataset_POSTGIS)

Writers:
- SOSI_1: SOSI to $(DestDataset_SOSI) in EPSG:32633

dsb.brannstasjoner (reader POSTGIS_1)
    attributes: lokalid uuid, navnerom text, versjonid varchar(2), msgeometry text, brannstasjon text, kasernert text, brannvesen text, anleggid text, ajourdato date, informasjon text, opphav text, stasjonstype text, objtype text, dato date, brannsta_ text, omradeid int8, kopidato timestamp, originaldatavert text
    -> dsb.brannstasjoner (writer SOSI_1)
dsb.brannstasjoner (writer SOSI_1)
    attributes: lokalid SOSI_buffer, navnerom SOSI_buffer, versjonid SOSI_varchar(2), msgeometry SOSI_buffer, brannstasjon SOSI_buffer, kasernert SOSI_buffer, brannvesen SOSI_buffer, anleggid SOSI_buffer, ajourdato SOSI_date, informasjon SOSI_buffer, opphav SOSI_buffer, stasjonstype SOSI_buffer, objtype SOSI_buffer, dato SOSI_date, brannsta_ SOSI_buffer, omradeid SOSI_int64, kopidato SOSI_datetime, originaldatavert SOSI_buffer
dsb.sentraldistrikter110 (reader POSTGIS_1)
    attributes: lokalid uuid, navnerom text, versjonid varchar(2), msgeometry text, poly_ text, poly_id text, area text, perimeter text, oppr text, x float8, y float8, koordh text, sentral text, lokalisering text, opphav text, omradeid int8, originaldatavert text, kopidato timestamp, malemetode text, noyaktighet int8, synbarhet text, h_malemetode text, h_noyaktig text, max_avvik text, objtype text, navn text, datafangstdato date
    -> dsb.sentraldistrikter110 (writer SOSI_1)
dsb.sentraldistrikter110 (writer SOSI_1)
    attributes: lokalid SOSI_buffer, navnerom SOSI_buffer, versjonid SOSI_varchar(2), msgeometry SOSI_buffer, poly_ SOSI_buffer, poly_id SOSI_buffer, area SOSI_buffer, perimeter SOSI_buffer, oppr SOSI_buffer, x SOSI_real64, y SOSI_real64, koordh SOSI_buffer, sentral SOSI_buffer, lokalisering SOSI_buffer, opphav SOSI_buffer, omradeid SOSI_int64, originaldatavert SOSI_buffer, kopidato SOSI_datetime, malemetode SOSI_buffer, noyaktighet SOSI_int64, synbarhet SOSI_buffer, h_malemetode SOSI_buffer, h_noyaktig SOSI_buffer, max_avvik SOSI_buffer, objtype SOSI_buffer, navn SOSI_buffer, datafangstdato SOSI_date
dsb.sivilforsvaret_distriktskontor (reader POSTGIS_1)
    attributes: lokalid uuid, navnerom text, versjonid varchar(2), msgeometry text, type text, kommune text, url text, navn text, dato date, omradeid int8, kopidato timestamp, originaldatavert text
    -> dsb.sivilforsvaret_distriktskontor (writer SOSI_1)
dsb.sivilforsvaret_distriktskontor (writer SOSI_1)
    attributes: lokalid SOSI_buffer, navnerom SOSI_buffer, versjonid SOSI_varchar(2), msgeometry SOSI_buffer, type SOSI_buffer, kommune SOSI_buffer, url SOSI_buffer, navn SOSI_buffer, dato SOSI_date, omradeid SOSI_int64, kopidato SOSI_datetime, originaldatavert SOSI_buffer
dsb.sivilforsvarsdistrikter (reader POSTGIS_1)
    attributes: lokalid uuid, navnerom text, versjonid varchar(2), msgeometry text, sivdistrik text, url text, navn text, kopidato timestamp, originaldatavert text, omradeid int4
    -> dsb.sivilforsvarsdistrikter (writer SOSI_1)
dsb.sivilforsvarsdistrikter (writer SOSI_1)
    attributes: lokalid SOSI_buffer, navnerom SOSI_buffer, versjonid SOSI_varchar(2), msgeometry SOSI_buffer, sivdistrik SOSI_buffer, url SOSI_buffer, navn SOSI_buffer, kopidato SOSI_datetime, originaldatavert SOSI_buffer, omradeid SOSI_int32
dsb.brannstasjonkasernering (reader POSTGIS_1)
    attributes: lokalid uuid, navnerom text, versjonid varchar(2), msgeometry text, brannstasjon text, kasernert text, brannvesen text, anleggid text, ajourdato date, informasjon text, opphav text, stasjonstype text, objtype text, dato date, brannsta_ text, omradeid int8, kopidato timestamp, originaldatavert text
    -> dsb.brannstasjonkasernering (writer SOSI_1)
dsb.brannstasjonkasernering (writer SOSI_1)
    attributes: lokalid SOSI_buffer, navnerom SOSI_buffer, versjonid SOSI_varchar(2), msgeometry SOSI_buffer, brannstasjon SOSI_buffer, kasernert SOSI_buffer, brannvesen SOSI_buffer, anleggid SOSI_buffer, ajourdato SOSI_date, informasjon SOSI_buffer, opphav SOSI_buffer, stasjonstype SOSI_buffer, objtype SOSI_buffer, dato SOSI_date, brannsta_ SOSI_buffer, omradeid SOSI_int64, kopidato SOSI_datetime, originaldatavert SOSI_buffer
