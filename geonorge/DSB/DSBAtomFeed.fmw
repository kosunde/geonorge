FME workspace DSBAtomFeed.fmw
Title: SOSI ATOM Data Download Feed
Description: Pakka data for SOSI tilbys.
Requirements: FME 2015.0+
History: 23/02/2015,N Wlock,Created

Parameters:
- FMEServerRoot = http://nnrite507   # Base URL for the FME Server host
- Title = DSB ATOM Feed: DSB Data
- Description = DSB data for brannstasjoner, sentraldistrikter og Sivilforsvaret
- Author = Karen Lie   # Author of ATOM service
- Repository_Name = DSB   # Server Repository name which contains workspace(s)
- workspaceName = DSB_PostGIS2DSB_Sosi.fmw   # INSPIRE Data Streaming Workspace(s) on FME Server
- LastUpdate = 2015-08-19T16:15Z   # Date the workspace was last updated
- FMEVersion = 2015.0   # Version of FME being used

Writers:
- GEORSS_1: GEORSS to $(FME_MF_DIR)ATOM\DSBAtomFeed.xml

Note: Explodes options.option{}
ListExploder
    LIST_ATTR = options.option{}
    MODE = List Elements and Original Attributes
    INDEX_ATTR = _element_index

Bookmark: Feed
Creator_2
    NUM = 1
    GEOMTYPE = Geometry Object
    CREATED -> AttributeCreator
AttributeCreator
    ATTR_LIST = Title,$(Title),Description,$(Description),LinkURI,$(FMEServerRoot)/$(Repository_Name),Id,$(FMEServerRoot)/$(Repository_Name),LastUpdate,$(LastUpdate),LinkRelation,self,LinkType,application/atom+xml,Copyright,DSB,Description,$(Description),GeneratorURI,$(FMEServerRoot),GeneratorVersion,$(FMEVersion)
    -> Feed (writer GEORSS_1)
Feed (writer GEORSS_1)

Bookmark: Entry
Creator_3
    NUM = 1
    GEOMTYPE = Geometry Object
    CREATED -> AttributeCreator_5
AttributeCreator_2
    ATTR_LIST = Title,@Value(value),Content,Trykk på linken for å laste ned data. <br />  <a href="@Value(DownloadUrl)">@Value(value)<\a>,Description,Data for Sivilforsvaret og Brannvesenet. Trykk på linken for nedlasting: @Value(value),ContentType,html,Id,@Value(DownloadUrl),Category{0}.Category,EPSG:25833,Category{0}.Domain,http://www.opengis.net/def/crs/,Category{0}.Label,EPSG/0/25833,Author,Karen Lie,Copyright,DSB - Sivilforsvaret og brannvesenet.,LinkURI,@Value(DownloadUrl)
    -> Entry (writer GEORSS_1)
Entry (writer GEORSS_1)

Bookmark: Set Up Entry Content with Download Link
Note: Creates the download URL
AttributeCreator_5
    ATTR_LIST = DownloadUrl,$(FMEServerRoot)/fmedatastreaming/$(Repository_Name)/$(workspaceName)?SourceDataset_POSTGIS_1=geonor01tst,name,DSB,value,DSB SOSI Data
    -> TimeStamper_6
TimeStamper_6
    FMT = FME Date/Time (^Y^m^d^H^M^S)
    TIME_ATTR = LastUpdate
    -> AttributeCreator_2
