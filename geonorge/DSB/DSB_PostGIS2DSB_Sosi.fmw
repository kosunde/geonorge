FME workspace DSB_PostGIS2DSB_Sosi.fmw
Title: DSB data fra PostGIS til SOSI

Parameters:
- SourceDataset_POSTGIS_1 = geonor01tst   # Database

Readers:
- POSTGIS_1: POSTGIS from $(SourceDataset_POSTGIS_1) in EPSG:25833
- TEXTLINE_1: TEXTLINE from $(FME_MF_DIR)DSBDescription.txt

Writers:
- SOSI_1: SOSI to $(FME_MF_DIR)dsb.sos in EPSG:25833
- TEXTLINE_2: TEXTLINE to C:\Users\xmaland\Documents\SOSIfiler\DSBDescription.txt

dsb.sivilforsvaret_distriktskontor (reader POSTGIS_1)
    attributes: lokalid uuid, navnerom text, versjonid varchar(2), msgeometry text, type text, kommune text, url text, navn text, dato date, omradeid int8, kopidato timestamp, originaldatavert text, objtype text
    -> dsb.sivilforsvaret_distriktskontor (writer SOSI_1)
dsb.sivilforsvaret_distriktskontor (writer SOSI_1)
    attributes: lokalid SOSI_buffer, navnerom SOSI_buffer, versjonid SOSI_varchar(2), msgeometry SOSI_buffer, type SOSI_buffer, kommune SOSI_buffer, url SOSI_buffer, navn SOSI_buffer, dato SOSI_date, omradeid SOSI_int64, kopidato SOSI_datetime, originaldatavert SOSI_buffer, objtype SOSI_buffer
dsb.sivilforsvarsdistrikter (reader POSTGIS_1)
    attributes: lokalid uuid, navnerom text, versjonid varchar(2), msgeometry text, sivdistrik text, url text, navn text, kopidato timestamp, originaldatavert text, omradeid int4, objtype text
    -> dsb.sivilforsvarsdistrikter (writer SOSI_1)
dsb.sivilforsvarsdistrikter (writer SOSI_1)
    attributes: lokalid SOSI_buffer, navnerom SOSI_buffer, versjonid SOSI_varchar(2), msgeometry SOSI_buffer, sivdistrik SOSI_buffer, url SOSI_buffer, navn SOSI_buffer, kopidato SOSI_datetime, originaldatavert SOSI_buffer, omradeid SOSI_int32, objtype SOSI_buffer
dsb.brannstasjoner (reader POSTGIS_1)
    attributes: lokalid uuid, navnerom text, versjonid varchar(2), msgeometry text, brannstasjon text, kasernert text, brannvesen text, anleggid text, ajourdato date, informasjon text, opphav text, stasjonstype text, objtype text, dato date, brannsta_ text, omradeid int8, kopidato timestamp, originaldatavert text
    -> dsb.brannstasjoner (writer SOSI_1)
dsb.brannstasjoner (writer SOSI_1)
    attributes: lokalid SOSI_buffer, navnerom SOSI_buffer, versjonid SOSI_varchar(2), msgeometry SOSI_buffer, brannstasjon SOSI_buffer, kasernert SOSI_buffer, brannvesen SOSI_buffer, anleggid SOSI_buffer, ajourdato SOSI_date, informasjon SOSI_buffer, opphav SOSI_buffer, stasjonstype SOSI_buffer, objtype SOSI_buffer, dato SOSI_date, brannsta_ SOSI_buffer, omradeid SOSI_int64, kopidato SOSI_datetime, originaldatavert SOSI_buffer
dsb.sentraldistrikter110 (reader POSTGIS_1)
    attributes: lokalid uuid, navnerom text, versjonid varchar(2), msgeometry text, poly_ text, poly_id text, area text, perimeter text, oppr text, x float8, y float8, koordh text, sentral text, lokalisering text, opphav text, omradeid int8, originaldatavert text, kopidato timestamp, malemetode text, noyaktighet int8, synbarhet text, h_malemetode text, h_noyaktig text, max_avvik text, objtype text, navn text, datafangstdato date
    -> dsb.sentraldistrikter110 (writer SOSI_1)
dsb.sentraldistrikter110 (writer SOSI_1)
    attributes: lokalid SOSI_buffer, navnerom SOSI_buffer, versjonid SOSI_varchar(2), msgeometry SOSI_buffer, poly_ SOSI_buffer, poly_id SOSI_buffer, area SOSI_buffer, perimeter SOSI_buffer, oppr SOSI_buffer, x SOSI_real64, y SOSI_real64, koordh SOSI_buffer, sentral SOSI_buffer, lokalisering SOSI_buffer, opphav SOSI_buffer, omradeid SOSI_int64, originaldatavert SOSI_buffer, kopidato SOSI_datetime, malemetode SOSI_buffer, noyaktighet SOSI_int64, synbarhet SOSI_buffer, h_malemetode SOSI_buffer, h_noyaktig SOSI_buffer, max_avvik SOSI_buffer, objtype SOSI_buffer, navn SOSI_buffer, datafangstdato SOSI_date

Bookmark: Workspace Description
text_line (reader TEXTLINE_1)
    attributes: text_line_data buffer
    -> text_line (writer TEXTLINE_2)
text_line (writer TEXTLINE_2)
    attributes: text_line_data buffer
