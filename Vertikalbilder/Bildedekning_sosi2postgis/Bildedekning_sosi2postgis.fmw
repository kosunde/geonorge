FME workspace Bildedekning_sosi2postgis.fmw

Parameters:
- CONFIG_FILE:   # Python Script
      #-------------------------------------------------------------------------------
      # Name:        GetConfigFile
      # Purpose:
      #
      # Author:      xsunknu
      #
      # Created:     21.08.2015
      # Copyright:   (c) xsunknu 2015
      # Licence:     <your licence>
      #-------------------------------------------------------------------------------
      
      import os, fme
      
      fmwdir = fme.macroValues['FME_MF_DIR']
      fmwfile = fme.macroValues['FME_MF_NAME']
      
      fmwfile = os.path.join(fmwdir, fmwfile)
      configfile = os.path.splitext(fmwfile)[0] + '_config.xml'
      
      return configfile
- PG_DB:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgdb').text
      
      return value
- SOSI_DIR:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('sosidir').text
      
      return value
- MATCH_PATTERN:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('matchpattern').text
      
      return value
- LOG_FILE:   # Python Script
      #-------------------------------------------------------------------------------
      # Name:        GetConfigFile
      # Purpose:
      #
      # Author:      xsunknu
      #
      # Created:     21.08.2015
      # Copyright:   (c) xsunknu 2015
      # Licence:     <your licence>
      #-------------------------------------------------------------------------------
      
      import os, uuid, fme
      
      fmwdir = fme.macroValues['FME_MF_DIR']
      fmwfile = fme.macroValues['FME_MF_NAME']
      
      logdir = os.path.join(fmwdir, 'log')
      if not os.path.isdir(logdir):
          os.mkdir(logdir)
      
      logfile = os.path.splitext(fmwfile)[0] + '_' + str(uuid.uuid1()).replace('-','') + '.log'
      logfile = os.path.join(logdir, logfile)
      
      return logfile

Writers:
- POSTGIS_1: POSTGIS to $(PG_DB)
- POSTGRES_1: POSTGRES to $(PG_DB)

Note: Finner alle SOSI-filer som / inneholder 'vertikalbildedekning.sos' / i filnavnet.
PythonCreator
    PYTHONSOURCE:
      import fme, fmeobjects
      import os, sys

      # Template Class
      class FeatureCreator(object):
          def __init__(self):
              pass
          def close(self):
              dir = fme.macroValues['SOSI_DIR']
              pattern = fme.macroValues['MATCH_PATTERN']
              for root, dirs, files in os.walk(dir):
                  for f in files:
                      if f.lower().find(pattern) > 0:
                          feature = fmeobjects.FMEFeature()
                          feature.setAttribute("filename", os.path.join(root, f))
                          self.pyoutput(feature)
    PYTHONSYMBOL = FeatureCreator
    NEW_ATTRIBUTES = filename
    -> FeatureReader
FeatureReader
    ATTR_ACCUM_MODE = Only Use Result
    FORMAT = SOSI
    FEATURETYPES_RADIO = FEATURETYPES
    SOSI_READER_ALLOW_MISSING_MANDATORY_ATTRS = yes
    COMBINE_GEOM = Use Result
    INTERACT = <No Spatial Filter>
    DATASET = @Value(filename)
    SOSI_READER_LOG_WARNINGS = no
    SOSI_READER_ENFORCE_Z_VALUES = Auto-detect
    SOSI_READER_MISSING_Z_VALUE = -9999
    ATTRS_TO_EXPOSE = OBJTYPE BILDEMALESTOKK DEKNINGNUMMER EIER FLYFIRMA FOTODATO LENGDEOVERLAPP OPPDRAGSNAVN SIDEOVERLAPP MALEMETODE DEKNINGSNUMMER ORIENTERINGSDATA ORIENTERINGSMETODE AEROTRIANGULERING PROSJEKTRAPPORTLINK SCANNEROPPLØSNING BITS_PR_PIXEL BAKKEOPPLØSNING OPPDRAGSGIVER BILDEFILFORMAT SOSI_parent_guid SOSI_guid
    SOSI_READER_LOG_ERRORS = yes
    SOSI_READER_REFERENCE_SCALE = 1
    OUTPUT_FEATURES_DISPLAY = Based on Connections
    SOSI_READER_ATTRIBUTE_VALIDATION_LEVEL = Basic
    <OTHER> -> BulkAttributeRenamer
BulkAttributeRenamer
    CASE_CHANGE_TYPE = lowercase
    ATTRCHOICE = All Attributes
    PATTERN_ACTION_DISP = Change Case
    -> Reprojector
Reprojector
    DEST = EPSG:4258
    SOURCE = Read from feature
    RASTER_CELL_SIZE = Preserve Cells
    INTERPOLATION_TYPE_NAME = Nearest Neighbor
    REPROJECTED -> ArcStroker
ArcStroker
    MAKE_POLY = No
    STROKE_CHOICE = Maximum Deviation
    TOLERANCE_VAL = 1
    STROKED -> GeometryValidator
GeometryValidator
    SUMMARY = Detailed
    REPAIR = Yes
    DUP_COORDS_CHECK_Z = Yes
    MISSING_VERTEX_NORMALS = MISSING_VERTEX_NORMALS
    ISSUE_ATTR_NAME = _issues
    NAN_REMOVAL = NAN_REMOVAL
    PLANAR_SURFACE = PLANAR_SURFACE
    OGC_SIMPLE_CHECK = OGC_SIMPLE_CHECK
    ANGULAR_TOLERANCE_CHOICE = Automatic
    TYPE_REPAIR = TYPE_REPAIR
    RULES = NAN_REMOVAL%""%"Yes"%NULL_REMOVAL%""%"Yes"%CONSECUTIVE_IDENTICAL_VERTICES_2D%CONSECUTIVE_IDENTICAL_VERTICES_2D_PARAMS%"Yes"%TYPE_REPAIR%TYPE_REPAIR_PARAMS%"Yes"%SELF_INTERSECTING%SELF_INTERSECTING_PARAMS%"Yes"%PLANAR_SURFACE%PLANAR_SURFACE_PARAMS%"Yes"%SHELL_VALIDATION%""%"Yes"%SOLID_VOID_REPAIR%""%"Yes"%OGC_SIMPLE_CHECK%""%"No"%OGC_VALID_CHECK%""%"No"%MISSING_TEXTURE_COORDINATES%""%"Yes"%MISSING_VERTEX_NORMALS%""%"Yes"%AREA_ORIENTATION%ORIENTATION_CHECK_PARAMS%"Yes"
    SHELL_VALIDATION = SHELL_VALIDATION
    SELF_INTERSECTING = SELF_INTERSECTING
    MISSING_TEXTURE_COORDINATES = MISSING_TEXTURE_COORDINATES
    CONSECUTIVE_IDENTICAL_VERTICES_2D = CONSECUTIVE_IDENTICAL_VERTICES_2D
    OGC_VALID_CHECK = OGC_VALID_CHECK
    AREA_ORIENTATION = AREA_ORIENTATION
    CHECK_HOLE_TOUCHING_POLYGON = No
    PRESETS = All
    NULL_REMOVAL = NULL_REMOVAL
    ARC_ENDPOINT_TOLERANCE_MODE = Auto
    SOLID_VOID_REPAIR = SOLID_VOID_REPAIR
    THICKNESS_TOLERANCE_CHOICE = Automatic
    ORIENTATION_CHECK_DIR = Valid
    PASSED -> FeatureTypeFilter
    REPAIRED -> FeatureTypeFilter
    FAILED -> GeometryValidator_Failed
FeatureTypeFilter
    ATTRIBUTES = Bildedekningsgrense,Vertikalbildedekning,FOTODATO_SOSI,EIER_SOSI,<BLANK>,<UNFILTERED>
    Vertikalbildedekning -> AttributeCreator_2
    Bildedekningsgrense -> AttributeCreator
    FOTODATO_SOSI -> FeatureMerger [input 1]
    EIER_SOSI -> FeatureMerger_2 [input 1]
AttributeCreator
    ATTR_LIST = objid,@Evaluate(@Count(bildedekningsgrense, 1))
    -> vertikalbilde.bildedekningsgrense (writer POSTGIS_1)
AttributeCreator_2
    ATTR_LIST = objid,@Evaluate(@Count(vertikalbidedekning, 1)),geodataeier,@Value(eier),fotodato,"FME_CONDITIONAL:DEFAULT_VALUE'@Value(fotodato)'BOOL_OP;OR;COMPOSITE_TEST;<Unused>;TEST @Value(fotodato) < 1900-01-01 00:00:00'FME_NULL_VALUE'FME_NUM_CONDITIONS2___",bakkopplosning,@Value(bakkeoppløsning),bitsprpixel,@Value(bits_pr_pixel),skanneropplosning,@Value(scanneroppløsning)
    -> FeatureMerger_2 [input 2]
    -> FeatureMerger [input 2]
    -> AttributeCreator_3
    -> AttributeCreator_5
    -> vertikalbilde.vertikalbildedekning (writer POSTGIS_1)
GeometryValidator_Failed: Inspector

Bookmark: PostGIS
vertikalbilde.bildedekningsgrense (writer POSTGIS_1)
    attributes: objid int4,PRIKEY, objtype varchar(32), malemetode int2
vertikalbilde.vertikalbildedekning (writer POSTGIS_1)
    attributes: objid int4,PRIKEY, objtype varchar(32), oppdragsnavn varchar(255), dekningsnummer varchar(80), bakkeopplosning int4, bildefilformat int4, bildemalestokk int4, bitsprpixel int4, flyfirma varchar(80), oppdragsgiver varchar(80), aerotriangulering int4, orienteringsdata varchar(80), orienteringsmetode int4, lengdeoverlapp int4, sideoverlapp int4, prosjektrapportlink varchar(255), skanneropplosning float4

Bookmark: Håndterer relaterte data, 1-n attributter
FeatureMerger
    IGNORE_NULLS = No
    ATTR_CONFLICT_RES = Use Requestor
    SUPPLIERS_FIRST = No
    MERGE_TYPE = Attributes Only
    PROCESS_DUPS = No
    ATTR_ACCUM_MODE = Merge Supplier
    JOIN_KEYS = @Value(sosi_parent_guid) @Value(sosi_guid) AUTO
    MERGED -> AttributeCreator_3
AttributeCreator_3
    ATTR_LIST = vertikalbildedekningfk,@Value(objid),objid,@Evaluate(@Count(fotodato, 1))
    -> DateFormatter
DateFormatter
    FMT = FME Date/Time (%Y%m%d%H%M%S)
    SRCFMT = Unknown - Automatic Detection
    DATE_ATTR = fotodato
    INVALID_DATE_VALUE = FME_NULL_VALUE
    -> Tester
Tester
    BOOL_OP = AND
    TEST_DESCRIPTION = ""
    TEST_MODE = Automatic
    TEST_CLAUSE:
      TEST fotodato NOT_ATTRIBUTE_VALUE_NULL ""
      TEST fotodato NOT_ATTRIBUTE_IS_EMPTY ""
      TEST fotodato NOT_ATTRIBUTE_IS_MISSING ""
    PASSED -> vertikalbilde.fotodato (writer POSTGRES_1)
FeatureMerger_2
    IGNORE_NULLS = No
    ATTR_CONFLICT_RES = Use Requestor
    SUPPLIERS_FIRST = No
    MERGE_TYPE = Attributes Only
    PROCESS_DUPS = No
    ATTR_ACCUM_MODE = Merge Supplier
    JOIN_KEYS = @Value(sosi_parent_guid) @Value(sosi_guid) AUTO
    MERGED -> AttributeCreator_5
AttributeCreator_5
    ATTR_LIST = vertikalbildedekningfk,@Value(objid),objid,@Evaluate(@Count(eier, 1))
    -> Tester_2
Tester_2
    BOOL_OP = AND
    TEST_DESCRIPTION = ""
    TEST_MODE = Automatic
    TEST_CLAUSE:
      TEST fotodato NOT_ATTRIBUTE_VALUE_NULL ""
      TEST fotodato NOT_ATTRIBUTE_IS_EMPTY ""
      TEST fotodato NOT_ATTRIBUTE_IS_MISSING ""
    PASSED -> vertikalbilde.eier (writer POSTGRES_1)

Bookmark: PostgreSQL
vertikalbilde.fotodato (writer POSTGRES_1)
    attributes: objid int4,PRIKEY, fotodato date, vertikalbildedekningfk int4,BTREE
vertikalbilde.eier (writer POSTGRES_1)
    attributes: objid int4,PRIKEY, geodataeier varchar(80), vertikalbildedekningfk int4,BTREE
