FME workspace Bildedekning_postgis2sosi.fmw
# Copyright: (c) xgrimor 2015
# Licence: <your licence>
Shutdown Python:
      # -*- coding: utf-8 -*-
      #-------------------------------------------------------------------------------
      # Name:        zipfiles.py
      # Purpose:     Pakker filer i output folderen
      #
      # Author:      xsunknu
      #
      # Created:     18.09.2015
      # Copyright:   (c) xsunknu 2015
      # Licence:     <your licence>
      #-------------------------------------------------------------------------------

      import sys, os, zipfile, fme

      def zip(sosifile, zfile):
          from os.path import basename

          # Lager korresponderende zip-fil av SOSI-fil
          if os.path.isfile(zfile):
              os.remove(zfile)

          zf = zipfile.ZipFile(zfile, "w", zipfile.ZIP_DEFLATED)

          # Ønsker ikke full sti inn i ZIP-filen
          arcname = basename(sosifile)

          # ZIP-formatet støtter ikke non-ascii tegn
          # Erstatter AØÅæøå med ascii-tegn
          arcname = arcname.replace('\xc6', 'E')
          arcname = arcname.replace('\xd8', 'O')
          arcname = arcname.replace('\xc5', 'A')
          arcname = arcname.replace('\xe6', 'e')
          arcname = arcname.replace('\xf8', 'o')
          arcname = arcname.replace('\xe5', 'a')

          zf.write(sosifile, arcname)
          zf.close()
          os.remove(sosifile)

          return

      def main():

          # Kjøres ikke på FME Server, da FME Server selv sørger for pakkingen
          if not 'FME_SERVER_DEST_DIR' in fme.macroValues:
              if 'FANOUT_FOLDER' in fme.macroValues:
                  path = fme.macroValues['FANOUT_FOLDER']
                  for dirpath, dnames, fnames in os.walk(path):
                      for f in fnames:
                          if f.endswith(".sos"):
                              # Scanner gjennom alle SOSI-filer
                              sosifile = os.path.join(path, f)
                              zfile = os.path.splitext(sosifile)[0] + '.zip'
                              if os.path.isfile(zfile):

                                  # Korresponderende ZIP-fil finnes, sjekker timestamps
                                  sositstamp = os.stat(sosifile).st_mtime
                                  ziptstamp = os.stat(zfile).st_mtime

                                  if sositstamp > ziptstamp:
                                      # SOSI-fil er nyere enn ZIP-fila, ZIP-fila oppdateres
                                      # SOSI-fila slettes
                                      try:
                                          zip(sosifile, zfile)
                                      except:
                                          print 'Kunne ikke pakke: ' + sosifile
                                  else:
                                      # SOSI-fila er eldre enn ZIP-fila
                                      # SOSI-fila slettes
                                      try:
                                          os.remove(sosifile)
                                      except:
                                          print 'Kunne ikke slette: ' + sosifile
                              else:
                                  # ZIP-fila eksisterer ikke og lages
                                  # SOSI-fila slettes
                                  try:
                                      zip(sosifile, zfile)
                                  except:
                                      print 'Kunne ikke pakke: ' + sosifile


      if __name__ == '__main__':
          main()

Parameters:
- KNR =   # Kommune(r)
- FNR =   # Fylke(r)
- FRA_DATO = 1930-01-01   # Fra dato
- TIL_DATO = 1939-12-31   # Til dato
- CLIPPERCOORDS =   # Clipper coordinates
- CLIPPER_EPSG_CODE =   # Clipper coordinate system
- CLIPPER_FILE =   # "" Clipper file (any format)
- OUTPUT_EPSG_CODE = 25833   # Destination coordinate system
- FANOUT = Norge   # Fanout områder
- WHERE_CLAUSE:   # Python Script
      #-------------------------------------------------------------------------------
      # Name:        MakeWhereClause
      # Purpose:     Create whereclause based on parameter SAMLING
      #
      # Author:      xsunknu
      #
      # Created:     21.08.2015
      # Copyright:   (c) xsunknu 2015
      # Licence:     <your licence>
      #-------------------------------------------------------------------------------
      
      import os, fme
      
      
      start = "'" + FME_MacroValues['FRA_DATO'] + "'"
      end = "'" + FME_MacroValues['TIL_DATO'] + "'"
      whereclause = 'fotodato > ' + start + ' and fotodato < ' + end
      
      return whereclause
- CONFIG_FILE:   # Python Script
      #-------------------------------------------------------------------------------
      # Name:        GetConfigFile
      # Purpose:
      #
      # Author:      xsunknu
      #
      # Created:     21.08.2015
      # Copyright:   (c) xsunknu 2015
      # Licence:     <your licence>
      #-------------------------------------------------------------------------------
      
      import os, fme
      
      fmwdir = fme.macroValues['FME_MF_DIR']
      fmwfile = fme.macroValues['FME_MF_NAME']
      
      fmwfile = os.path.join(fmwdir, fmwfile)
      configfile = os.path.splitext(fmwfile)[0] + '_config.xml'
      
      return configfile
- CLIPPERCOORDSYS:   # Python Script
      #-------------------------------------------------------------------------------
      # Name:        SetCoordinateSystem
      # Purpose:
      #
      # Author:      xsunknu
      #
      # Created:     21.08.2015
      # Copyright:   (c) xsunknu 2015
      # Licence:     <your licence>
      #-------------------------------------------------------------------------------
      
      import os, fme
      
      EPSGvalue = fme.macroValues['CLIPPER_EPSG_CODE']
      EPSGcode  = 'EPSG:' + EPSGvalue
      
      return EPSGcode
- DESTCOORDSYS:   # Python Script
      #-------------------------------------------------------------------------------
      # Name:        SetCoordinateSystem
      # Purpose:
      #
      # Author:      xsunknu
      #
      # Created:     21.08.2015
      # Copyright:   (c) xsunknu 2015
      # Licence:     <your licence>
      #-------------------------------------------------------------------------------
      
      import os, fme
      
      EPSGvalue = fme.macroValues['OUTPUT_EPSG_CODE']
      EPSGcode  = 'EPSG:' + EPSGvalue
      
      return EPSGcode
- SPATIAL_FILTER:   # Python Script
      #-------------------------------------------------------------------------------
      # Name:        SetSpatialFilter
      # Purpose:
      #
      # Author:      xsunknu
      #
      # Created:     21.08.2015
      # Copyright:   (c) xsunknu 2015
      # Licence:     <your licence>
      #-------------------------------------------------------------------------------
      
      import fme
      
      spatialfilter = 'Intersects'
      
      knr = fme.macroValues['KNR']
      fnr = fme.macroValues['FNR']
      coords = fme.macroValues['CLIPPERCOORDS']
      file = fme.macroValues['CLIPPER_FILE']
      
      if knr == '' and fnr == '' and coords == '' and file == '':
          spatialfilter = '<No Spatial Filter>'
      
      return spatialfilter
- FIXEDCLIPPERCOORDS:   # Python Script
      #-------------------------------------------------------------------------------
      # Name:        FixClipperCoords
      # Purpose:
      #
      # Author:      xsunknu
      #
      # Created:     21.08.2015
      # Copyright:   (c) xsunknu 2015
      # Licence:     <your licence>
      #-------------------------------------------------------------------------------
      
      import fme
      clippercoords = fme.macroValues['CLIPPERCOORDS']
      
      if clippercoords == '':
          clippercoords = '1 1'
      
      return clippercoords
- HOVEDTEMA = Vertikalbilder   # Hovedtema
- UNDERTEMA = Bildedekning   # Undertema
- PG_DB:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgdb').text
      
      return value
- PG_HOST:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pghost').text
      
      return value
- PG_PORT:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgport').text
      
      return value
- PG_USER:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pguser').text
      
      return value
- PG_PWD:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgpwd').text
      
      return value
- MAPPINGFILE:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme, os
      from xml.etree import ElementTree as ET
      
      #Read XML config file
      configtree = ET.parse(fme.macroValues['CONFIG_FILE'])
      configdoc = configtree.getroot()
      
      value = os.path.join(fme.macroValues['FME_MF_DIR'], configdoc.find('mappingfile').text)
      
      return value
- FANOUT_FOLDER:   # Python Script
      #-------------------------------------------------------------------------------
      # Name:        GetConfigFile
      # Purpose:
      #
      # Author:      xsunknu
      #
      # Created:     21.08.2015
      # Copyright:   (c) xsunknu 2015
      # Licence:     <your licence>
      #-------------------------------------------------------------------------------
      
      import os, fme
      from xml.etree import ElementTree as ET
      
      if 'FME_SERVER_DEST_DIR' in fme.macroValues:
          value = fme.macroValues['FME_SERVER_DEST_DIR']
      else:
          #Read XML config file
          configtree = ET.parse(fme.macroValues['CONFIG_FILE'])
          configdoc = configtree.getroot()
          value = configdoc.find('destdir').text
      
      return value
- LOG_FILE:   # Python Script
      #-------------------------------------------------------------------------------
      # Name:        GetConfigFile
      # Purpose:
      #
      # Author:      xsunknu
      #
      # Created:     21.08.2015
      # Copyright:   (c) xsunknu 2015
      # Licence:     <your licence>
      #-------------------------------------------------------------------------------
      
      import os, uuid, fme
      
      fmwdir = fme.macroValues['FME_MF_DIR']
      fmwfile = fme.macroValues['FME_MF_NAME']
      
      logdir = os.path.join(fmwdir, 'log')
      if not os.path.isdir(logdir):
          os.mkdir(logdir)
      
      logfile = os.path.splitext(fmwfile)[0] + '_' + str(uuid.uuid1()).replace('-','') + '.log'
      logfile = os.path.join(logdir, logfile)
      
      return logfile

Readers:
- POSTGIS_1: POSTGIS from $(PG_DB)

Writers:
- SOSI_1: SOSI to D:\scratch\sikringssoner.sos

CreateClipper
    CLIPPERCOORDS = $(FIXEDCLIPPERCOORDS)
    CLIPPERCOORDSYS = $(CLIPPERCOORDSYS)
    DESTCOORDSYS = $(DESTCOORDSYS)
    -> Clipper [input 1]
    -> FeatureReader_3

Bookmark: Fylke and/or kommune clippers
admingrense.fylkeflate (reader POSTGIS_1)
    attributes: fylkeid int4, navn varchar(80)
    -> Tester
    -> AttributeCreator_8
AttributeCreator_8
    ATTR_LIST = _clippercoords,$(CLIPPERCOORDS),_clipper_file,$(CLIPPER_FILE),_fnr,$(FNR),_knr,$(KNR)
    -> Tester_4
Tester_4
    TEST_MODE = Automatic
    TEST_CLAUSE:
      TEST _clipper_file ATTRIBUTE_IS_EMPTY ""
      TEST _clippercoords ATTRIBUTE_IS_EMPTY ""
      TEST _fnr ATTRIBUTE_IS_EMPTY ""
      TEST _knr ATTRIBUTE_IS_EMPTY ""
    BOOL_OP = AND
    TEST_DESCRIPTION = ""
    PASSED -> Reprojector_2
Tester
    TEST_MODE = Automatic
    TEST_CLAUSE = TEST @Value(fylkeid) IN $(FNR)
    BOOL_OP = OR
    TEST_DESCRIPTION = ""
    PASSED -> Reprojector_2
admingrense.kommuneflate (reader POSTGIS_1)
    attributes: kommuneid int4, navn varchar(80)
    -> Tester_2
Tester_2
    TEST_MODE = Automatic
    TEST_CLAUSE = TEST @Value(kommuneid) IN $(KNR)
    BOOL_OP = OR
    TEST_DESCRIPTION = ""
    PASSED -> Reprojector_2
Note: Sender inn hele landet som initiator / dersom alle klippeparametrene er / blanke
Reprojector_2
    RASTER_CELL_SIZE = Preserve Cells
    DEST = EPSG:4258
    SOURCE = Read from feature
    INTERPOLATION_TYPE_NAME = Nearest Neighbor
    REPROJECTED -> Clipper [input 1]
    REPROJECTED -> Dissolver

Bookmark: Clipper file (any format)
Creator
    GEOMTYPE = Geometry Object
    NUM = 1
    CREATED -> FeatureReader
FeatureReader
    COMBINE_GEOM = Use Result
    FORMAT = GENERIC
    OUTPUT_FEATURES_DISPLAY = Based on Connections
    GENERIC_REAL_FORMAT = GUESS_FROM_EXTENSION
    ATTRIBUTES = NewFeatureType,
    INTERACT = $(SPATIAL_FILTER)
    FEATURETYPES_RADIO = FEATURETYPES
    ATTR_ACCUM_MODE = Only Use Result
    DATASET = $(CLIPPER_FILE)
    <OTHER> -> Reprojector_3
Reprojector_3
    RASTER_CELL_SIZE = Preserve Cells
    DEST = EPSG:4258
    SOURCE = Read from feature
    INTERPOLATION_TYPE_NAME = Nearest Neighbor
    REPROJECTED -> Clipper [input 1]
    REPROJECTED -> Dissolver

Bookmark: Leser features fra views og kobler inn relaterte tabeller
Dissolver
    NO_OVRLP = No
    ACCUM_INPUT_ATTRS = No
    AREA -> FeatureReader_3
FeatureReader_3
    ATTRIBUTES = vertikalbilde.v_sp_bildedekningsgrense,"objid,objtype,malemetode,fotodato,fk",vertikalbilde.v_vertikalbildedekning,"objid,objtype,oppdragsnavn,dekningsnummer,bakkeopplosning,bildefilformat,bildemalestokk,bitsprpixel,flyfirma,oppdragsgiver,aerotriangulering,orienteringsdata,orienteringsmetode,lengdeoverlapp,sideoverlapp,prosjektrapportlink,skanneropplosning,fotodato,vertikalbildedekningfk"
    POSTGIS_DISABLE_COLLECTION_SPLITTING = yes
    POSTGIS_CLIP_TO_ENVELOPE = NO
    FEATURETYPES_RADIO = FEATURETYPES
    POSTGIS_SCHEMALIST = vertikalbilde
    POSTGIS_QUERY_FEATURE_TYPES_FOR_MERGE_FILTERS = Yes
    OUTPUT_FEATURES_DISPLAY = Based on Connections
    INTERACT = Intersects
    POSTGIS_USE_SEARCH_ENVELOPE = NO
    DATASET = $(PG_DB)
    POSTGIS_PORT = $(PG_PORT)
    FORMAT = POSTGIS
    WHERE = $(WHERE_CLAUSE)
    POSTGIS_USE_TRUE_POSTGIS_TYPES = yes
    POSTGIS_USER_NAME = $(PG_USER)
    FEATURETYPES = vertikalbilde.v_sp_bildedekningsgrense vertikalbilde.v_vertikalbildedekning
    POSTGIS_PASSWORD = $(PG_PWD)
    POSTGIS_HOST = $(PG_HOST)
    COMBINE_GEOM = Use Result
    ATTR_ACCUM_MODE = Only Use Result
    vertikalbilde.v_sp_bildedekningsgrense -> CoordinateSystemSetter
    vertikalbilde.v_vertikalbildedekning -> Aggregator_4
    vertikalbilde.v_vertikalbildedekning -> FeatureMerger [input 1]
Aggregator_4
    ACCUM_ATTRS_NAME = No
    CONCAT_ATTRS = objid
    ORDERED = No
    MODE = Attributes Only
    SEP = ,
    AGGREGATE -> AttributeCreator_9
    AGGREGATE -> AttributeCreator_2
AttributeCreator_9
    ATTR_LIST = sql,select * from vertikalbilde.fotodato where vertikalbildedekningfk in (@Value(objid));
    -> SQLExecutor
SQLExecutor
    EXPOSED_ATTRIBUTE_LIST = objid,fotodato,vertikalbildedekningfk
    POSTGRES_QUERY_FEATURE_TYPES_FOR_MERGE_FILTERS = Yes
    POSTGRES_HOST = $(PG_HOST)
    DATASET = $(PG_DB)
    SQL_STATEMENT = @Value(sql)
    COMBINE_GEOM = Initiator Geometry Only
    POSTGRES_PORT = $(PG_PORT)
    FORMAT = POSTGRES
    COMBINE_ATTRS = Result Attributes Only
    POSTGRES_USER_NAME = $(PG_USER)
    POSTGRES_PASSWORD = $(PG_PWD)
    RESULT -> FeatureMerger [input 2]
FeatureMerger
    IGNORE_NULLS = No
    LIST_NAME = L:fotodatoer
    JOIN_KEYS = @Value(objid) @Value(vertikalbildedekningfk) AUTO
    SUPPLIERS_FIRST = No
    ATTR_CONFLICT_RES = Use Requestor
    PROCESS_DUPS = No
    MERGE_TYPE = Attributes and Geometry
    ATTR_ACCUM_MODE = Merge Supplier
    MERGED -> FeatureMerger_2 [input 1]
AttributeCreator_2
    ATTR_LIST = sql,select * from vertikalbilde.eier where vertikalbildedekningfk in (@Value(objid));
    -> SQLExecutor_2
SQLExecutor_2
    EXPOSED_ATTRIBUTE_LIST = objid,eier,vertikalbildedekningfk
    POSTGRES_QUERY_FEATURE_TYPES_FOR_MERGE_FILTERS = Yes
    POSTGRES_HOST = $(PG_HOST)
    DATASET = $(PG_DB)
    SQL_STATEMENT = @Value(sql)
    COMBINE_GEOM = Initiator Geometry Only
    POSTGRES_PORT = $(PG_PORT)
    FORMAT = POSTGRES
    COMBINE_ATTRS = Result Attributes Only
    POSTGRES_USER_NAME = $(PG_USER)
    POSTGRES_PASSWORD = $(PG_PWD)
    RESULT -> FeatureMerger_2 [input 2]
FeatureMerger_2
    IGNORE_NULLS = No
    LIST_NAME = L:eiere
    JOIN_KEYS = @Value(objid) @Value(vertikalbildedekningfk) AUTO
    SUPPLIERS_FIRST = No
    ATTR_CONFLICT_RES = Use Requestor
    PROCESS_DUPS = No
    MERGE_TYPE = Attributes and Geometry
    ATTR_ACCUM_MODE = Merge Supplier
    MERGED -> CoordinateSystemSetter
CoordinateSystemSetter
    COORDSYS = EPSG:4258
    -> AttributeCreator_12
AttributeCreator_12
    ATTR_LIST = _clippercoords,$(CLIPPERCOORDS),_clipper_file,$(CLIPPER_FILE),_fnr,$(FNR),_knr,$(KNR)
    -> TestFilter
TestFilter
    DEFAULT_VALUE = <UNFILTERED>
    TEST_LIST:
      BOOL_OP,AND,COMPOSITE_TEST,<Unused>,TEST_CLAUSE,"TEST _clipper_file ATTRIBUTE_IS_EMPTY """"
      TEST _clippercoords ATTRIBUTE_IS_EMPTY """"
      TEST _fnr ATTRIBUTE_IS_EMPTY """"
      TEST _knr ATTRIBUTE_IS_EMPTY """"",Landsdekkende,BOOL_OP,AND,COMPOSITE_TEST,<Unused>,TEST_CLAUSE,"TEST _clipper_file ATTRIBUTE_IS_EMPTY """"
      TEST _clippercoords ATTRIBUTE_IS_EMPTY """"
      TEST _fnr NOT_ATTRIBUTE_IS_EMPTY """"
      TEST _knr ATTRIBUTE_IS_EMPTY """"",Fylkesvis,BOOL_OP,AND,COMPOSITE_TEST,<Unused>,TEST_CLAUSE,"TEST _clipper_file ATTRIBUTE_IS_EMPTY """"
      TEST _clippercoords ATTRIBUTE_IS_EMPTY """"
      TEST _fnr ATTRIBUTE_IS_EMPTY """"
      TEST _knr NOT_ATTRIBUTE_IS_EMPTY """"",Kommunevis
    Fylkesvis -> Clipper [input 2]
    Kommunevis -> Clipper [input 2]
    <UNFILTERED> -> Clipper [input 2]
    Landsdekkende -> SosiFilenameSetter

Bookmark: Klipper
Clipper
    ATTR_ACCUM_MODE = Merge Clipper
    CLIPPED_ATTR = _clipped
    BOUNDARY_CASES = Treat as Inside
    ATTR_CONFLICT_RES = Use Clippee
    CREATE_AGGREGATES = No
    PRESERVE_CLIPPEE_EXTENTS = No
    CLIP_TYPE = Multiple Clippers
    INSIDE -> SosiFilenameSetter

Bookmark: Tagger og reprojiserer
SosiFilenameSetter
    BITSPRPIXEL = @Value(bitsprpixel)
    ORIENTERINGSDATA = @Value(orienteringsdata)
    AEROTRIANGULERING = @Value(aerotriangulering)
    OPPDRAGSNAVN = @Value(oppdragsnavn)
    OPPDRAGSGIVER = @Value(oppdragsgiver)
    BILDEMALESTOKK = @Value(bildemalestokk)
    FLYFIRMA = @Value(flyfirma)
    KOMMUNEID = @Value(kommuneid)
    OBJID = @Value(objid)
    DEKNINGSNUMMER = @Value(dekningsnummer)
    PG_DB:
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------

      import fme
      from xml.etree import ElementTree as ET

      #Read XML config file
      configtree = ET.parse(fme.macroValues['CONFIG_FILE'])
      configdoc = configtree.getroot()
      value = configdoc.find('pgdb').text

      return value
    PG_PWD:
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------

      import fme
      from xml.etree import ElementTree as ET

      #Read XML config file
      configtree = ET.parse(fme.macroValues['CONFIG_FILE'])
      configdoc = configtree.getroot()
      value = configdoc.find('pgpwd').text

      return value
    NAVN = @Value(navn)
    HOVEDTEMA = $(HOVEDTEMA)
    VERTIKALBILDEDEKNINGFK = @Value(vertikalbildedekningfk)
    PROSJEKTRAPPORTLINK = @Value(prosjektrapportlink)
    EIER = @Value(eier)
    PG_HOST:
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------

      import fme
      from xml.etree import ElementTree as ET

      #Read XML config file
      configtree = ET.parse(fme.macroValues['CONFIG_FILE'])
      configdoc = configtree.getroot()
      value = configdoc.find('pghost').text

      return value
    OBJTYPE = @Value(objtype)
    SIDEOVERLAPP = @Value(sideoverlapp)
    OUTPUT_EPSG_CODE = $(OUTPUT_EPSG_CODE)
    FYLKEID = @Value(fylkeid)
    PG_USER:
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------

      import fme
      from xml.etree import ElementTree as ET

      #Read XML config file
      configtree = ET.parse(fme.macroValues['CONFIG_FILE'])
      configdoc = configtree.getroot()
      value = configdoc.find('pguser').text

      return value
    FANOUT = $(FANOUT)
    ORIENTERINGSMETODE = @Value(orienteringsmetode)
    FOTODATO = @Value(fotodato)
    SKANNEROPPLOSNING = @Value(skanneropplosning)
    BILDEFILFORMAT = @Value(bildefilformat)
    LENGDEOVERLAPP = @Value(lengdeoverlapp)
    BAKKEOPPLOSNING = @Value(bakkeopplosning)
    PG_PORT:
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------

      import fme
      from xml.etree import ElementTree as ET

      #Read XML config file
      configtree = ET.parse(fme.macroValues['CONFIG_FILE'])
      configdoc = configtree.getroot()
      value = configdoc.find('pgport').text

      return value
    SAMLING = $(FRA_DATO)
    UNDERTEMA = $(UNDERTEMA)
    -> Reprojector
Reprojector
    RASTER_CELL_SIZE = Preserve Cells
    DEST = $(DESTCOORDSYS)
    SOURCE = Read from feature
    INTERPOLATION_TYPE_NAME = Nearest Neighbor
    REPROJECTED -> AttributeCreator
AttributeCreator
    ATTR_LIST = OBJTYPE,@Value(objtype)
    -> FeatureTypeFilter
FeatureTypeFilter
    ATTRIBUTES = vertikalbilde.v_sp_bildedekningsgrense,vertikalbilde.v_vertikalbildedekning,<BLANK>,<UNFILTERED>
    vertikalbilde.v_sp_bildedekningsgrense -> vertikalbilde.bildedekningsgrense (writer SOSI_1)
    vertikalbilde.v_vertikalbildedekning -> vertikalbilde.vertikalbildedekning (writer SOSI_1)

Bookmark: SOSI-output
vertikalbilde.bildedekningsgrense (writer SOSI_1)
    attributes: malemetode SOSI_int16
vertikalbilde.vertikalbildedekning (writer SOSI_1)
    attributes: oppdragsnavn SOSI_varchar(255), dekningsnummer SOSI_varchar(80), bakkeopplosning SOSI_int32, bildefilformat SOSI_int32, bildemalestokk SOSI_int32, bitsprpixel SOSI_int32, flyfirma SOSI_varchar(80), L:fotodatoer{}.fotodato SOSI_date, L:eiere{}.eier SOSI_varchar(80), oppdragsgiver SOSI_varchar(80), aerotriangulering SOSI_int32, orienteringsdata SOSI_varchar(80), orienteringsmetode SOSI_int32, lengdeoverlapp SOSI_int32, sideoverlapp SOSI_int32, prosjektrapportlink SOSI_varchar(255), skanneropplosning SOSI_real32

FME custom transformer SosiFilenameSetter

Parameters:
- SAMLING =   # Samling
- OUTPUT_EPSG_CODE = 25832   # Destination coordinate system
- FANOUT = Kommuner   # Fanout områder
- UNDERTEMA =   # Undertema
- HOVEDTEMA =   # Hovedtema
- AEROTRIANGULERING = @Value(aerotriangulering)   # aerotriangulering
- BAKKEOPPLOSNING = @Value(bakkeopplosning)   # bakkeopplosning
- BILDEFILFORMAT = @Value(bildefilformat)   # bildefilformat
- BILDEMALESTOKK = @Value(bildemalestokk)   # bildemalestokk
- BITSPRPIXEL = @Value(bitsprpixel)   # bitsprpixel
- DEKNINGSNUMMER = @Value(dekningsnummer)   # dekningsnummer
- EIER = @Value(eier)   # eier
- FLYFIRMA = @Value(flyfirma)   # flyfirma
- FOTODATO = @Value(fotodato)   # fotodato
- FYLKEID = @Value(fylkeid)   # fylkeid
- KOMMUNEID = @Value(kommuneid)   # kommuneid
- LENGDEOVERLAPP = @Value(lengdeoverlapp)   # lengdeoverlapp
- NAVN = @Value(navn)   # navn
- OBJID = @Value(objid)   # objid
- OBJTYPE = @Value(objtype)   # objtype
- OPPDRAGSGIVER = @Value(oppdragsgiver)   # oppdragsgiver
- OPPDRAGSNAVN = @Value(oppdragsnavn)   # oppdragsnavn
- ORIENTERINGSDATA = @Value(orienteringsdata)   # orienteringsdata
- ORIENTERINGSMETODE = @Value(orienteringsmetode)   # orienteringsmetode
- PROSJEKTRAPPORTLINK = @Value(prosjektrapportlink)   # prosjektrapportlink
- SIDEOVERLAPP = @Value(sideoverlapp)   # sideoverlapp
- SKANNEROPPLOSNING = @Value(skanneropplosning)   # skanneropplosning
- VERTIKALBILDEDEKNINGFK = @Value(vertikalbildedekningfk)   # vertikalbildedekningfk
- PG_DB:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgdb').text
      
      return value
- PG_HOST:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pghost').text
      
      return value
- PG_PORT:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgport').text
      
      return value
- PG_PWD:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgpwd').text
      
      return value
- PG_USER:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pguser').text
      
      return value

Input (input)
    -> ParameterFetcher
ParameterFetcher
    ATTR_LIST = _output_epsg_code {$(OUTPUT_EPSG_CODE)} _fanout {$(FANOUT)}
    -> AttributeValueMapper
Note: Fikser kjente feil i kommunenummer
AttributeValueMapper
    DIRECTION = Forward (Source To Destination)
    LUT = 1901,1903
    SRC = kommuneid
    DEFAULT_VALUE = @Value(kommuneid)
    VAL_ATTR = kommuneid
    -> TestFilter_2
TestFilter_2
    DEFAULT_VALUE = Ufiltrert
    TEST_LIST = BOOL_OP,OR,COMPOSITE_TEST,<Unused>,TEST_CLAUSE,"TEST $(FANOUT) = Kommuner",Kommuner,BOOL_OP,OR,COMPOSITE_TEST,<Unused>,TEST_CLAUSE,"TEST $(FANOUT) = Fylker",Fylker
    Kommuner -> Joiner
    Fylker -> Joiner_2
    Ufiltrert -> AttributeCreator_13
Joiner
    POSTGIS_PASSWORD = $(PG_PWD)
    FORMAT = POSTGIS
    POSTGIS_USER_NAME = $(PG_USER)
    PREFETCH_EXHAUSTIVE = Yes
    POSTGIS_PORT = $(PG_PORT)
    CACHE_SIZE = 5000
    POSTGIS_QUERY_FEATURE_TYPES_FOR_MERGE_FILTERS = Yes
    JOIN_KEYS = kommuneid kommuneid
    ADDED_FIELDS = navn
    POSTGIS_DISABLE_COLLECTION_SPLITTING = yes
    MATCH_RULE_DISPLAY = Must Match Exactly One (1:1)
    POSTGIS_USE_TRUE_POSTGIS_TYPES = yes
    POSTGIS_HOST = $(PG_HOST)
    DATASET = $(PG_DB)
    TABLE = admingrense.kommuner
    JOINED -> StringReplacer_2
Joiner_2
    POSTGIS_PASSWORD = $(PG_PWD)
    FORMAT = POSTGIS
    POSTGIS_USER_NAME = $(PG_USER)
    PREFETCH_EXHAUSTIVE = Yes
    POSTGIS_PORT = $(PG_PORT)
    CACHE_SIZE = 5000
    POSTGIS_QUERY_FEATURE_TYPES_FOR_MERGE_FILTERS = Yes
    JOIN_KEYS = fylkeid fylkeid
    ADDED_FIELDS = navn
    POSTGIS_DISABLE_COLLECTION_SPLITTING = yes
    MATCH_RULE_DISPLAY = Must Match Exactly One (1:1)
    POSTGIS_USE_TRUE_POSTGIS_TYPES = yes
    POSTGIS_HOST = $(PG_HOST)
    DATASET = $(PG_DB)
    TABLE = admingrense.fylkeflate
    JOINED -> StringReplacer_2
AttributeCreator_13
    ATTR_LIST = sosifile,"FME_CONDITIONAL:DEFAULT_VALUE'$(HOVEDTEMA)_$(OUTPUT_EPSG_CODE)_$(UNDERTEMA)_$(SAMLING)_SOSI'BOOL_OP;OR;COMPOSITE_TEST;<Unused>;TEST $(FANOUT) LIKE Kommuner'$(HOVEDTEMA)_@PadLeft(@Value(kommuneid),4,0)_@Value(navn)_$(OUTPUT_EPSG_CODE)_$(UNDERTEMA)_$(SAMLING)_SOSI'BOOL_OP;OR;COMPOSITE_TEST;<Unused>;TEST $(FANOUT) LIKE Fylker'$(HOVEDTEMA)_@PadLeft(@Value(fylkeid),2,0)_@Value(navn)_$(OUTPUT_EPSG_CODE)_$(UNDERTEMA)_$(SAMLING)_SOSI'BOOL_OP;OR;COMPOSITE_TEST;<Unused>;TEST $(FANOUT) LIKE Norge'$(HOVEDTEMA)_0000_Norge_$(OUTPUT_EPSG_CODE)_$(UNDERTEMA)_$(SAMLING)_SOSI'FME_NUM_CONDITIONS4___"
    -> Output (output)
Output (output)

Bookmark: Substituerer ÆØÅ og mellomrom
StringReplacer_2
    NO_MATCH = _FME_NO_OP_
    SRC_ATTRS = navn
    REGEXP = no
    FIND_TEXT = " "
    REPLACE_TEXT = _
    CASE = no
    -> StringReplacer_3
StringReplacer_3
    NO_MATCH = _FME_NO_OP_
    SRC_ATTRS = navn
    REGEXP = no
    FIND_TEXT = Æ
    REPLACE_TEXT = E
    CASE = yes
    -> StringReplacer_4
StringReplacer_4
    NO_MATCH = _FME_NO_OP_
    SRC_ATTRS = navn
    REGEXP = no
    FIND_TEXT = Ø
    REPLACE_TEXT = O
    CASE = yes
    -> StringReplacer_5
StringReplacer_5
    NO_MATCH = _FME_NO_OP_
    SRC_ATTRS = navn
    REGEXP = no
    FIND_TEXT = Å
    REPLACE_TEXT = A
    CASE = yes
    -> StringReplacer_6
StringReplacer_6
    NO_MATCH = _FME_NO_OP_
    SRC_ATTRS = navn
    REGEXP = no
    FIND_TEXT = æ
    REPLACE_TEXT = e
    CASE = yes
    -> StringReplacer_7
StringReplacer_7
    NO_MATCH = _FME_NO_OP_
    SRC_ATTRS = navn
    REGEXP = no
    FIND_TEXT = ø
    REPLACE_TEXT = o
    CASE = yes
    -> StringReplacer_8
StringReplacer_8
    NO_MATCH = _FME_NO_OP_
    SRC_ATTRS = navn
    REGEXP = no
    FIND_TEXT = å
    REPLACE_TEXT = a
    CASE = yes
    -> AttributeCreator_13

FME custom transformer CreateClipper

Parameters:
- CLIPPERCOORDS = 253577 6650999 253577 6651246 253763 6651246 253763 6650999 253577 6650999   # Clipper Coordinate List
- CLIPPERCOORDSYS = EPSG:25833   # Clipper Coordinate System
- DESTCOORDSYS = "ESRIWKT|ETRS_1989_UTM_Zone_35N|PROJCS["ETRS_1989_UTM_Zone_35N",GEOGCS["GCS_ETRS_1989",DATUM["D_ETRS_1989",SPHEROID["GRS_1980",6378137.0,298.257222101]],PRIMEM["Greenwich",0.0],UNIT["Degree",0.0174532925199433]],PROJECTION["Transverse_Mercator"],PARAMETER["False_Easting",500000.0],PARAMETER["False_Northing",0.0],PARAMETER["Central_Meridian",27.0],PARAMETER["Scale_Factor",0.9996],PARAMETER["Latitude_Of_Origin",0.0],UNIT["Meter",1.0]]"   # Destination Coordinate System

Note: Creating geometry from / the Clipper coords
Creator
    GEOMTYPE = 2D Coordinate List
    COORDS = $(CLIPPERCOORDS)
    COORDSYS = $(CLIPPERCOORDSYS)
    NUM = 1
    CREATED -> BoundingBoxAccumulator
Note: Calculating the bounding / box (envelope) from the geometry
BoundingBoxAccumulator
    TOPFER_INDEX = No
    BOUNDING_BOX -> SpatialFilter [input 1]
    ORIGINAL -> SpatialFilter [input 2]
Note: If the geometry is equal to its / own bounding box - it is a rectangle!
SpatialFilter
    PREDATTR = _predicate
    PREDICATES = EQUALS
    MERGE_ATTRS = No
    PASS_CRITERIA = Pass Against One Base
    USE_BOUNDING_BOX = No
    BASE_TYPE = Single Base
    CURVE_BOUNDARY_RULE_PARAM = Default Rule
    PASSED -> Reprojector
    FAILED -> Reprojector_2
Note: If rectangle, reproject the / geometry to the destination / coordinate system
Reprojector
    STROKE_ARCS = Yes
    RASTER_CELL_SIZE = Preserve Cells
    DEST = $(DESTCOORDSYS)
    SOURCE = Read from feature
    INTERPOLATION_TYPE_NAME = Nearest Neighbor
    REPROJECTED -> BoundingBoxAccumulator_2
Note: Then calculate the bounding / box from the projected geoemtry
BoundingBoxAccumulator_2
    TOPFER_INDEX = No
    BOUNDING_BOX -> Reprojector_3
Note: Reproject the geometry back to / the DB coordsys (LL/EUREF89)
Reprojector_3
    STROKE_ARCS = Yes
    RASTER_CELL_SIZE = Preserve Cells
    DEST = EPSG:4258
    SOURCE = Read from feature
    INTERPOLATION_TYPE_NAME = Nearest Neighbor
    REPROJECTED -> GeometryFilter
Note: Reproject clipper to / the DB coordsys (LL/EUREF89)
Reprojector_2
    STROKE_ARCS = Yes
    RASTER_CELL_SIZE = Preserve Cells
    DEST = EPSG:4258
    SOURCE = Read from feature
    INTERPOLATION_TYPE_NAME = Nearest Neighbor
    REPROJECTED -> GeometryFilter
Note: Getting rid of dummies
GeometryFilter
    GEOM_PORT_NAMES = Area
    BREAK_AGG = No
    AREA -> Output (output)
Output (output)
