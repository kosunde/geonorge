FME workspace Planomrade_sosi2postgis.fmw

Parameters:
- CONFIG_FILE:   # Python Script
      #-------------------------------------------------------------------------------
      # Name:        GetConfigFile
      # Purpose:
      #
      # Author:      xsunknu
      #
      # Created:     21.08.2015
      # Copyright:   (c) xsunknu 2015
      # Licence:     <your licence>
      #-------------------------------------------------------------------------------
      
      import os, fme
      
      fmwdir = fme.macroValues['FME_MF_DIR']
      fmwfile = fme.macroValues['FME_MF_NAME']
      
      fmwfile = os.path.join(fmwdir, fmwfile)
      configfile = os.path.splitext(fmwfile)[0] + '_config.xml'
      
      return configfile
- SOSI_IN:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('sosiin').text
      
      return value
- PG_DB:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgdb').text
      
      return value
- DESTCOORDSYS:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('sr').text
      
      return value
- LOG_FILE:   # Python Script
      #-------------------------------------------------------------------------------
      # Name:        GetConfigFile
      # Purpose:
      #
      # Author:      xsunknu
      #
      # Created:     21.08.2015
      # Copyright:   (c) xsunknu 2015
      # Licence:     <your licence>
      #-------------------------------------------------------------------------------
      
      import os, uuid, fme
      
      fmwdir = fme.macroValues['FME_MF_DIR']
      fmwfile = fme.macroValues['FME_MF_NAME']
      
      logdir = os.path.join(fmwdir, 'log')
      if not os.path.isdir(logdir):
          os.mkdir(logdir)
      
      logfile = os.path.splitext(fmwfile)[0] + '_' + str(uuid.uuid1()).replace('-','') + '.log'
      logfile = os.path.join(logdir, logfile)
      
      return logfile

Readers:
- SOSI_1: SOSI from $(SOSI_IN)

Writers:
- POSTGIS_1: POSTGIS to $(PG_DB)
- POSTGRES_1: POSTGRES to $(PG_DB)

Note: Konverterer til lowercase / attributtnavn
BulkAttributeRenamer
    ATTRCHOICE = All Attributes
    PATTERN_ACTION_DISP = Change Case
    CASE_CHANGE_TYPE = lowercase
    -> AttributeRenamer
Note: Ekspanderer forkortede / attributtnavn
AttributeRenamer
    ATTR_LIST = ikraft,ikrafttredelsesdato,,planstat,planstatus,,lovrefbeskrivelse,lovreferansebeskrivelse,,planbest,planbestemmelse,,sosi_id,objid,
    -> Reprojector
Note: Projiserer til DESTCOORDSYS
Reprojector
    SOURCE = Read from feature
    INTERPOLATION_TYPE_NAME = Nearest Neighbor
    RASTER_CELL_SIZE = Preserve Cells
    DEST = $(DESTCOORDSYS)
    REPROJECTED -> FeatureTypeFilter
FeatureTypeFilter
    ATTRIBUTES = KpOmrade,KpGrense,KpGrense_1,KpArealGrense,KpArealGrense_1,RpOmrade,RpFareGrense,RpFormalGrense,RpFormalGrense_1,RpAngittHensynGrense,RpGrense_1,RpGrense,<BLANK>,<UNFILTERED>
    KpOmrade -> AttributeCreator_2
    KpGrense_1 -> AttributeCreator
    KpArealGrense -> AttributeCreator
    KpArealGrense_1 -> AttributeCreator
    KpGrense -> AttributeCreator
    RpOmrade -> AttributeCreator_3
    RpFareGrense -> AttributeCreator_4
    RpFormalGrense -> AttributeCreator_4
    RpFormalGrense_1 -> AttributeCreator_4
    RpAngittHensynGrense -> AttributeCreator_4
    RpGrense_1 -> AttributeCreator_4
    RpGrense -> AttributeCreator_4
Note: Splitter attributter, setter standardattributter og genererer nøkler
AttributeCreator_2
    ATTR_LIST = objtype,KpOmråde,landkode,NO,fylkesnr,@Evaluate(@int(@Value(komm)/100)),objid,@Evaluate(@Count(omradeteller, 1)),kpomrade_fk,@Value(objid)
    -> planomriss.kpomrade (writer POSTGIS_1)
    -> planomriss.sosi_objekt_planomrade_kp (writer POSTGRES_1)
AttributeCreator
    ATTR_LIST = objtype,KpGrense,objid,@Count(grenseteller, 1),kpgrense_fk,@Value(objid)
    -> planomriss.kpgrense (writer POSTGIS_1)
    -> planomriss.sosi_objekt_planlinjer_kp (writer POSTGRES_1)
AttributeCreator_3
    ATTR_LIST = objtype,RpOmråde,landkode,NO,fylkesnr,@Evaluate(@int(@Value(komm)/100)),objid,@Evaluate(@Count(omradeteller, 1)),rpomrade_fk,@Value(objid)
    -> planomriss.rpomrade (writer POSTGIS_1)
    -> planomriss.sosi_objekt_planomrade_rp (writer POSTGRES_1)
AttributeCreator_4
    ATTR_LIST = objtype,KpGrense,objid,@Count(grenseteller, 1),rpgrense_fk,@Value(objid)
    -> planomriss.sosi_objekt_planlinjer_rp (writer POSTGRES_1)
    -> planomriss.rpgrense (writer POSTGIS_1)
KOPIDATA_SOSI (reader SOSI_1)
    attributes: KOPIDATO SOSI_datetime, SOSI_parent_guid SOSI_char(36), OMRADEID SOSI_number(8,0), ORIGINALDATAVERT SOSI_char(100)
    -> KOPIDATA_SOSI
KOPIDATA_SOSI: Logger
    MAXFEATS = 20
    MESSAGE = Feature is:
    MAXCOORDS = 20
SOSI_RelationshipClasses (reader SOSI_1)
    attributes: FeatureClass SOSI_char(100), GeometryType SOSI_char(32), Table SOSI_char(100)
    -> SOSI_RelationshipClasses
SOSI_RelationshipClasses: Logger
    MAXFEATS = 20
    MESSAGE = Feature is:
    MAXCOORDS = 20

Bookmark: Kommuneplan
KpOmrade (reader SOSI_1)
    attributes: SOSI_id SOSI_int32, LANDKODE SOSI_char(2), LOVREFERANSE SOSI_int16, LINK SOSI_char(255), KOPIDATO SOSI_datetime, FORSTEDIGITALISERINGSDATO SOSI_datetime, PLANTYPE SOSI_int16, PROSESS_HISTORIE SOSI_char(255), IKRAFT SOSI_date, OMRADEID SOSI_number(8,0), KOMM SOSI_char(4), PLANID SOSI_char(16), ORIGINALDATAVERT SOSI_char(100), PLANBEST SOSI_int16, PLANNAVN SOSI_char(120), LOVREFBESKRIVELSE SOSI_char(120), KUNNGJORINGSDATO SOSI_date, PLANSTAT SOSI_int16, INFORMASJON SOSI_char(255), OBJTYPE SOSI_char(32), FYLKESNR SOSI_int16, OPPDATERINGSDATO SOSI_datetime, VEDTAKENDELIGPLANDATO SOSI_date
    -> BulkAttributeRenamer
KpGrense (reader SOSI_1)
    attributes: SOSI_id SOSI_int32, NOYAKTIGHET SOSI_number(6,0), OMRADEID SOSI_number(8,0), KOPIDATO SOSI_datetime, OPPDATERINGSDATO SOSI_datetime, OBJTYPE SOSI_char(32), SOSI_guid SOSI_char(36), SYNBARHET SOSI_int16, FORSTEDIGITALISERINGSDATO SOSI_datetime, MALEMETODE SOSI_int16, ORIGINALDATAVERT SOSI_char(100)
    -> BulkAttributeRenamer
KpGrense_1 (reader SOSI_1)
    attributes: SOSI_id SOSI_int32, NOYAKTIGHET SOSI_number(6,0), OMRADEID SOSI_number(8,0), KOPIDATO SOSI_datetime, OPPDATERINGSDATO SOSI_datetime, OBJTYPE SOSI_char(32), SYNBARHET SOSI_int16, FORSTEDIGITALISERINGSDATO SOSI_datetime, MALEMETODE SOSI_int16, ORIGINALDATAVERT SOSI_char(100)
    -> BulkAttributeRenamer
KpArealGrense (reader SOSI_1)
    attributes: SOSI_id SOSI_int32, NOYAKTIGHET SOSI_number(6,0), OMRADEID SOSI_number(8,0), KOPIDATO SOSI_datetime, OPPDATERINGSDATO SOSI_datetime, OBJTYPE SOSI_char(32), SYNBARHET SOSI_int16, FORSTEDIGITALISERINGSDATO SOSI_datetime, MALEMETODE SOSI_int16, ORIGINALDATAVERT SOSI_char(100)
    -> BulkAttributeRenamer
KpArealGrense_1 (reader SOSI_1)
    attributes: SOSI_id SOSI_int32, NOYAKTIGHET SOSI_number(6,0), OMRADEID SOSI_number(8,0), KOPIDATO SOSI_datetime, OPPDATERINGSDATO SOSI_datetime, OBJTYPE SOSI_char(32), SYNBARHET SOSI_int16, MALEMETODE SOSI_int16, ORIGINALDATAVERT SOSI_char(100)
    -> BulkAttributeRenamer

Bookmark: Reguleringsplan
RpOmrade (reader SOSI_1)
    attributes: SOSI_id SOSI_int32, LANDKODE SOSI_char(2), LOVREFERANSE SOSI_int16, LINK SOSI_char(255), FORSLAGSSTILLERTYPE SOSI_int16, KOPIDATO SOSI_datetime, FORSTEDIGITALISERINGSDATO SOSI_datetime, PLANTYPE SOSI_int16, PROSESS_HISTORIE SOSI_char(255), IKRAFT SOSI_date, OPPRINNELIGADMINISTRATIVENHET SOSI_char(4), OMRADEID SOSI_number(8,0), KOMM SOSI_char(4), PLANID SOSI_char(16), ORIGINALDATAVERT SOSI_char(100), PLANBEST SOSI_int16, PLANNAVN SOSI_char(120), LOVREFBESKRIVELSE SOSI_char(120), GJENNOMFORINGSFRIST SOSI_date, SOSI_guid SOSI_char(36), KUNNGJORINGSDATO SOSI_date, PLANSTAT SOSI_int16, INFORMASJON SOSI_char(255), OPPRINNELIGPLANID SOSI_char(16), OBJTYPE SOSI_char(32), VERTNIV SOSI_int16, FYLKESNR SOSI_int16, OPPDATERINGSDATO SOSI_datetime, VEDTAKENDELIGPLANDATO SOSI_date
    -> BulkAttributeRenamer
RpGrense (reader SOSI_1)
    attributes: SOSI_id SOSI_int32, KOPIDATO SOSI_datetime, H_MALEMETODE SOSI_int16, FORSTEDIGITALISERINGSDATO SOSI_datetime, NOYAKTIGHET SOSI_number(6,0), SYNBARHET SOSI_int16, OMRADEID SOSI_number(8,0), MALEMETODE SOSI_int16, ORIGINALDATAVERT SOSI_char(100), SOSI_guid SOSI_char(36), OBJTYPE SOSI_char(32), OPPDATERINGSDATO SOSI_datetime
    -> BulkAttributeRenamer
RpGrense_1 (reader SOSI_1)
    attributes: SOSI_id SOSI_int32, NOYAKTIGHET SOSI_number(6,0), OMRADEID SOSI_number(8,0), KOPIDATO SOSI_datetime, OPPDATERINGSDATO SOSI_datetime, OBJTYPE SOSI_char(32), SOSI_guid SOSI_char(36), SYNBARHET SOSI_int16, FORSTEDIGITALISERINGSDATO SOSI_datetime, MALEMETODE SOSI_int16, ORIGINALDATAVERT SOSI_char(100)
    -> BulkAttributeRenamer
RpFormalGrense (reader SOSI_1)
    attributes: SOSI_id SOSI_int32, OMRADEID SOSI_number(8,0), KOPIDATO SOSI_datetime, OPPDATERINGSDATO SOSI_datetime, OBJTYPE SOSI_char(32), FORSTEDIGITALISERINGSDATO SOSI_datetime, MALEMETODE SOSI_int16, ORIGINALDATAVERT SOSI_char(100)
    -> BulkAttributeRenamer
RpFormalGrense_1 (reader SOSI_1)
    attributes: SOSI_id SOSI_int32, OMRADEID SOSI_number(8,0), KOPIDATO SOSI_datetime, OPPDATERINGSDATO SOSI_datetime, OBJTYPE SOSI_char(32), MALEMETODE SOSI_int16, ORIGINALDATAVERT SOSI_char(100)
    -> BulkAttributeRenamer
RpAngittHensynGrense (reader SOSI_1)
    attributes: SOSI_id SOSI_int32, OMRADEID SOSI_number(8,0), KOPIDATO SOSI_datetime, OPPDATERINGSDATO SOSI_datetime, OBJTYPE SOSI_char(32), FORSTEDIGITALISERINGSDATO SOSI_datetime, ORIGINALDATAVERT SOSI_char(100)
    -> BulkAttributeRenamer
RpFareGrense (reader SOSI_1)
    attributes: SOSI_id SOSI_int32, OMRADEID SOSI_number(8,0), KOPIDATO SOSI_datetime, OPPDATERINGSDATO SOSI_datetime, OBJTYPE SOSI_char(32), FORSTEDIGITALISERINGSDATO SOSI_datetime, ORIGINALDATAVERT SOSI_char(100)
    -> BulkAttributeRenamer

Bookmark: Planområde PostGIS
planomriss.kpomrade (writer POSTGIS_1)
    attributes: objid int4,PRIKEY, objtype varchar(32), landkode varchar(2), fylkesnr int2, komm int2, planid varchar(16), ikrafttredelsesdato date, kunngjoringsdato date, lovreferanse int2, lovreferansebeskrivelse varchar(255), opprinneligadministrativenhet int2, opprinneligplanid varchar(16), planbestemmelse int2, plannavn varchar(255), planstatus int2, plantype int2, vedtakendeligplandato date
planomriss.kpgrense (writer POSTGIS_1)
    attributes: objid int4,PRIKEY, objtype varchar(32)
planomriss.rpomrade (writer POSTGIS_1)
    attributes: objid int4,PRIKEY, objtype varchar(32), landkode varchar(2), fylkesnr int2, komm int2, planid varchar(16), forslagsstillertype int2, gjennomforingsfrist date, ikrafttredelsesdato date, kunngjoringsdato date, lovreferanse int2, lovreferansebeskrivelse varchar(255), opprinneligadministrativenhet int2, opprinneligplanid varchar(16), planbestemmelse int2, plannavn varchar(255), planstatus int2, plantype int2, vedtakendeligplandato date, vertikalniva int4
planomriss.rpgrense (writer POSTGIS_1)
    attributes: objid int4,PRIKEY, objtype varchar(32)

Bookmark: Planområde PostgreSQL
planomriss.sosi_objekt_planomrade_kp (writer POSTGRES_1)
    attributes: objid int4,PRIKEY, forstedigitaliseringsdato date, informasjon varchar(255), link varchar(255), oppdateringsdato date, prosess_historie varchar(255), kpomrade_fk int4,BTREE
planomriss.sosi_objekt_planlinjer_kp (writer POSTGRES_1)
    attributes: objid int4,PRIKEY, forstedigitaliseringsdato date, noyaktighet int2, malemetode int2, synbarhet int2, oppdateringsdato date, kpgrense_fk int4,BTREE
planomriss.sosi_objekt_planomrade_rp (writer POSTGRES_1)
    attributes: objid int4,PRIKEY, forstedigitaliseringsdato date, informasjon varchar(255), link varchar(255), oppdateringsdato date, prosess_historie varchar(255), rpomrade_fk int4,BTREE
planomriss.sosi_objekt_planlinjer_rp (writer POSTGRES_1)
    attributes: objid int4,PRIKEY, forstedigitaliseringsdato date, noyaktighet int2, malemetode int2, synbarhet int2, oppdateringsdato date, rpgrense_fk int4,BTREE
