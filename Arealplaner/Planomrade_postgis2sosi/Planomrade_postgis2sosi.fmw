FME workspace Planomrade_postgis2sosi.fmw
# Copyright: (c) xgrimor 2015
# Licence: <your licence>

Parameters:
- KNR =   # Kommune(r)
- FNR =   # Fylke(r)
- CLIPPERCOORDS = 8 59 9 59 9 60 8 60 8 59   # Clipper coordinates
- CLIPPER_EPSG_CODE = 4258   # Clipper coordinate system
- CLIPPER_FILE =   # "" Clipper file (any format)
- OUTPUT_EPSG_CODE = 25832   # Destination coordinate system
- FANOUT = Ingen   # Fanout områder
- CONFIG_FILE:   # Python Script
      #-------------------------------------------------------------------------------
      # Name:        GetConfigFile
      # Purpose:
      #
      # Author:      xsunknu
      #
      # Created:     21.08.2015
      # Copyright:   (c) xsunknu 2015
      # Licence:     <your licence>
      #-------------------------------------------------------------------------------
      
      import os, fme
      
      fmwdir = fme.macroValues['FME_MF_DIR']
      fmwfile = fme.macroValues['FME_MF_NAME']
      
      fmwfile = os.path.join(fmwdir, fmwfile)
      configfile = os.path.splitext(fmwfile)[0] + '_config.xml'
      
      return configfile
- PG_DB:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgdb').text
      
      return value
- PG_HOST:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pghost').text
      
      return value
- PG_PORT:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgport').text
      
      return value
- PG_PWD:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgpwd').text
      
      return value
- FIXEDCLIPPERCOORDS:   # Python Script
      #-------------------------------------------------------------------------------
      # Name:        FixClipperCoords
      # Purpose:
      #
      # Author:      xsunknu
      #
      # Created:     21.08.2015
      # Copyright:   (c) xsunknu 2015
      # Licence:     <your licence>
      #-------------------------------------------------------------------------------
      
      import fme
      clippercoords = fme.macroValues['CLIPPERCOORDS']
      
      if clippercoords == '':
          clippercoords = '1 1'
      
      return clippercoords
- PG_USER:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pguser').text
      
      return value
- CLIPPERCOORDSYS:   # Python Script
      #-------------------------------------------------------------------------------
      # Name:        SetCoordinateSystem
      # Purpose:
      #
      # Author:      xsunknu
      #
      # Created:     21.08.2015
      # Copyright:   (c) xsunknu 2015
      # Licence:     <your licence>
      #-------------------------------------------------------------------------------
      
      import os, fme
      
      EPSGvalue = fme.macroValues['CLIPPER_EPSG_CODE']
      EPSGcode  = 'EPSG:' + EPSGvalue
      
      return EPSGcode
- DESTCOORDSYS:   # Python Script
      #-------------------------------------------------------------------------------
      # Name:        SetCoordinateSystem
      # Purpose:
      #
      # Author:      xsunknu
      #
      # Created:     21.08.2015
      # Copyright:   (c) xsunknu 2015
      # Licence:     <your licence>
      #-------------------------------------------------------------------------------
      
      import os, fme
      
      EPSGvalue = fme.macroValues['OUTPUT_EPSG_CODE']
      EPSGcode  = 'EPSG:' + EPSGvalue
      
      return EPSGcode
- FANOUT_FOLDER:   # Python Script
      #-------------------------------------------------------------------------------
      # Name:        GetConfigFile
      # Purpose:
      #
      # Author:      xsunknu
      #
      # Created:     21.08.2015
      # Copyright:   (c) xsunknu 2015
      # Licence:     <your licence>
      #-------------------------------------------------------------------------------
      
      import os, fme
      from xml.etree import ElementTree as ET
      
      #Read XML config file
      configtree = ET.parse(fme.macroValues['CONFIG_FILE'])
      configdoc = configtree.getroot()
      value = configdoc.find('destdir').text
      
      return value
- LOG_FILE:   # Python Script
      #-------------------------------------------------------------------------------
      # Name:        GetConfigFile
      # Purpose:
      #
      # Author:      xsunknu
      #
      # Created:     21.08.2015
      # Copyright:   (c) xsunknu 2015
      # Licence:     <your licence>
      #-------------------------------------------------------------------------------
      
      import os, uuid, fme
      
      fmwdir = fme.macroValues['FME_MF_DIR']
      fmwfile = fme.macroValues['FME_MF_NAME']
      
      logdir = os.path.join(fmwdir, 'log')
      if not os.path.isdir(logdir):
          os.mkdir(logdir)
      
      logfile = os.path.splitext(fmwfile)[0] + '_' + str(uuid.uuid1()).replace('-','') + '.log'
      logfile = os.path.join(logdir, logfile)
      
      return logfile

Readers:
- POSTGIS_1: POSTGIS from $(PG_DB)

Writers:
- SOSI_1: SOSI to C:\Users\xsunknu\Documents\work\Output\planomriss.sos

Generalizer
    PRESERVE = No
    TOLERANCE = 0.000009
    ALG_TEXT = Douglas (Generalize)
    -> Clipper [input 1]
CreateClipper
    CLIPPERCOORDS = $(FIXEDCLIPPERCOORDS)
    DESTCOORDSYS = $(DESTCOORDSYS)
    CLIPPERCOORDSYS = $(CLIPPERCOORDSYS)
    -> Clipper [input 1]
    -> FeatureReader_2
FeatureReader_2
    FEATURETYPES_RADIO = FEATURETYPES
    POSTGIS_NAMED_CONNECTION = geonortst@Nnridb504:5432/geonor01tst
    COMBINE_GEOM = Use Result
    POSTGIS_SCHEMALIST = planomriss
    OUTPUT_FEATURES_DISPLAY = Based on Connections
    POSTGIS_QUERY_FEATURE_TYPES_FOR_MERGE_FILTERS = Yes
    FORMAT = POSTGIS
    INTERACT = Intersects
    POSTGIS_CLIP_TO_ENVELOPE = NO
    POSTGIS_USE_TRUE_POSTGIS_TYPES = yes
    DATASET = geonortst@Nnridb504:5432/geonor01tst
    POSTGIS_DISABLE_COLLECTION_SPLITTING = yes
    ATTRIBUTES = planomriss.kpgrense,"objid,objtype",planomriss.kpomrade,"objid,objtype,landkode,fylkesnr,komm,planid,ikrafttredelsesdato,kunngjoringsdato,lovreferanse,lovreferansebeskrivelse,opprinneligadministrativenhet,opprinneligplanid,planbestemmelse,plannavn,planstatus,plantype,vedtakendeligplandato",planomriss.rpgrense,"objid,objtype",planomriss.rpomrade,"objid,objtype,landkode,fylkesnr,komm,planid,forslagsstillertype,gjennomforingsfrist,ikrafttredelsesdato,kunngjoringsdato,lovreferanse,lovreferansebeskrivelse,opprinneligadministrativenhet,opprinneligplanid,planbestemmelse,plannavn,planstatus,plantype,vedtakendeligplandato,vertikalniva"
    POSTGIS_USE_SEARCH_ENVELOPE = NO
    FEATURETYPES = planomriss.kpgrense planomriss.kpomrade planomriss.rpgrense planomriss.rpomrade
    ATTR_ACCUM_MODE = Only Use Result
    planomriss.kpgrense -> Clipper [input 2]
    planomriss.kpomrade -> Clipper [input 2]
    planomriss.rpgrense -> Clipper [input 2]
    planomriss.rpomrade -> Clipper [input 2]
Clipper
    PRESERVE_CLIPPEE_EXTENTS = No
    CLIPPED_ATTR = _clipped
    CLIP_TYPE = Multiple Clippers
    BOUNDARY_CASES = Treat as Inside
    ATTR_CONFLICT_RES = Use Clippee
    CREATE_AGGREGATES = No
    ATTR_ACCUM_MODE = Merge Clipper
    INSIDE -> Reprojector
Note: Reprojiserer til destcoordsys
Reprojector
    RASTER_CELL_SIZE = Preserve Cells
    INTERPOLATION_TYPE_NAME = Nearest Neighbor
    DEST = $(DESTCOORDSYS)
    SOURCE = Read from feature
    REPROJECTED -> AttributeCreator_5
AttributeCreator_5
    ATTR_LIST = sosifile,"FME_CONDITIONAL:DEFAULT_VALUE'planomriss_$(OUTPUT_EPSG_CODE)'BOOL_OP;OR;COMPOSITE_TEST;<Unused>;TEST $(FANOUT) LIKE Kommuner'planomriss_@PadLeft(@Value(kommuneid),4,0)_$(OUTPUT_EPSG_CODE)'BOOL_OP;OR;COMPOSITE_TEST;<Unused>;TEST $(FANOUT) LIKE Fylker'planomriss_@PadLeft(@Value(fylkeid),2,0)_$(OUTPUT_EPSG_CODE)'FME_NUM_CONDITIONS3___",komm,@PadLeft(@Value(komm),4,0),opprinneligadministrativenhet,"FME_CONDITIONAL:DEFAULT_VALUE'@PadLeft(@Value(opprinneligadministrativenhet),4,0)'BOOL_OP;OR;COMPOSITE_TEST;<Unused>;TEST opprinneligadministrativenhet ATTRIBUTE_VALUE_NULL _FME_BLANK_STRING_'FME_NULL_VALUE'FME_NUM_CONDITIONS2___"
    -> FeatureTypeFilter

Bookmark: Fylke and/or kommune clippers
admingrense.fylkeflate (reader POSTGIS_1)
    attributes: fylkeid int4
    -> Tester
Tester
    TEST_CLAUSE = TEST @Value(fylkeid) IN $(FNR)
    BOOL_OP = OR
    TEST_MODE = Automatic
    TEST_DESCRIPTION = ""
    PASSED -> Reprojector_2
admingrense.kommuneflate (reader POSTGIS_1)
    attributes: kommuneid int4
    -> Tester_2
Tester_2
    TEST_CLAUSE = TEST @Value(kommuneid) IN $(KNR)
    BOOL_OP = OR
    TEST_MODE = Automatic
    TEST_DESCRIPTION = ""
    PASSED -> Reprojector_2
Reprojector_2
    RASTER_CELL_SIZE = Preserve Cells
    INTERPOLATION_TYPE_NAME = Nearest Neighbor
    DEST = EPSG:4258
    SOURCE = Read from feature
    REPROJECTED -> FeatureReader_2
    REPROJECTED -> Generalizer

Bookmark: Clipper file (any format)
Creator
    NUM = 1
    GEOMTYPE = Geometry Object
    CREATED -> FeatureReader
FeatureReader
    OUTPUT_FEATURES_DISPLAY = Based on Connections
    GENERIC_REAL_FORMAT = GUESS_FROM_EXTENSION
    DATASET = $(CLIPPER_FILE)
    ATTR_ACCUM_MODE = Only Use Result
    ATTRIBUTES = NewFeatureType,
    COMBINE_GEOM = Use Result
    INTERACT = <No Spatial Filter>
    FEATURETYPES_RADIO = FEATURETYPES
    FORMAT = GENERIC
    <OTHER> -> Reprojector_3
Reprojector_3
    RASTER_CELL_SIZE = Preserve Cells
    INTERPOLATION_TYPE_NAME = Nearest Neighbor
    DEST = EPSG:4258
    SOURCE = Read from feature
    REPROJECTED -> FeatureReader_2
    REPROJECTED -> Generalizer

Bookmark: Kobler inn relaterte tabeller
FeatureTypeFilter
    ATTRIBUTES = planomriss.kpomrade,planomriss.kpgrense,planomriss.rpomrade,planomriss.rpgrense,<BLANK>,<UNFILTERED>
    planomriss.kpomrade -> FeatureMerger [input 1]
    planomriss.kpgrense -> FeatureMerger_2 [input 1]
    planomriss.rpomrade -> FeatureMerger_3 [input 1]
    planomriss.rpgrense -> FeatureMerger_4 [input 1]
    planomriss.kpomrade -> Aggregator
    planomriss.kpgrense -> Aggregator_2
    planomriss.rpomrade -> Aggregator_3
    planomriss.rpgrense -> Aggregator_4
Aggregator
    MODE = Attributes Only
    CONCAT_ATTRS = objid
    SEP = ,
    ORDERED = No
    ACCUM_ATTRS_NAME = No
    AGGREGATE -> AttributeCreator
AttributeCreator
    ATTR_LIST = sql,select * from planomriss.sosi_objekt_planomrade_kp where objid in (@Value(objid));
    -> SQLExecutor
SQLExecutor
    POSTGRES_USER_NAME = $(PG_USER)
    DATASET = $(PG_DB)
    POSTGRES_HOST = $(PG_HOST)
    COMBINE_GEOM = Initiator Geometry Only
    SQL_STATEMENT = @Value(sql)
    FORMAT = POSTGRES
    POSTGRES_QUERY_FEATURE_TYPES_FOR_MERGE_FILTERS = Yes
    EXPOSED_ATTRIBUTE_LIST = forstedigitaliseringsdato,informasjon,kpomrade_fk,link,objid,oppdateringsdato,prosess_historie
    POSTGRES_PASSWORD = $(PG_PWD)
    POSTGRES_PORT = $(PG_PORT)
    COMBINE_ATTRS = Result Attributes Only
    RESULT -> FeatureMerger [input 2]
FeatureMerger
    JOIN_KEYS = @Value(objid) @Value(kpomrade_fk) AUTO
    PROCESS_DUPS = No
    ATTR_CONFLICT_RES = Use Requestor
    ATTR_ACCUM_MODE = Merge Supplier
    IGNORE_NULLS = No
    MERGE_TYPE = Attributes Only
    SUPPLIERS_FIRST = No
    MERGED -> KpOmrade (writer SOSI_1)
Aggregator_2
    MODE = Attributes Only
    CONCAT_ATTRS = objid
    SEP = ,
    ORDERED = No
    ACCUM_ATTRS_NAME = No
    AGGREGATE -> AttributeCreator_2
AttributeCreator_2
    ATTR_LIST = sql,select * from planomriss.sosi_objekt_planlinjer_kp where objid in (@Value(objid));
    -> SQLExecutor_2
SQLExecutor_2
    POSTGRES_USER_NAME = $(PG_USER)
    DATASET = $(PG_DB)
    POSTGRES_HOST = $(PG_HOST)
    COMBINE_GEOM = Initiator Geometry Only
    SQL_STATEMENT = @Value(sql)
    FORMAT = POSTGRES
    POSTGRES_QUERY_FEATURE_TYPES_FOR_MERGE_FILTERS = Yes
    EXPOSED_ATTRIBUTE_LIST = forstedigitaliseringsdato,kpgrense_fk,malemetode,noyaktighet,objid,oppdateringsdato,synbarhet
    POSTGRES_PASSWORD = $(PG_PWD)
    POSTGRES_PORT = $(PG_PORT)
    COMBINE_ATTRS = Result Attributes Only
    RESULT -> FeatureMerger_2 [input 2]
FeatureMerger_2
    JOIN_KEYS = @Value(objid) @Value(kpgrense_fk) AUTO
    PROCESS_DUPS = No
    ATTR_CONFLICT_RES = Use Requestor
    ATTR_ACCUM_MODE = Merge Supplier
    IGNORE_NULLS = No
    MERGE_TYPE = Attributes Only
    SUPPLIERS_FIRST = No
    MERGED -> KpGrense (writer SOSI_1)
Aggregator_3
    MODE = Attributes Only
    CONCAT_ATTRS = objid
    SEP = ,
    ORDERED = No
    ACCUM_ATTRS_NAME = No
    AGGREGATE -> AttributeCreator_3
AttributeCreator_3
    ATTR_LIST = sql,select * from planomriss.sosi_objekt_planomrade_rp where objid in (@Value(objid));
    -> SQLExecutor_3
SQLExecutor_3
    POSTGRES_USER_NAME = $(PG_USER)
    DATASET = $(PG_DB)
    POSTGRES_HOST = $(PG_HOST)
    COMBINE_GEOM = Initiator Geometry Only
    SQL_STATEMENT = @Value(sql)
    FORMAT = POSTGRES
    POSTGRES_QUERY_FEATURE_TYPES_FOR_MERGE_FILTERS = Yes
    EXPOSED_ATTRIBUTE_LIST = forstedigitaliseringsdato,informasjon,link,objid,oppdateringsdato,prosess_historie,rpomrade_fk
    POSTGRES_PASSWORD = $(PG_PWD)
    POSTGRES_PORT = $(PG_PORT)
    COMBINE_ATTRS = Result Attributes Only
    RESULT -> FeatureMerger_3 [input 2]
FeatureMerger_3
    JOIN_KEYS = @Value(objid) @Value(rpomrade_fk) AUTO
    PROCESS_DUPS = No
    ATTR_CONFLICT_RES = Use Requestor
    ATTR_ACCUM_MODE = Merge Supplier
    IGNORE_NULLS = No
    MERGE_TYPE = Attributes Only
    SUPPLIERS_FIRST = No
    MERGED -> RpOmrade (writer SOSI_1)
Aggregator_4
    MODE = Attributes Only
    CONCAT_ATTRS = objid
    SEP = ,
    ORDERED = No
    ACCUM_ATTRS_NAME = No
    AGGREGATE -> AttributeCreator_4
AttributeCreator_4
    ATTR_LIST = sql,select * from planomriss.sosi_objekt_planlinjer_rp where objid in (@Value(objid));
    -> SQLExecutor_4
SQLExecutor_4
    POSTGRES_USER_NAME = $(PG_USER)
    DATASET = $(PG_DB)
    POSTGRES_HOST = $(PG_HOST)
    COMBINE_GEOM = Initiator Geometry Only
    SQL_STATEMENT = @Value(sql)
    FORMAT = POSTGRES
    POSTGRES_QUERY_FEATURE_TYPES_FOR_MERGE_FILTERS = Yes
    EXPOSED_ATTRIBUTE_LIST = forstedigitaliseringsdato,malemetode,noyaktighet,objid,oppdateringsdato,rpgrense_fk,synbarhet
    POSTGRES_PASSWORD = $(PG_PWD)
    POSTGRES_PORT = $(PG_PORT)
    COMBINE_ATTRS = Result Attributes Only
    RESULT -> FeatureMerger_4 [input 2]
FeatureMerger_4
    JOIN_KEYS = @Value(objid) @Value(rpgrense_fk) AUTO
    PROCESS_DUPS = No
    ATTR_CONFLICT_RES = Use Requestor
    ATTR_ACCUM_MODE = Merge Supplier
    IGNORE_NULLS = No
    MERGE_TYPE = Attributes Only
    SUPPLIERS_FIRST = No
    MERGED -> RpGrense (writer SOSI_1)

Bookmark: SOSI output
KpOmrade (writer SOSI_1)
    attributes: objtype SOSI_varchar(32), landkode SOSI_varchar(2), fylkesnr SOSI_int16, komm SOSI_varchar(4), planid SOSI_char, ikrafttredelsesdato SOSI_date, kunngjoringsdato SOSI_date, lovreferanse SOSI_int16, lovreferansebeskrivelse SOSI_varchar(255), opprinneligadministrativenhet SOSI_varchar(4), opprinneligplanid SOSI_varchar(16), planbestemmelse SOSI_int16, plannavn SOSI_varchar(255), planstatus SOSI_int16, plantype SOSI_char, vedtakendeligplandato SOSI_date, forstedigitaliseringsdato SOSI_datetime, informasjon SOSI_varchar(255), link SOSI_varchar(255), oppdateringsdato SOSI_datetime, prosess_historie SOSI_varchar(255)
KpGrense (writer SOSI_1)
    attributes: objtype SOSI_varchar(32), forstedigitaliseringsdato SOSI_datetime, malemetode SOSI_int16, noyaktighet SOSI_int16, synbarhet SOSI_int16, oppdateringsdato SOSI_datetime
RpOmrade (writer SOSI_1)
    attributes: objtype SOSI_varchar(32), landkode SOSI_varchar(2), fylkesnr SOSI_int16, komm SOSI_varchar(4), planid SOSI_varchar(16), forslagsstillertype SOSI_char, gjennomforingsfrist SOSI_date, ikrafttredelsesdato SOSI_date, kunngjoringsdato SOSI_date, lovreferanse SOSI_int16, lovreferansebeskrivelse SOSI_varchar(255), opprinneligadministrativenhet SOSI_varchar(4), opprinneligplanid SOSI_varchar(16), planbestemmelse SOSI_int16, plannavn SOSI_varchar(255), planstatus SOSI_int16, plantype SOSI_int16, vedtakendeligplandato SOSI_date, vertikalniva SOSI_int16, forstedigitaliseringsdato SOSI_datetime, informasjon SOSI_varchar(255), link SOSI_varchar(255), oppdateringsdato SOSI_datetime, prosess_historie SOSI_varchar(255)
RpGrense (writer SOSI_1)
    attributes: objtype SOSI_varchar(32), forstedigitaliseringsdato SOSI_datetime, malemetode SOSI_int16, noyaktighet SOSI_int16, synbarhet SOSI_int16, oppdateringsdato SOSI_datetime

FME custom transformer CreateClipper

Parameters:
- CLIPPERCOORDS = 253577 6650999 253577 6651246 253763 6651246 253763 6650999 253577 6650999   # Clipper Coordinate List
- CLIPPERCOORDSYS = EPSG:25833   # Clipper Coordinate System
- DESTCOORDSYS = "ESRIWKT|ETRS_1989_UTM_Zone_35N|PROJCS["ETRS_1989_UTM_Zone_35N",GEOGCS["GCS_ETRS_1989",DATUM["D_ETRS_1989",SPHEROID["GRS_1980",6378137.0,298.257222101]],PRIMEM["Greenwich",0.0],UNIT["Degree",0.0174532925199433]],PROJECTION["Transverse_Mercator"],PARAMETER["False_Easting",500000.0],PARAMETER["False_Northing",0.0],PARAMETER["Central_Meridian",27.0],PARAMETER["Scale_Factor",0.9996],PARAMETER["Latitude_Of_Origin",0.0],UNIT["Meter",1.0]]"   # Destination Coordinate System

Note: Creating geometry from / the Clipper coords
Creator
    NUM = 1
    COORDS = $(CLIPPERCOORDS)
    GEOMTYPE = 2D Coordinate List
    COORDSYS = $(CLIPPERCOORDSYS)
    CREATED -> BoundingBoxAccumulator
Note: Calculating the bounding / box (envelope) from the geometry
BoundingBoxAccumulator
    TOPFER_INDEX = No
    BOUNDING_BOX -> SpatialFilter [input 1]
    ORIGINAL -> SpatialFilter [input 2]
Note: If the geometry is equal to its / own bounding box - it is a rectangle!
SpatialFilter
    MERGE_ATTRS = No
    PASS_CRITERIA = Pass Against One Base
    PREDICATES = EQUALS
    CURVE_BOUNDARY_RULE_PARAM = Default Rule
    PREDATTR = _predicate
    BASE_TYPE = Single Base
    USE_BOUNDING_BOX = No
    PASSED -> Reprojector
    FAILED -> Reprojector_2
Note: If rectangle, reproject the / geometry to the destination / coordinate system
Reprojector
    RASTER_CELL_SIZE = Preserve Cells
    INTERPOLATION_TYPE_NAME = Nearest Neighbor
    DEST = $(DESTCOORDSYS)
    SOURCE = Read from feature
    STROKE_ARCS = Yes
    REPROJECTED -> BoundingBoxAccumulator_2
Note: Then calculate the bounding / box from the projected geoemtry
BoundingBoxAccumulator_2
    TOPFER_INDEX = No
    BOUNDING_BOX -> Reprojector_3
Note: Reproject the geometry back to / the DB coordsys (LL/EUREF89)
Reprojector_3
    RASTER_CELL_SIZE = Preserve Cells
    INTERPOLATION_TYPE_NAME = Nearest Neighbor
    DEST = EPSG:4258
    SOURCE = Read from feature
    STROKE_ARCS = Yes
    REPROJECTED -> GeometryFilter
Note: Reproject clipper to / the DB coordsys (LL/EUREF89)
Reprojector_2
    RASTER_CELL_SIZE = Preserve Cells
    INTERPOLATION_TYPE_NAME = Nearest Neighbor
    DEST = EPSG:4258
    SOURCE = Read from feature
    STROKE_ARCS = Yes
    REPROJECTED -> GeometryFilter
Note: Getting rid of dummies
GeometryFilter
    GEOM_PORT_NAMES = Area
    BREAK_AGG = No
    AREA -> Output (output)
Output (output)
