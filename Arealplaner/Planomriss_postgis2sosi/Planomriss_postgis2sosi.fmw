FME workspace Planomriss_postgis2sosi.fmw
# Copyright: (c) xgrimor 2015
# Licence: <your licence>
Shutdown Python:
      # -*- coding: utf-8 -*-
      #-------------------------------------------------------------------------------
      # Name:        zipfiles.py
      # Purpose:     Pakker filer i output folderen
      #
      # Author:      xsunknu
      #
      # Created:     18.09.2015
      # Copyright:   (c) xsunknu 2015
      # Licence:     <your licence>
      #-------------------------------------------------------------------------------

      import sys, os, zipfile, fme

      def zip(sosifile, zfile):
          from os.path import basename

          # Lager korresponderende zip-fil av SOSI-fil
          if os.path.isfile(zfile):
              os.remove(zfile)

          zf = zipfile.ZipFile(zfile, "w", zipfile.ZIP_DEFLATED)

          # Ønsker ikke full sti inn i ZIP-filen
          arcname = basename(sosifile)

          # ZIP-formatet støtter ikke non-ascii tegn
          # Erstatter AØÅæøå med ascii-tegn
          arcname = arcname.replace('\xc6', 'E')
          arcname = arcname.replace('\xd8', 'O')
          arcname = arcname.replace('\xc5', 'A')
          arcname = arcname.replace('\xe6', 'e')
          arcname = arcname.replace('\xf8', 'o')
          arcname = arcname.replace('\xe5', 'a')

          zf.write(sosifile, arcname)
          zf.close()
          os.remove(sosifile)

          return

      def main():

          # Kjøres ikke på FME Server, da FME Server selv sørger for pakkingen
          if not 'FME_SERVER_DEST_DIR' in fme.macroValues:
              if 'FANOUT_FOLDER' in fme.macroValues:
                  path = fme.macroValues['FANOUT_FOLDER']
                  for dirpath, dnames, fnames in os.walk(path):
                      for f in fnames:
                          if f.endswith(".sos"):
                              # Scanner gjennom alle SOSI-filer
                              sosifile = os.path.join(path, f)
                              zfile = os.path.splitext(sosifile)[0] + '.zip'
                              if os.path.isfile(zfile):

                                  # Korresponderende ZIP-fil finnes, sjekker timestamps
                                  sositstamp = os.stat(sosifile).st_mtime
                                  ziptstamp = os.stat(zfile).st_mtime

                                  if sositstamp > ziptstamp:
                                      # SOSI-fil er nyere enn ZIP-fila, ZIP-fila oppdateres
                                      # SOSI-fila slettes
                                      try:
                                          zip(sosifile, zfile)
                                      except:
                                          print 'Kunne ikke pakke: ' + sosifile
                                  else:
                                      # SOSI-fila er eldre enn ZIP-fila
                                      # SOSI-fila slettes
                                      try:
                                          os.remove(sosifile)
                                      except:
                                          print 'Kunne ikke slette: ' + sosifile
                              else:
                                  # ZIP-fila eksisterer ikke og lages
                                  # SOSI-fila slettes
                                  try:
                                      zip(sosifile, zfile)
                                  except:
                                      print 'Kunne ikke pakke: ' + sosifile


      if __name__ == '__main__':
          main()

Parameters:
- KNR =   # Kommune(r)
- FNR =   # Fylke(r)
- CLIPPERCOORDS =   # Clipper coordinates
- CLIPPER_EPSG_CODE =   # Clipper coordinate system
- CLIPPER_FILE =   # "" Clipper file (any format)
- OUTPUT_EPSG_CODE = 25833   # Destination coordinate system
- FANOUT =   # Fanout områder
- CONFIG_FILE:   # Python Script
      #-------------------------------------------------------------------------------
      # Name:        GetConfigFile
      # Purpose:
      #
      # Author:      xsunknu
      #
      # Created:     21.08.2015
      # Copyright:   (c) xsunknu 2015
      # Licence:     <your licence>
      #-------------------------------------------------------------------------------
      
      import os, fme
      
      fmwdir = fme.macroValues['FME_MF_DIR']
      fmwfile = fme.macroValues['FME_MF_NAME']
      
      fmwfile = os.path.join(fmwdir, fmwfile)
      configfile = os.path.splitext(fmwfile)[0] + '_config.xml'
      
      return configfile
- PG_DB:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgdb').text
      
      return value
- PG_HOST:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pghost').text
      
      return value
- PG_PORT:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgport').text
      
      return value
- PG_PWD:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgpwd').text
      
      return value
- FIXEDCLIPPERCOORDS:   # Python Script
      #-------------------------------------------------------------------------------
      # Name:        FixClipperCoords
      # Purpose:
      #
      # Author:      xsunknu
      #
      # Created:     21.08.2015
      # Copyright:   (c) xsunknu 2015
      # Licence:     <your licence>
      #-------------------------------------------------------------------------------
      
      import fme
      clippercoords = fme.macroValues['CLIPPERCOORDS']
      
      if clippercoords == '':
          clippercoords = '1 1'
      
      return clippercoords
- PG_USER:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pguser').text
      
      return value
- CLIPPERCOORDSYS:   # Python Script
      #-------------------------------------------------------------------------------
      # Name:        SetCoordinateSystem
      # Purpose:
      #
      # Author:      xsunknu
      #
      # Created:     21.08.2015
      # Copyright:   (c) xsunknu 2015
      # Licence:     <your licence>
      #-------------------------------------------------------------------------------
      
      import os, fme
      
      EPSGvalue = fme.macroValues['CLIPPER_EPSG_CODE']
      EPSGcode  = 'EPSG:' + EPSGvalue
      
      return EPSGcode
- DESTCOORDSYS:   # Python Script
      #-------------------------------------------------------------------------------
      # Name:        SetCoordinateSystem
      # Purpose:
      #
      # Author:      xsunknu
      #
      # Created:     21.08.2015
      # Copyright:   (c) xsunknu 2015
      # Licence:     <your licence>
      #-------------------------------------------------------------------------------
      
      import os, fme
      
      EPSGvalue = fme.macroValues['OUTPUT_EPSG_CODE']
      EPSGcode  = 'EPSG:' + EPSGvalue
      
      return EPSGcode
- FANOUT_FOLDER:   # Python Script
      #-------------------------------------------------------------------------------
      # Name:        GetConfigFile
      # Purpose:
      #
      # Author:      xsunknu
      #
      # Created:     21.08.2015
      # Copyright:   (c) xsunknu 2015
      # Licence:     <your licence>
      #-------------------------------------------------------------------------------
      
      import os, fme
      from xml.etree import ElementTree as ET
      
      if 'FME_SERVER_DEST_DIR' in fme.macroValues:
          value = fme.macroValues['FME_SERVER_DEST_DIR']
      else:
          #Read XML config file
          configtree = ET.parse(fme.macroValues['CONFIG_FILE'])
          configdoc = configtree.getroot()
          value = configdoc.find('destdir').text
      
      return value
- MAPPING_FILE:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme, os
      from xml.etree import ElementTree as ET
      
      #Read XML config file
      configtree = ET.parse(fme.macroValues['CONFIG_FILE'])
      configdoc = configtree.getroot()
      
      value = os.path.join(fme.macroValues['FME_MF_DIR'], configdoc.find('mappingfile').text)
      
      return value
- SOSIDEF_FILE:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme, os
      from xml.etree import ElementTree as ET
      
      #Read XML config file
      configtree = ET.parse(fme.macroValues['CONFIG_FILE'])
      configdoc = configtree.getroot()
      
      value = os.path.join(fme.macroValues['FME_MF_DIR'], configdoc.find('sosideffile').text)
      
      return value
- LOG_FILE:   # Python Script
      #-------------------------------------------------------------------------------
      # Name:        GetConfigFile
      # Purpose:
      #
      # Author:      xsunknu
      #
      # Created:     21.08.2015
      # Copyright:   (c) xsunknu 2015
      # Licence:     <your licence>
      #-------------------------------------------------------------------------------
      
      import os, uuid, fme
      
      fmwdir = fme.macroValues['FME_MF_DIR']
      fmwfile = fme.macroValues['FME_MF_NAME']
      
      logdir = os.path.join(fmwdir, 'log')
      if not os.path.isdir(logdir):
          os.mkdir(logdir)
      
      logfile = os.path.splitext(fmwfile)[0] + '_' + str(uuid.uuid1()).replace('-','') + '.log'
      logfile = os.path.join(logdir, logfile)
      
      return logfile
- HOVEDTEMA = Arealplaner   # Hovedtema
- UNDERTEMA = Planomriss   # Undertema

Readers:
- POSTGIS_1: POSTGIS from $(PG_DB)

Writers:
- SOSI_1: SOSI to C:\Users\xsunknu\Documents\work\Output\planomriss.sos

CreateClipper
    CLIPPERCOORDSYS = $(CLIPPERCOORDSYS)
    DESTCOORDSYS = $(DESTCOORDSYS)
    CLIPPERCOORDS = $(FIXEDCLIPPERCOORDS)
    -> Clipper [input 1]
    -> FeatureReader_2

Bookmark: Fylke and/or kommune clippers
admingrense.fylkeflate (reader POSTGIS_1)
    attributes: fylkeid int4, navn varchar(80)
    -> Tester
    -> AttributeCreator_7
AttributeCreator_7
    ATTR_LIST = _clippercoords,$(CLIPPERCOORDS),_clipper_file,$(CLIPPER_FILE),_fnr,$(FNR),_knr,$(KNR)
    -> Tester_4
Note: Sender inn hele landet som initiator / dersom alle klippeparametrene er / blanke
Tester_4
    TEST_CLAUSE:
      TEST _clipper_file ATTRIBUTE_IS_EMPTY ""
      TEST _clippercoords ATTRIBUTE_IS_EMPTY ""
      TEST _fnr ATTRIBUTE_IS_EMPTY ""
      TEST _knr ATTRIBUTE_IS_EMPTY ""
    TEST_MODE = Automatic
    TEST_DESCRIPTION = ""
    BOOL_OP = AND
    PASSED -> Reprojector_2
Tester
    TEST_CLAUSE = TEST @Value(fylkeid) IN $(FNR)
    TEST_MODE = Automatic
    TEST_DESCRIPTION = ""
    BOOL_OP = OR
    PASSED -> Reprojector_2
admingrense.kommuneflate (reader POSTGIS_1)
    attributes: kommuneid int4, navn varchar(80)
    -> Tester_2
Tester_2
    TEST_CLAUSE = TEST @Value(kommuneid) IN $(KNR)
    TEST_MODE = Automatic
    TEST_DESCRIPTION = ""
    BOOL_OP = OR
    PASSED -> Reprojector_2
Reprojector_2
    INTERPOLATION_TYPE_NAME = Nearest Neighbor
    SOURCE = Read from feature
    DEST = EPSG:4258
    RASTER_CELL_SIZE = Preserve Cells
    REPROJECTED -> FeatureReader_2

Bookmark: Clipper file (any format)
Creator
    GEOMTYPE = Geometry Object
    NUM = 1
    CREATED -> FeatureReader
FeatureReader
    COMBINE_GEOM = Use Result
    FORMAT = GENERIC
    GENERIC_REAL_FORMAT = GUESS_FROM_EXTENSION
    OUTPUT_FEATURES_DISPLAY = Based on Connections
    ATTRIBUTES = NewFeatureType,
    FEATURETYPES_RADIO = FEATURETYPES
    DATASET = $(CLIPPER_FILE)
    ATTR_ACCUM_MODE = Only Use Result
    INTERACT = <No Spatial Filter>
    <OTHER> -> Reprojector_3
Reprojector_3
    INTERPOLATION_TYPE_NAME = Nearest Neighbor
    SOURCE = Read from feature
    DEST = EPSG:4258
    RASTER_CELL_SIZE = Preserve Cells
    REPROJECTED -> FeatureReader_2
    REPROJECTED -> Clipper [input 1]

Bookmark: Lesing, klipping og transformasjon
FeatureReader_2
    ATTR_ACCUM_MODE = Only Use Result
    DATASET = $(PG_DB)
    POSTGIS_SCHEMALIST = planomriss
    POSTGIS_PASSWORD = $(PG_PWD)
    INTERACT = Intersects
    POSTGIS_PORT = $(PG_PORT)
    POSTGIS_USE_TRUE_POSTGIS_TYPES = yes
    FORMAT = POSTGIS
    POSTGIS_QUERY_FEATURE_TYPES_FOR_MERGE_FILTERS = Yes
    POSTGIS_HOST = $(PG_HOST)
    FEATURETYPES_RADIO = FEATURETYPES
    POSTGIS_DISABLE_COLLECTION_SPLITTING = yes
    OUTPUT_FEATURES_DISPLAY = Based on Connections
    COMBINE_GEOM = Use Result
    POSTGIS_USE_SEARCH_ENVELOPE = NO
    FEATURETYPES = planomriss.kpgrense planomriss.kpomrade planomriss.rpgrense planomriss.rpomrade
    POSTGIS_USER_NAME = $(PG_USER)
    ATTRIBUTES = planomriss.kpgrense,"objid,objtype",planomriss.kpomrade,"objid,objtype,landkode,fylkesnr,komm,planid,ikrafttredelsesdato,kunngjoringsdato,lovreferanse,lovreferansebeskrivelse,opprinneligadministrativenhet,opprinneligplanid,planbestemmelse,plannavn,planstatus,plantype,vedtakendeligplandato",planomriss.rpgrense,"objid,objtype",planomriss.rpomrade,"objid,objtype,landkode,fylkesnr,komm,planid,forslagsstillertype,gjennomforingsfrist,ikrafttredelsesdato,kunngjoringsdato,lovreferanse,lovreferansebeskrivelse,opprinneligadministrativenhet,opprinneligplanid,planbestemmelse,plannavn,planstatus,plantype,vedtakendeligplandato,vertikalniva"
    POSTGIS_CLIP_TO_ENVELOPE = NO
    planomriss.kpgrense -> AttributeCreator_6
    planomriss.kpomrade -> AttributeCreator_6
    planomriss.rpgrense -> AttributeCreator_6
    planomriss.rpomrade -> AttributeCreator_6
AttributeCreator_6
    ATTR_LIST = _clippercoords,$(CLIPPERCOORDS),_clipper_file,$(CLIPPER_FILE),_fnr,$(FNR),_knr,$(KNR)
    -> TestFilter
TestFilter
    TEST_LIST:
      BOOL_OP,AND,COMPOSITE_TEST,<Unused>,TEST_CLAUSE,"TEST _clipper_file ATTRIBUTE_IS_EMPTY """"
      TEST _clippercoords ATTRIBUTE_IS_EMPTY """"
      TEST _fnr ATTRIBUTE_IS_EMPTY """"
      TEST _knr ATTRIBUTE_IS_EMPTY """"",Landsdekkende,BOOL_OP,AND,COMPOSITE_TEST,<Unused>,TEST_CLAUSE,"TEST _clipper_file ATTRIBUTE_IS_EMPTY """"
      TEST _clippercoords ATTRIBUTE_IS_EMPTY """"
      TEST _fnr NOT_ATTRIBUTE_IS_EMPTY """"
      TEST _knr ATTRIBUTE_IS_EMPTY """"",Fylkesvis,BOOL_OP,AND,COMPOSITE_TEST,<Unused>,TEST_CLAUSE,"TEST _clipper_file ATTRIBUTE_IS_EMPTY """"
      TEST _clippercoords ATTRIBUTE_IS_EMPTY """"
      TEST _fnr ATTRIBUTE_IS_EMPTY """"
      TEST _knr NOT_ATTRIBUTE_IS_EMPTY """"",Kommunevis
    DEFAULT_VALUE = <UNFILTERED>
    Landsdekkende -> Reprojector
    <UNFILTERED> -> Clipper [input 2]
    Fylkesvis -> FeatureTypeFilter_2
    Kommunevis -> FeatureTypeFilter_3
Clipper
    CLIPPED_ATTR = _clipped
    ATTR_ACCUM_MODE = Merge Clipper
    PRESERVE_CLIPPEE_EXTENTS = No
    ATTR_CONFLICT_RES = Use Clipper
    CLIP_TYPE = Multiple Clippers
    CREATE_AGGREGATES = No
    BOUNDARY_CASES = Treat as Inside
    INSIDE -> Reprojector
FeatureTypeFilter_2
    ATTRIBUTES = planomriss.kpomrade,planomriss.kpgrense,planomriss.rpomrade,planomriss.rpgrense,<BLANK>,<UNFILTERED>
    planomriss.kpomrade -> Tester_3
    planomriss.rpomrade -> Tester_9
    planomriss.kpgrense -> SpatialRelator [input 1]
    planomriss.rpgrense -> SpatialRelator_2 [input 1]
Tester_3
    TEST_CLAUSE = TEST @Value(fylkesnr) IN @Value(_fnr)
    TEST_MODE = Automatic
    TEST_DESCRIPTION = ""
    BOOL_OP = OR
    PASSED -> SpatialRelator [input 2]
    PASSED -> Tester_13
SpatialRelator
    PREDICATES = TOUCHES
    CALC_CARD = No
    SUCCESS_ATTR = _related_candidates
    LIST_NAME = _relationships
    CURVE_BOUNDARY_RULE_PARAM = Default Rule
    -> Tester_13
Tester_9
    TEST_CLAUSE = TEST @Value(fylkesnr) IN @Value(_fnr)
    TEST_MODE = Automatic
    TEST_DESCRIPTION = ""
    BOOL_OP = OR
    PASSED -> SpatialRelator_2 [input 2]
    PASSED -> Tester_13
SpatialRelator_2
    PREDICATES = TOUCHES
    CALC_CARD = No
    SUCCESS_ATTR = _related_candidates
    LIST_NAME = _relationships
    CURVE_BOUNDARY_RULE_PARAM = Default Rule
    -> Tester_13
FeatureTypeFilter_3
    ATTRIBUTES = planomriss.kpomrade,planomriss.kpgrense,planomriss.rpomrade,planomriss.rpgrense,<BLANK>,<UNFILTERED>
    planomriss.kpomrade -> Tester_10
    planomriss.rpomrade -> Tester_11
    planomriss.kpgrense -> SpatialRelator_3 [input 1]
    planomriss.rpgrense -> SpatialRelator_4 [input 1]
Tester_10
    TEST_CLAUSE = TEST @Value(komm) IN @Value(_knr)
    TEST_MODE = Automatic
    TEST_DESCRIPTION = ""
    BOOL_OP = OR
    PASSED -> SpatialRelator_3 [input 2]
    PASSED -> Tester_13
SpatialRelator_3
    PREDICATES = INTERSECTS
    CALC_CARD = No
    SUCCESS_ATTR = _related_candidates
    LIST_NAME = _relationships
    CURVE_BOUNDARY_RULE_PARAM = Curve Boundary Includes All Endpoints
    -> Tester_13
Tester_11
    TEST_CLAUSE = TEST @Value(komm) IN @Value(_knr)
    TEST_MODE = Automatic
    TEST_DESCRIPTION = ""
    BOOL_OP = OR
    PASSED -> SpatialRelator_4 [input 2]
    PASSED -> Tester_13
SpatialRelator_4
    PREDICATES = INTERSECTS
    CALC_CARD = No
    SUCCESS_ATTR = _related_candidates
    LIST_NAME = _relationships
    CURVE_BOUNDARY_RULE_PARAM = Curve Boundary Includes All Endpoints
    -> Tester_13
Tester_13
    TEST_CLAUSE:
      TEST komm NOT_ATTRIBUTE_IS_MISSING ""
      TEST fylkesnr NOT_ATTRIBUTE_IS_MISSING ""
    TEST_MODE = Automatic
    TEST_DESCRIPTION = ""
    BOOL_OP = OR
    PASSED -> AttributeCreator_12
AttributeCreator_12
    ATTR_LIST = kommuneid,@Value(komm),fylkeid,@Value(fylkesnr)
    -> Reprojector
Reprojector
    INTERPOLATION_TYPE_NAME = Nearest Neighbor
    SOURCE = Read from feature
    DEST = $(DESTCOORDSYS)
    RASTER_CELL_SIZE = Preserve Cells
    REPROJECTED -> AttributeCreator_5
AttributeCreator_5
    ATTR_LIST = komm,@PadLeft(@Value(komm),4,0),opprinneligadministrativenhet,"FME_CONDITIONAL:DEFAULT_VALUE'@PadLeft(@Value(opprinneligadministrativenhet),4,0)'BOOL_OP;OR;COMPOSITE_TEST;<Unused>;TEST opprinneligadministrativenhet ATTRIBUTE_VALUE_NULL _FME_BLANK_STRING_'FME_NULL_VALUE'FME_NUM_CONDITIONS2___"
    -> SosiFilenameSetter
SosiFilenameSetter
    PLANBESTEMMELSE = @Value(planbestemmelse)
    UNDERTEMA = $(UNDERTEMA)
    _CREATION_INSTANCE = @Value(_creation_instance)
    KUNNGJORINGSDATO = @Value(kunngjoringsdato)
    LANDKODE = @Value(landkode)
    LOVREFERANSE = @Value(lovreferanse)
    _CLIPPER_FILE = @Value(_clipper_file)
    PG_PWD:
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------

      import fme
      from xml.etree import ElementTree as ET

      #Read XML config file
      configtree = ET.parse(fme.macroValues['CONFIG_FILE'])
      configdoc = configtree.getroot()
      value = configdoc.find('pgpwd').text

      return value
    PLANSTATUS = @Value(planstatus)
    KOMM = @Value(komm)
    _KNR = @Value(_knr)
    PG_HOST:
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------

      import fme
      from xml.etree import ElementTree as ET

      #Read XML config file
      configtree = ET.parse(fme.macroValues['CONFIG_FILE'])
      configdoc = configtree.getroot()
      value = configdoc.find('pghost').text

      return value
    PLANID = @Value(planid)
    VERTIKALNIVA = @Value(vertikalniva)
    FANOUT = $(FANOUT)
    IKRAFTTREDELSESDATO = @Value(ikrafttredelsesdato)
    OPPRINNELIGPLANID = @Value(opprinneligplanid)
    LOVREFERANSEBESKRIVELSE = @Value(lovreferansebeskrivelse)
    _CLIPPERCOORDS = @Value(_clippercoords)
    OPPRINNELIGADMINISTRATIVENHET = @Value(opprinneligadministrativenhet)
    KOMMUNEID = @Value(kommuneid)
    PG_USER:
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------

      import fme
      from xml.etree import ElementTree as ET

      #Read XML config file
      configtree = ET.parse(fme.macroValues['CONFIG_FILE'])
      configdoc = configtree.getroot()
      value = configdoc.find('pguser').text

      return value
    HOVEDTEMA = $(HOVEDTEMA)
    _FNR = @Value(_fnr)
    OUTPUT_EPSG_CODE = $(OUTPUT_EPSG_CODE)
    OBJTYPE = @Value(objtype)
    FYLKEID = @Value(fylkeid)
    PLANNAVN = @Value(plannavn)
    PG_DB:
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------

      import fme
      from xml.etree import ElementTree as ET

      #Read XML config file
      configtree = ET.parse(fme.macroValues['CONFIG_FILE'])
      configdoc = configtree.getroot()
      value = configdoc.find('pgdb').text

      return value
    VEDTAKENDELIGPLANDATO = @Value(vedtakendeligplandato)
    GJENNOMFORINGSFRIST = @Value(gjennomforingsfrist)
    OBJID = @Value(objid)
    FORSLAGSSTILLERTYPE = @Value(forslagsstillertype)
    _RELATED_CANDIDATES = @Value(_related_candidates)
    PLANTYPE = @Value(plantype)
    FYLKESNR = @Value(fylkesnr)
    _CLIPPED = @Value(_clipped)
    PG_PORT:
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------

      import fme
      from xml.etree import ElementTree as ET

      #Read XML config file
      configtree = ET.parse(fme.macroValues['CONFIG_FILE'])
      configdoc = configtree.getroot()
      value = configdoc.find('pgport').text

      return value
    -> FeatureTypeFilter

Bookmark: Kobler inn relaterte tabeller
FeatureTypeFilter
    ATTRIBUTES = planomriss.kpomrade,planomriss.kpgrense,planomriss.rpomrade,planomriss.rpgrense,<BLANK>,<UNFILTERED>
    planomriss.kpomrade -> FeatureMerger [input 1]
    planomriss.kpgrense -> FeatureMerger_2 [input 1]
    planomriss.rpomrade -> FeatureMerger_3 [input 1]
    planomriss.rpgrense -> FeatureMerger_4 [input 1]
    planomriss.kpomrade -> Tester_5
    planomriss.kpgrense -> Tester_6
    planomriss.rpomrade -> Tester_7
    planomriss.rpgrense -> Tester_8
Tester_5
    TEST_CLAUSE:
      TEST _clipper_file ATTRIBUTE_IS_EMPTY ""
      TEST _clippercoords ATTRIBUTE_IS_EMPTY ""
      TEST _fnr ATTRIBUTE_IS_EMPTY ""
      TEST _knr ATTRIBUTE_IS_EMPTY ""
    TEST_MODE = Automatic
    TEST_DESCRIPTION = ""
    BOOL_OP = AND
    FAILED -> Aggregator
    PASSED -> Sampler_5
Aggregator
    ORDERED = No
    MODE = Attributes Only
    CONCAT_ATTRS = objid
    ACCUM_ATTRS_NAME = No
    SEP = ,
    AGGREGATE -> AttributeCreator
AttributeCreator
    ATTR_LIST = sql,select * from planomriss.sosi_objekt_planomrade_kp where objid in (@Value(objid));
    -> SQLExecutor
Sampler_5
    SAMPLE_TYPE_LONG = First N Features
    RATE = 1
    SAMPLED -> AttributeCreator_11
AttributeCreator_11
    ATTR_LIST = sql,select * from planomriss.sosi_objekt_planomrade_kp;
    -> SQLExecutor
SQLExecutor
    POSTGRES_USER_NAME = $(PG_USER)
    COMBINE_GEOM = Initiator Geometry Only
    POSTGRES_HOST = $(PG_HOST)
    DATASET = $(PG_DB)
    POSTGRES_QUERY_FEATURE_TYPES_FOR_MERGE_FILTERS = Yes
    SQL_STATEMENT = @Value(sql)
    POSTGRES_PORT = $(PG_PORT)
    FORMAT = POSTGRES
    EXPOSED_ATTRIBUTE_LIST = forstedigitaliseringsdato,informasjon,kpomrade_fk,link,objid,oppdateringsdato,prosess_historie
    COMBINE_ATTRS = Result Attributes Only
    POSTGRES_PASSWORD = $(PG_PWD)
    RESULT -> FeatureMerger [input 2]
FeatureMerger
    IGNORE_NULLS = No
    JOIN_KEYS = @Value(objid) @Value(kpomrade_fk) AUTO
    SUPPLIERS_FIRST = No
    PROCESS_DUPS = No
    ATTR_CONFLICT_RES = Use Requestor
    MERGE_TYPE = Attributes Only
    ATTR_ACCUM_MODE = Merge Supplier
    MERGED -> KpOmrade (writer SOSI_1)
Tester_6
    TEST_CLAUSE:
      TEST _clipper_file ATTRIBUTE_IS_EMPTY ""
      TEST _clippercoords ATTRIBUTE_IS_EMPTY ""
      TEST _fnr ATTRIBUTE_IS_EMPTY ""
      TEST _knr ATTRIBUTE_IS_EMPTY ""
    TEST_MODE = Automatic
    TEST_DESCRIPTION = ""
    BOOL_OP = AND
    FAILED -> Aggregator_2
    PASSED -> Sampler_4
Aggregator_2
    ORDERED = No
    MODE = Attributes Only
    CONCAT_ATTRS = objid
    ACCUM_ATTRS_NAME = No
    SEP = ,
    AGGREGATE -> AttributeCreator_2
AttributeCreator_2
    ATTR_LIST = sql,select * from planomriss.sosi_objekt_planlinjer_kp where objid in (@Value(objid));
    -> SQLExecutor_2
Sampler_4
    SAMPLE_TYPE_LONG = First N Features
    RATE = 1
    SAMPLED -> AttributeCreator_10
AttributeCreator_10
    ATTR_LIST = sql,select * from planomriss.sosi_objekt_planlinjer_kp;
    -> SQLExecutor_2
SQLExecutor_2
    POSTGRES_USER_NAME = $(PG_USER)
    COMBINE_GEOM = Initiator Geometry Only
    POSTGRES_HOST = $(PG_HOST)
    DATASET = $(PG_DB)
    POSTGRES_QUERY_FEATURE_TYPES_FOR_MERGE_FILTERS = Yes
    SQL_STATEMENT = @Value(sql)
    POSTGRES_PORT = $(PG_PORT)
    FORMAT = POSTGRES
    EXPOSED_ATTRIBUTE_LIST = forstedigitaliseringsdato,kpgrense_fk,malemetode,noyaktighet,objid,oppdateringsdato,synbarhet
    COMBINE_ATTRS = Result Attributes Only
    POSTGRES_PASSWORD = $(PG_PWD)
    RESULT -> FeatureMerger_2 [input 2]
FeatureMerger_2
    IGNORE_NULLS = No
    JOIN_KEYS = @Value(objid) @Value(kpgrense_fk) AUTO
    SUPPLIERS_FIRST = No
    PROCESS_DUPS = No
    ATTR_CONFLICT_RES = Use Requestor
    MERGE_TYPE = Attributes Only
    ATTR_ACCUM_MODE = Merge Supplier
    MERGED -> KpGrense (writer SOSI_1)
Tester_7
    TEST_CLAUSE:
      TEST _clipper_file ATTRIBUTE_IS_EMPTY ""
      TEST _clippercoords ATTRIBUTE_IS_EMPTY ""
      TEST _fnr ATTRIBUTE_IS_EMPTY ""
      TEST _knr ATTRIBUTE_IS_EMPTY ""
    TEST_MODE = Automatic
    TEST_DESCRIPTION = ""
    BOOL_OP = AND
    FAILED -> Aggregator_3
    PASSED -> Sampler_3
Aggregator_3
    ORDERED = No
    MODE = Attributes Only
    CONCAT_ATTRS = objid
    ACCUM_ATTRS_NAME = No
    SEP = ,
    AGGREGATE -> AttributeCreator_3
AttributeCreator_3
    ATTR_LIST = sql,select * from planomriss.sosi_objekt_planomrade_rp where objid in (@Value(objid));
    -> SQLExecutor_3
Sampler_3
    SAMPLE_TYPE_LONG = First N Features
    RATE = 1
    SAMPLED -> AttributeCreator_9
AttributeCreator_9
    ATTR_LIST = sql,select * from planomriss.sosi_objekt_planomrade_rp;
    -> SQLExecutor_3
SQLExecutor_3
    POSTGRES_USER_NAME = $(PG_USER)
    COMBINE_GEOM = Initiator Geometry Only
    POSTGRES_HOST = $(PG_HOST)
    DATASET = $(PG_DB)
    POSTGRES_QUERY_FEATURE_TYPES_FOR_MERGE_FILTERS = Yes
    SQL_STATEMENT = @Value(sql)
    POSTGRES_PORT = $(PG_PORT)
    FORMAT = POSTGRES
    EXPOSED_ATTRIBUTE_LIST = forstedigitaliseringsdato,informasjon,link,objid,oppdateringsdato,prosess_historie,rpomrade_fk
    COMBINE_ATTRS = Result Attributes Only
    POSTGRES_PASSWORD = $(PG_PWD)
    RESULT -> FeatureMerger_3 [input 2]
FeatureMerger_3
    IGNORE_NULLS = No
    JOIN_KEYS = @Value(objid) @Value(rpomrade_fk) AUTO
    SUPPLIERS_FIRST = No
    PROCESS_DUPS = No
    ATTR_CONFLICT_RES = Use Requestor
    MERGE_TYPE = Attributes Only
    ATTR_ACCUM_MODE = Merge Supplier
    MERGED -> RpOmrade (writer SOSI_1)
Tester_8
    TEST_CLAUSE:
      TEST _clipper_file ATTRIBUTE_IS_EMPTY ""
      TEST _clippercoords ATTRIBUTE_IS_EMPTY ""
      TEST _fnr ATTRIBUTE_IS_EMPTY ""
      TEST _knr ATTRIBUTE_IS_EMPTY ""
    TEST_MODE = Automatic
    TEST_DESCRIPTION = ""
    BOOL_OP = AND
    FAILED -> Aggregator_4
    PASSED -> Sampler_2
Aggregator_4
    ORDERED = No
    MODE = Attributes Only
    CONCAT_ATTRS = objid
    ACCUM_ATTRS_NAME = No
    SEP = ,
    AGGREGATE -> AttributeCreator_4
AttributeCreator_4
    ATTR_LIST = sql,select * from planomriss.sosi_objekt_planlinjer_rp where objid in (@Value(objid));
    -> SQLExecutor_4
Sampler_2
    SAMPLE_TYPE_LONG = First N Features
    RATE = 1
    SAMPLED -> AttributeCreator_8
AttributeCreator_8
    ATTR_LIST = sql,select * from planomriss.sosi_objekt_planlinjer_rp;
    -> SQLExecutor_4
SQLExecutor_4
    POSTGRES_USER_NAME = $(PG_USER)
    COMBINE_GEOM = Initiator Geometry Only
    POSTGRES_HOST = $(PG_HOST)
    DATASET = $(PG_DB)
    POSTGRES_QUERY_FEATURE_TYPES_FOR_MERGE_FILTERS = Yes
    SQL_STATEMENT = @Value(sql)
    POSTGRES_PORT = $(PG_PORT)
    FORMAT = POSTGRES
    EXPOSED_ATTRIBUTE_LIST = forstedigitaliseringsdato,malemetode,noyaktighet,objid,oppdateringsdato,rpgrense_fk,synbarhet
    COMBINE_ATTRS = Result Attributes Only
    POSTGRES_PASSWORD = $(PG_PWD)
    RESULT -> FeatureMerger_4 [input 2]
FeatureMerger_4
    IGNORE_NULLS = No
    JOIN_KEYS = @Value(objid) @Value(rpgrense_fk) AUTO
    SUPPLIERS_FIRST = No
    PROCESS_DUPS = No
    ATTR_CONFLICT_RES = Use Requestor
    MERGE_TYPE = Attributes Only
    ATTR_ACCUM_MODE = Merge Supplier
    MERGED -> RpGrense (writer SOSI_1)

Bookmark: SOSI output
KpOmrade (writer SOSI_1)
    attributes: objtype SOSI_varchar(32), landkode SOSI_varchar(2), fylkesnr SOSI_int16, komm SOSI_varchar(4), planid SOSI_char, ikrafttredelsesdato SOSI_date, kunngjoringsdato SOSI_date, lovreferanse SOSI_int16, lovreferansebeskrivelse SOSI_varchar(255), opprinneligadministrativenhet SOSI_varchar(4), opprinneligplanid SOSI_varchar(16), planbestemmelse SOSI_int16, plannavn SOSI_varchar(255), planstatus SOSI_int16, plantype SOSI_char, vedtakendeligplandato SOSI_date, forstedigitaliseringsdato SOSI_datetime, informasjon SOSI_varchar(255), link SOSI_varchar(255), oppdateringsdato SOSI_datetime, prosess_historie SOSI_varchar(255)
KpGrense (writer SOSI_1)
    attributes: objtype SOSI_varchar(32), forstedigitaliseringsdato SOSI_datetime, malemetode SOSI_int16, noyaktighet SOSI_int16, synbarhet SOSI_int16, oppdateringsdato SOSI_datetime
RpOmrade (writer SOSI_1)
    attributes: objtype SOSI_varchar(32), landkode SOSI_varchar(2), fylkesnr SOSI_int16, komm SOSI_varchar(4), planid SOSI_varchar(16), forslagsstillertype SOSI_char, gjennomforingsfrist SOSI_date, ikrafttredelsesdato SOSI_date, kunngjoringsdato SOSI_date, lovreferanse SOSI_int16, lovreferansebeskrivelse SOSI_varchar(255), opprinneligadministrativenhet SOSI_varchar(4), opprinneligplanid SOSI_varchar(16), planbestemmelse SOSI_int16, plannavn SOSI_varchar(255), planstatus SOSI_int16, plantype SOSI_int16, vedtakendeligplandato SOSI_date, vertikalniva SOSI_int16, forstedigitaliseringsdato SOSI_datetime, informasjon SOSI_varchar(255), link SOSI_varchar(255), oppdateringsdato SOSI_datetime, prosess_historie SOSI_varchar(255)
RpGrense (writer SOSI_1)
    attributes: objtype SOSI_varchar(32), forstedigitaliseringsdato SOSI_datetime, malemetode SOSI_int16, noyaktighet SOSI_int16, synbarhet SOSI_int16, oppdateringsdato SOSI_datetime

FME custom transformer CreateClipper

Parameters:
- CLIPPERCOORDS = 253577 6650999 253577 6651246 253763 6651246 253763 6650999 253577 6650999   # Clipper Coordinate List
- CLIPPERCOORDSYS = EPSG:25833   # Clipper Coordinate System
- DESTCOORDSYS = "ESRIWKT|ETRS_1989_UTM_Zone_35N|PROJCS["ETRS_1989_UTM_Zone_35N",GEOGCS["GCS_ETRS_1989",DATUM["D_ETRS_1989",SPHEROID["GRS_1980",6378137.0,298.257222101]],PRIMEM["Greenwich",0.0],UNIT["Degree",0.0174532925199433]],PROJECTION["Transverse_Mercator"],PARAMETER["False_Easting",500000.0],PARAMETER["False_Northing",0.0],PARAMETER["Central_Meridian",27.0],PARAMETER["Scale_Factor",0.9996],PARAMETER["Latitude_Of_Origin",0.0],UNIT["Meter",1.0]]"   # Destination Coordinate System

Note: Creating geometry from / the Clipper coords
Creator
    GEOMTYPE = 2D Coordinate List
    COORDSYS = $(CLIPPERCOORDSYS)
    COORDS = $(CLIPPERCOORDS)
    NUM = 1
    CREATED -> BoundingBoxAccumulator
Note: Calculating the bounding / box (envelope) from the geometry
BoundingBoxAccumulator
    TOPFER_INDEX = No
    BOUNDING_BOX -> SpatialFilter [input 1]
    ORIGINAL -> SpatialFilter [input 2]
Note: If the geometry is equal to its / own bounding box - it is a rectangle!
SpatialFilter
    PREDICATES = EQUALS
    PASS_CRITERIA = Pass Against One Base
    MERGE_ATTRS = No
    BASE_TYPE = Single Base
    USE_BOUNDING_BOX = No
    PREDATTR = _predicate
    CURVE_BOUNDARY_RULE_PARAM = Default Rule
    PASSED -> Reprojector
    FAILED -> Reprojector_2
Note: If rectangle, reproject the / geometry to the destination / coordinate system
Reprojector
    STROKE_ARCS = Yes
    INTERPOLATION_TYPE_NAME = Nearest Neighbor
    SOURCE = Read from feature
    DEST = $(DESTCOORDSYS)
    RASTER_CELL_SIZE = Preserve Cells
    REPROJECTED -> BoundingBoxAccumulator_2
Note: Then calculate the bounding / box from the projected geoemtry
BoundingBoxAccumulator_2
    TOPFER_INDEX = No
    BOUNDING_BOX -> Reprojector_3
Note: Reproject the geometry back to / the DB coordsys (LL/EUREF89)
Reprojector_3
    STROKE_ARCS = Yes
    INTERPOLATION_TYPE_NAME = Nearest Neighbor
    SOURCE = Read from feature
    DEST = EPSG:4258
    RASTER_CELL_SIZE = Preserve Cells
    REPROJECTED -> GeometryFilter
Note: Reproject clipper to / the DB coordsys (LL/EUREF89)
Reprojector_2
    STROKE_ARCS = Yes
    INTERPOLATION_TYPE_NAME = Nearest Neighbor
    SOURCE = Read from feature
    DEST = EPSG:4258
    RASTER_CELL_SIZE = Preserve Cells
    REPROJECTED -> GeometryFilter
Note: Getting rid of dummies
GeometryFilter
    GEOM_PORT_NAMES = Area
    BREAK_AGG = No
    AREA -> Output (output)
Output (output)

FME custom transformer SosiFilenameSetter

Parameters:
- OUTPUT_EPSG_CODE = 25832   # Destination coordinate system
- FANOUT = Kommuner   # Fanout områder
- KOMMUNEID = @Value(kommuneid)   # kommuneid
- FYLKEID = @Value(fylkeid)   # fylkeid
- _CLIPPED = @Value(_clipped)   # Clipped
- _CLIPPER_FILE = @Value(_clipper_file)   # Clipper File
- _CLIPPERCOORDS = @Value(_clippercoords)   # Clippercoords
- _CREATION_INSTANCE = @Value(_creation_instance)   # Creation Instance
- _FNR = @Value(_fnr)   # Fnr
- _KNR = @Value(_knr)   # Knr
- _RELATED_CANDIDATES = @Value(_related_candidates)   # Related Candidates
- FORSLAGSSTILLERTYPE = @Value(forslagsstillertype)   # forslagsstillertype
- FYLKESNR = @Value(fylkesnr)   # fylkesnr
- GJENNOMFORINGSFRIST = @Value(gjennomforingsfrist)   # gjennomforingsfrist
- IKRAFTTREDELSESDATO = @Value(ikrafttredelsesdato)   # ikrafttredelsesdato
- KOMM = @Value(komm)   # komm
- KUNNGJORINGSDATO = @Value(kunngjoringsdato)   # kunngjoringsdato
- LANDKODE = @Value(landkode)   # landkode
- LOVREFERANSE = @Value(lovreferanse)   # lovreferanse
- LOVREFERANSEBESKRIVELSE = @Value(lovreferansebeskrivelse)   # lovreferansebeskrivelse
- OBJID = @Value(objid)   # objid
- OBJTYPE = @Value(objtype)   # objtype
- OPPRINNELIGADMINISTRATIVENHET = @Value(opprinneligadministrativenhet)   # opprinneligadministrativenhet
- OPPRINNELIGPLANID = @Value(opprinneligplanid)   # opprinneligplanid
- PLANBESTEMMELSE = @Value(planbestemmelse)   # planbestemmelse
- PLANID = @Value(planid)   # planid
- PLANNAVN = @Value(plannavn)   # plannavn
- PLANSTATUS = @Value(planstatus)   # planstatus
- PLANTYPE = @Value(plantype)   # plantype
- VEDTAKENDELIGPLANDATO = @Value(vedtakendeligplandato)   # vedtakendeligplandato
- VERTIKALNIVA = @Value(vertikalniva)   # vertikalniva
- UNDERTEMA =   # Undertema
- HOVEDTEMA =   # Hovedtema
- PG_DB:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgdb').text
      
      return value
- PG_HOST:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pghost').text
      
      return value
- PG_PORT:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgport').text
      
      return value
- PG_PWD:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgpwd').text
      
      return value
- PG_USER:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pguser').text
      
      return value

Input (input)
    -> ParameterFetcher
ParameterFetcher
    ATTR_LIST = _output_epsg_code {$(OUTPUT_EPSG_CODE)} _fanout {$(FANOUT)}
    -> AttributeValueMapper
Note: Fikser kjente feil i kommunenummer
AttributeValueMapper
    LUT = 1901,1903
    SRC = kommuneid
    VAL_ATTR = kommuneid
    DEFAULT_VALUE = @Value(kommuneid)
    DIRECTION = Forward (Source To Destination)
    -> TestFilter_2
TestFilter_2
    TEST_LIST = BOOL_OP,OR,COMPOSITE_TEST,<Unused>,TEST_CLAUSE,"TEST $(FANOUT) = Kommuner",Kommuner,BOOL_OP,OR,COMPOSITE_TEST,<Unused>,TEST_CLAUSE,"TEST $(FANOUT) = Fylker",Fylker
    DEFAULT_VALUE = Ufiltrert
    Kommuner -> Joiner
    Ufiltrert -> AttributeCreator_13
    Fylker -> Joiner_2
Joiner
    POSTGIS_QUERY_FEATURE_TYPES_FOR_MERGE_FILTERS = Yes
    POSTGIS_DISABLE_COLLECTION_SPLITTING = yes
    JOIN_KEYS = kommuneid kommuneid
    POSTGIS_PASSWORD = $(PG_PWD)
    FORMAT = POSTGIS
    PREFETCH_EXHAUSTIVE = Yes
    CACHE_SIZE = 5000
    POSTGIS_PORT = $(PG_PORT)
    POSTGIS_USE_TRUE_POSTGIS_TYPES = yes
    POSTGIS_USER_NAME = $(PG_USER)
    DATASET = $(PG_DB)
    MATCH_RULE_DISPLAY = Must Match Exactly One (1:1)
    ADDED_FIELDS = navn
    TABLE = admingrense.kommuner
    POSTGIS_HOST = $(PG_HOST)
    JOINED -> StringReplacer_2
Joiner_2
    POSTGIS_QUERY_FEATURE_TYPES_FOR_MERGE_FILTERS = Yes
    POSTGIS_DISABLE_COLLECTION_SPLITTING = yes
    JOIN_KEYS = fylkeid fylkeid
    POSTGIS_PASSWORD = $(PG_PWD)
    FORMAT = POSTGIS
    PREFETCH_EXHAUSTIVE = Yes
    CACHE_SIZE = 5000
    POSTGIS_PORT = $(PG_PORT)
    POSTGIS_USE_TRUE_POSTGIS_TYPES = yes
    POSTGIS_USER_NAME = $(PG_USER)
    DATASET = $(PG_DB)
    MATCH_RULE_DISPLAY = Must Match Exactly One (1:1)
    ADDED_FIELDS = navn
    TABLE = admingrense.fylkeflate
    POSTGIS_HOST = $(PG_HOST)
    JOINED -> StringReplacer_2
AttributeCreator_13
    ATTR_LIST = sosifile,"FME_CONDITIONAL:DEFAULT_VALUE'Arealplaner_$(OUTPUT_EPSG_CODE)_$(UNDERTEMA)_SOSI'BOOL_OP;OR;COMPOSITE_TEST;<Unused>;TEST $(FANOUT) LIKE Kommuner'Arealplaner_@PadLeft(@Value(kommuneid),4,0)_@Value(navn)_$(OUTPUT_EPSG_CODE)_$(UNDERTEMA)_SOSI'BOOL_OP;OR;COMPOSITE_TEST;<Unused>;TEST $(FANOUT) LIKE Fylker'Arealplaner_@PadLeft(@Value(fylkeid),2,0)_@Value(navn)_$(OUTPUT_EPSG_CODE)_$(UNDERTEMA)_SOSI'BOOL_OP;OR;COMPOSITE_TEST;<Unused>;TEST $(FANOUT) LIKE Norge'Arealplaner_Norge_$(OUTPUT_EPSG_CODE)_$(UNDERTEMA)_SOSI'FME_NUM_CONDITIONS4___"
    -> Output (output)
Output (output)

Bookmark: Substituerer ÆØÅ og mellomrom
StringReplacer_2
    FIND_TEXT = " "
    REPLACE_TEXT = _
    REGEXP = no
    CASE = no
    SRC_ATTRS = navn
    NO_MATCH = _FME_NO_OP_
    -> StringReplacer_3
StringReplacer_3
    FIND_TEXT = Æ
    REPLACE_TEXT = E
    REGEXP = no
    CASE = yes
    SRC_ATTRS = navn
    NO_MATCH = _FME_NO_OP_
    -> StringReplacer_4
StringReplacer_4
    FIND_TEXT = Ø
    REPLACE_TEXT = O
    REGEXP = no
    CASE = yes
    SRC_ATTRS = navn
    NO_MATCH = _FME_NO_OP_
    -> StringReplacer_5
StringReplacer_5
    FIND_TEXT = Å
    REPLACE_TEXT = A
    REGEXP = no
    CASE = yes
    SRC_ATTRS = navn
    NO_MATCH = _FME_NO_OP_
    -> StringReplacer_6
StringReplacer_6
    FIND_TEXT = æ
    REPLACE_TEXT = e
    REGEXP = no
    CASE = yes
    SRC_ATTRS = navn
    NO_MATCH = _FME_NO_OP_
    -> StringReplacer_7
StringReplacer_7
    FIND_TEXT = ø
    REPLACE_TEXT = o
    REGEXP = no
    CASE = yes
    SRC_ATTRS = navn
    NO_MATCH = _FME_NO_OP_
    -> StringReplacer_8
StringReplacer_8
    FIND_TEXT = å
    REPLACE_TEXT = a
    REGEXP = no
    CASE = yes
    SRC_ATTRS = navn
    NO_MATCH = _FME_NO_OP_
    -> AttributeCreator_13
