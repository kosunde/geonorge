FME workspace Planomriss_postgis2wfstest.fmw

Parameters:
- CONFIG_FILE:   # Python Script
      #-------------------------------------------------------------------------------
      # Name:        GetConfigFile
      # Purpose:
      #
      # Author:      xsunknu
      #
      # Created:     21.08.2015
      # Copyright:   (c) xsunknu 2015
      # Licence:     <your licence>
      #-------------------------------------------------------------------------------
      
      import os, fme
      
      fmwdir = fme.macroValues['FME_MF_DIR']
      fmwfile = fme.macroValues['FME_MF_NAME']
      
      fmwfile = os.path.join(fmwdir, fmwfile)
      configfile = os.path.splitext(fmwfile)[0] + '_config.xml'
      
      return configfile
- READER_FORMAT = GML   # Input Format
- GML_OUT_TARGET_NS_PREFIX_GML = app   # Target Namespace Prefix
- GML_OUT_TARGET_NS_URI_GML = http://skjema.geonorge.no/SOSI/produktspesifikasjon/Planomriss/4.5   # Target Namespace URI
- MAX_FEATURES = 3000   # Max features returned
- PG_DB:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgdb').text
      
      return value
- PG_HOST:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pghost').text
      
      return value
- PG_PORT:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgport').text
      
      return value
- PG_PWD:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgpwd').text
      
      return value
- PG_USER:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pguser').text
      
      return value
- DestDataset_GML = $(FME_MF_DIR)Planomriss.gml   # Destination Geography Markup Language (GML) File
- SourceDataset_GML = C:\Users\xmaland\Documents\GitHub\geonorge\Arealplaner\Planomriss_postgis2gml\Planomriss.gml   # Source Geography Markup Language (GML) File(s)
- FME_SERVER_REQUEST_URI = http://nnrite507/fmedatastreaming/Arealplaner/Planomriss_postgis2wfstest.fmw?   # FME Server Request URI

Readers:
- XML_1: XML from C:\Users\xmaland\Documents\GitHub\geonorge\DSB\useparameters.xml
- GML_1: GML from $(SourceDataset_GML)

Writers:
- GML2_1: GML2 to C:\Users\bpont\Downloads\return.gml
- GML_2: GML to C:\Users\bpont\Downloads\return.gml
- TEXTLINE_1: TEXTLINE to return.xml
- GML_3: GML to $(DestDataset_GML)

Note: WFS Service Template / To modify this workspace to serve your desired dataset, please follow the steps below: / 1. Open the Transformers in the Navigation Window. / 2. Click on the first transformer (_FeatureReader_Source) to navigate to it. / 3. Open the transformer Properties and modify the reader settings to read your desired source data. / 4. Modify the Private Parameters in the Navigation Window / Input Format: Choose the same format as you used in the FeatureReader / Reader Dataset: Copy the contents of the Dataset field in the FeatureReader / Target Namespace Prefix: Default of 'mywfs' will work, but you can specify your own namespace ('fme' is reserved and will cause the workspace to fail). / Target Namespace URI: Your namespace schema, if you change from the default. / 5. Right-click on Workspace Resources in the Navigator and choose Add a Reader as a Resource. / Add a reader with the same settings you used in the Feature Reader. / This resource will provide the output schema information for the results. / 6. Open the Properties of the three GML feature types in the lower right section of the workspace. / Check the Dynamic Properties box. / Modify the Schema Sources to point only to the reader you added as a resource. / Leave Schema Definition set to Default / 7. Publish workspace to FME Server Data Streaming Service. Check the service properties to ensure that / The Output Datasets include the Textline and all three GML writers / The Source Dataset to Override is set to useParameters[XML]
Note: Route Features
AttributeFilter_6
    ATTR_NAME = REQUEST
    ATTR_VALUES = <EMPTY>,<MISSING>,<NULL>,<UNFILTERED>,GetCapabilities,DescribeFeatureType,GetFeature
    DescribeFeatureType -> FeatureReader_Schema_2
    GetFeature -> StringReplacer_2
    GetCapabilities -> AttributeFilter_2
    <NULL> -> AttributeFilter_2
    <MISSING> -> AttributeFilter_2
    <EMPTY> -> AttributeFilter_2
    <UNFILTERED> -> XMLTemplater_2
text_line (writer TEXTLINE_1)
    attributes: text_line_data buffer

Bookmark: Read POST if sent, otherwise create feature to use GET parameters
GetCapabilities (reader XML_1)
    attributes: xml_fragment xml_xml, xml_id xml_char(21), xml_matched_element xml_char(16), xml_parent_child_pos xml_char(1), xml_parent_id xml_char(1)
    -> AttributeCreator
DescribeFeatureType (reader XML_1)
    attributes: xml_fragment xml_xml, xml_id xml_char(25), xml_matched_element xml_char(20), xml_parent_child_pos xml_char(1), xml_parent_id xml_char(1)
    -> AttributeCreator
GetFeature (reader XML_1)
    attributes: xml_fragment xml_xml, xml_id xml_char(16), xml_matched_element xml_char(11), xml_parent_child_pos xml_char(1), xml_parent_id xml_char(1)
    -> AttributeCreator
Note: Copy Feature Type to attribute
AttributeCreator
    ATTR_LIST = _id,0
    -> FeatureTypeExtractor_2
    -> AttributeCreator_Output
AttributeCreator_Output: Logger
    MAXCOORDS = 20
    MAXFEATS = 20
    MESSAGE = Feature is:
FeatureTypeExtractor_2
    DEST_ATTR = REQUEST
    -> DuplicateRemover
Note: Create feature after all / input features read
Creator
    GEOMTYPE = Geometry Object
    NUM = 1
    CREATED -> DuplicateRemover
Note: Block GET feature if POST is read
DuplicateRemover
    KEYATTR = _id
    UNIQUE -> AttributeRenamer_5
AttributeRenamer_5
    ATTR_LIST = xml_fragment,xml_request,
    -> AttributeFilter
Note: Route Features
AttributeFilter
    ATTR_NAME = REQUEST
    ATTR_VALUES = <EMPTY>,<MISSING>,<NULL>,<UNFILTERED>,GetCapabilities,DescribeFeatureType,GetFeature
    GetCapabilities -> XMLFlattener_2
    DescribeFeatureType -> XMLFlattener
    <MISSING> -> ParameterFetcher_2
    GetFeature -> XMLFlattener_3

Bookmark: Process GET Request
Note: Get URI of workspace / Map null for testing in desktop
ParameterFetcher_2
    ATTR_LIST = _FME_SERVER_REQUEST_URI {$(FME_SERVER_REQUEST_URI)}
    -> NullAttributeMapper_2
NullAttributeMapper_2
    NULL_TREATMENT = New Value
    ATTRCHOICE = Selected Attributes
    SOURCE_ATTR_VAL = Empty "Missing (Selected Attributes Only)" Null
    NEW_VALUE = " "
    ATTRLIST = _FME_SERVER_REQUEST_URI
    -> TextDecoder
Note: Decode URL string
TextDecoder
    STRING_TO_DECODE = @Value(_FME_SERVER_REQUEST_URI)
    ENCODING_TYPE = URL (Percent Encoding)
    DEST_ATTR = _FME_SERVER_REQUEST_URI
    -> FMEServerURLSplitter
Note: Split calling URI to get parameters
Note: FMEServerURLSplitter [FMEServerURLSplitter] / [Embedded] / Request URI: @Value(_FME_SERVER_REQUEST_URI) / URL Parameter Name Case: UPPERCASE / Decode URL Parameters: Decode
FMEServerURLSplitter
    _FME_SERVER_REQUEST_URI = @Value(_FME_SERVER_REQUEST_URI)
    DECODE_URL_TEXT = Decode
    URL_PARAM_NAME_CASE = UPPERCASE
    -> AttributeExposer_4
Note: Expose parameter attributes
AttributeExposer_4
    ATTR_LIST = SERVICE,REQUEST,VERSION,TYPENAME,TYPENAMES,FILTER,BBOX,ACCEPTVERSIONS,SRSNAME,COUNT,MAXFEATURES
    -> AttributeFilter_6

Bookmark: GetCapabilities POST Request
Note: Flatten POST XML
XMLFlattener_2
    ATTRIBUTE_XML = xml_request
    NEW_ATTRIBUTES = GetCapabilities.version TypeName TypeNames
    XML_SOURCE_TYPE = Attribute with XML document
    EMBEDDED_EXPRESSIONS = GetCapabilities
    FLATTEN_OPTIONS = <structure separator="." map-empty-elements="yes" matched-prefix="attributes" matched-attributes="yes" cardinality="+{?}" structure-prefix="" child-position-attribute="" except-expression="" ui-mode="basic" matched-ancestor-attributes=""/>
    -> AttributeRenamer_2
Note: Copy Version
AttributeRenamer_2
    ATTR_LIST = GetCapabilities.version,VERSION,
    -> AttributeFilter_6

Bookmark: DescribeFeatureType POST request
Note: Flatten POST XML
XMLFlattener
    ATTRIBUTE_XML = xml_request
    NEW_ATTRIBUTES = DescribeFeatureType.version TypeName TypeNames TypeName{} TypeNames{}
    XML_SOURCE_TYPE = Attribute with XML document
    EMBEDDED_EXPRESSIONS = DescribeFeatureType
    FLATTEN_OPTIONS = <structure separator="." map-empty-elements="yes" matched-prefix="attributes" matched-attributes="yes" cardinality="+{?}" structure-prefix="" child-position-attribute="" except-expression="" ui-mode="basic" matched-ancestor-attributes=""/>
    -> ListConcatenator
Note: Create Type lists
ListConcatenator
    VAL_ATTR = _typename
    DROP_EMPTY_PARTS = Yes
    SEP = ,
    LIST_ATTR = TypeName{}
    -> ListConcatenator_2
ListConcatenator_2
    VAL_ATTR = _typenames
    DROP_EMPTY_PARTS = Yes
    SEP = ,
    LIST_ATTR = TypeNames{}
    -> AttributeCreator_6
Note: Copy Version and Type Names
AttributeCreator_6
    ATTR_LIST = TYPENAME,"FME_CONDITIONAL:DEFAULT_VALUE'@Value(_typename)'BOOL_OP;OR;COMPOSITE_TEST;<Unused>;TEST _typename ATTRIBUTE_VALUE_NULL _FME_BLANK_STRING_;TEST _typename ATTRIBUTE_IS_EMPTY _FME_BLANK_STRING_;TEST _typename ATTRIBUTE_IS_MISSING _FME_BLANK_STRING_'@Value(TypeName)'FME_NUM_CONDITIONS2___",TYPENAMES,"FME_CONDITIONAL:DEFAULT_VALUE'@Value(_typenames)'BOOL_OP;OR;COMPOSITE_TEST;<Unused>;TEST _typenames ATTRIBUTE_VALUE_NULL _FME_BLANK_STRING_;TEST _typenames ATTRIBUTE_IS_EMPTY _FME_BLANK_STRING_;TEST _typenames ATTRIBUTE_IS_MISSING _FME_BLANK_STRING_'@Value(TypeNames)'FME_NUM_CONDITIONS2___",VERSION,@Value(DescribeFeatureType.version)
    -> AttributeFilter_6

Bookmark: GetFeature POST
Note: Flatten POST XML
XMLFlattener_3
    ATTRIBUTE_XML = xml_request
    NEW_ATTRIBUTES = GetFeature.version Query.typeName Query.typeNames Query{}.typeName Query{}.typeNames Query{}.srsName Query{}.COUNT Query.COUNT Query.MAXFEATURES Query{}.MAXFEATURES
    XML_SOURCE_TYPE = Attribute with XML document
    EMBEDDED_EXPRESSIONS = GetFeature
    FLATTEN_OPTIONS:
      <structure
      separator="."
      open-list-brace="{"
      close-list-brace="}"
      map-empty-elements="yes"
      matched-prefix="attributes"
      matched-attributes="yes"
      matched-ancestor-attributes=""
      cardinality="+{?}"
      except=""
      structure-prefix=""
      child-position-attribute=""
      attribute-identifier=""/>

      <!--
      The options here allows customization of the attributes and attribute lists of the matched XML subtree
      that will be added to FME Features.

      Here are the following options that can be specified:

      1. separator
      This value of this option is used as the separator in the naming of the attributes of the children of the matched elements.

      Default value: .
      Possible values: any string

      2. open-list-brace
      Specifies the open list index delimiter brace for the flattened attributes.

      Default value: {
      Possible values: any string

      3. close-list-brace
      Specifies the close list index delimiter brace for the flattened attributes.

      Default value: }
      Possible values: any string

      4. map-empty-elements
      If set to yes, then any empty elements will be added as attributes with empty values onto the features.
      Otherwise, the attributes will not be added onto the features.

      Default value if not specified: yes
      Possible values: yes|no

      Default value:
      Possible values: any string

      5. matched-prefix
      This option controls whether FME feature attributes produced will be prefixed with matched element's name.
      If the value is 'yes', then both the matched element's attributes and all its children are prefixed
      If the value is 'no', then none of the feature attributes are prefixed with matched element's name
      If the value is 'children', then only the children of the matched element are prefixed
      If the value is 'attributes', then only the attributes of the matched element are prefixed

      Default value if not specified: yes
      Possible values: yes|no|children|attributes

      6. matched-attributes
      If this option is set to 'yes' then the attributes of the matched element are mapped as FME feature attributes.
      Otherwise, the attributes of the matched element are ignored.

      matched-prefix option can also be set to 'attributes' or 'yes' to allow the attributes to be prefixed with
      the name of the matched element.

      Default value if not specified: yes
      Possible values: yes|no

      7. matched-ancestor-attributes
      The option controls whether XML attributes from ancestor of the matched element should be included as FME feature attributes.

      The valid values for this option are:
      - 'parent' or '1'         : XML attributes of the parent of the matched element are added
      - 'grandparent' or '2'    : XML attributes of the grandparent of the matched element are added
      - 'root' or '-1'          : XML attributes of the root of the document are added
      - any non-negative number : XML attributes of the ancestor by going up x levels from the matched element are added.
                                  0 is the matched element.

      To include more than one ancestor, multiple values can be separated by a space.
      For example: To get the attributes from root, parent and grand parent, we can specify
      matched-ancestor-attributes="parent grandparent root"

      Default value:
      Possible values: parent|grandparent|root

      8. cardinality
      This option can be specified as a space separated list of cardinality directives.

      Default value: +{?} (Treat child elements as a list if there are more than one with the same name)
      Possible values: Refer to the documentation of XFMap section in XML Reader documentation

      9. structure-prefix
      This option can be set to non-empty string that serves as a prefix to every attribute that is generated for a matched element.

      Default value:
      Possible values: any string

      10. except
      The except attribute accepts the same types of expressions as the match or except attribute of a mapping rule.
      For example, the expression except=”parent/child{2}” could be used to exclude the second <child> element
      contained in a <parent> element from the output of the structure subrule.

      Default value:
      Possible values: any path expression

      11. child-position-attribute
      When this option is set to non-empty string, each child element will generate an additional feature attribute
      whose value will be the position of the child element witihin its parent.

      Default value:
      Possible values: any string

      12. attribute-identifier (Any string)
      XML attributes can be differentiated from leaf elements. By setting this option to non-empty string, XML reader
      will append a prefix to the attributes in the leaf elements.

      All the options have more elaborated examples and descriptions in the XML reader documentation.
      -->
    -> XMLFragmenter
    -> FeatureMerger [input 1]
Note: Extract Filter XML
XMLFragmenter
    ATTRIBUTE_XML = xml_request
    XML_SOURCE_TYPE = Attribute with XML document
    MERGE_ATTRS = Yes
    EMBEDDED_EXPRESSIONS = Filter
    FRAGMENTS -> FeatureMerger [input 2]
Note: Merge Filter onto request
FeatureMerger
    ATTR_CONFLICT_RES = Use Supplier
    ATTR_ACCUM_MODE = Merge Supplier
    IGNORE_NULLS = No
    MERGE_TYPE = Attributes Only
    SUPPLIERS_FIRST = No
    PROCESS_DUPS = No
    JOIN_KEYS = 1 1 AUTO
    MERGED -> ListExploder_4
    NOT_MERGED -> ListExploder_4
Note: Explode query list
ListExploder_4
    ATTR_ACCUM_MODE = Merge Incoming List
    INDEX_ATTR = _element_index
    LIST_ATTR = Query{}
    ATTR_CONFLICT_RES = Use Original
    NOT_FOUND -> AttributeRenamer_4
    LIST_FOUND -> AttributeRenamer_3
Note: Copy Version and Type Names
AttributeRenamer_3
    ATTR_LIST = GetFeature.version,VERSION,,typeName,TYPENAME,,typeNames,TYPENAMES,,xml_fragment,FILTER,,srsName,SRSNAME,,COUNT,Teller,,MAXFEATURES,Teller,
    -> AttributeFilter_6
Note: Copy Version and Type Names
AttributeRenamer_4
    ATTR_LIST = GetFeature.version,VERSION,,Query.typeName,TYPENAME,,Query.typeNames,TYPENAMES,,xml_fragment,FILTER,,Query.srsName,SRSNAME,,COUNT,Teller,,MAXFEATURES,Teller,
    -> AttributeFilter_6

Bookmark: GetCapabilities
AttributeFilter_2
    ATTR_NAME = VERSION
    ATTR_VALUES = <EMPTY>,<MISSING>,<NULL>,<UNFILTERED>,1.0.0,1.1.0,2.0.0
    1.0.0 -> AttributeFileReader_2
    1.1.0 -> AttributeFileReader_3
    2.0.0 -> AttributeFileReader
    <UNFILTERED> -> AttributeFileReader
    <NULL> -> AttributeFileReader
    <EMPTY> -> AttributeFileReader
    <MISSING> -> AttributeFileReader
AttributeFileReader_2
    CHAR_ENCODING = utf-8
    FILE_NAME = $(FME_MF_DIR_ENCODED)GetCapabilities10.xml
    DEST_ATTR = text_line_data
    -> text_line (writer TEXTLINE_1)
AttributeFileReader_3
    CHAR_ENCODING = utf-8
    FILE_NAME = $(FME_MF_DIR_ENCODED)GetCapabilities11.xml
    DEST_ATTR = text_line_data
    -> text_line (writer TEXTLINE_1)
AttributeFileReader
    CHAR_ENCODING = utf-8
    FILE_NAME = $(FME_MF_DIR_ENCODED)GetCapabilities20.xml
    DEST_ATTR = text_line_data
    -> text_line (writer TEXTLINE_1)

Bookmark: Error handling unsupported request
XMLTemplater_2
    RESULT_ATTRIBUTE = text_line_data
    ROOT_QUERY_EXPR:
      <ows:ExceptionReport xmlns:ows="http://www.opengis.net/ows/1.1" xmlns:xsi="http://www.w3.org/2001/XMLSchema-instance" xsi:schemaLocation="http://www.opengis.net/ows/1.1 http://schemas.opengis.net/ows/1.1.0/owsExceptionReport.xsd" version="2.0.0">
        <ows:Exception exceptionCode="InvalidParameterValue" locator="request">
          <ows:ExceptionText>No service for request type {fme:get-attribute("REQUEST")} is configured / active.</ows:ExceptionText>
        </ows:Exception>
      </ows:ExceptionReport>
    VISIBLE_QUERY_VALIDATE = Yes
    OUTPUT_XML_HEADER = Yes
    -> text_line (writer TEXTLINE_1)

Bookmark: DescribeFeatureType
Note: Read Source data schema
FeatureReader_Schema_2
    ATTR_CONFLICT_RES = Use Result
    ATTR_ACCUM_MODE = Merge Initiator and Result
    DATASET = C:\Users\xmaland\Documents\GitHub\geonorge\Arealplaner\Planomriss_postgis2gml\Planomriss.xsd
    COMBINE_GEOM = Use Result
    CACHE_TIMEOUT_HRS = 24
    FEATURETYPES = schema
    SUPPORTED_SPATIAL_INTERACTIONS = ENVELOPE_INTERSECT%INTERSECTS%CONTAINS%CROSSES%DISJOINT%EQUALS%OVERLAPS%TOUCHES%WITHIN
    SCHEMA_SCHEMA_READER = yes
    FORMAT = SCHEMA
    SCHEMA_REAL_FORMAT = $(READER_FORMAT)
    FEATURETYPES_RADIO = FEATURETYPES
    <OTHER> -> DescribeFeatureType
DescribeFeatureType
    GML_OUT_TARGET_NS_URI_GML = $(GML_OUT_TARGET_NS_URI_GML)
    TYPENAMES = @Value(TYPENAMES)
    GML_OUT_TARGET_NS_PREFIX_GML = $(GML_OUT_TARGET_NS_PREFIX_GML)
    TYPENAME = @Value(TYPENAME)
    VERSION = @Value(VERSION)
    XMLFormatter_2_Passed -> text_line (writer TEXTLINE_1)

Bookmark: GetFeatures
Note: Remove NameSpace from TypeNames
StringReplacer_2
    FIND_TEXT = $(GML_OUT_TARGET_NS_PREFIX_GML):
    CASE = no
    REGEXP = no
    NO_MATCH = _FME_NO_OP_
    SRC_ATTRS = TYPENAME,TYPENAMES
    -> StringReplacer
StringReplacer
    FIND_TEXT = ,
    CASE = no
    REGEXP = no
    NO_MATCH = _FME_NO_OP_
    SRC_ATTRS = TYPENAME,TYPENAMES
    REPLACE_TEXT = " "
    -> Tester_4
Note: Different WFS versions have / different type name attributes
Tester_4
    BOOL_OP = OR
    TEST_DESCRIPTION = ""
    TEST_MODE = Automatic
    TEST_CLAUSE = TEST @Value(VERSION) = 2.0.0
    PASSED -> AttributeCopier
    FAILED -> AttributeCopier_2
Note: WFS 2.0.0
AttributeCopier
    ATTR_LIST = TYPENAMES,_types,"",COUNT,Teller,""
    -> WFS_BBOX_CREATOR
AttributeCopier_2
    ATTR_LIST = TYPENAME,_types,"",MAXFEATURES,Teller,""
    -> WFS_BBOX_CREATOR
WFS_BBOX_CREATOR
    FILTER = @Value(FILTER)
    SRSNAME = @Value(SRSNAME)
    BBOX = @Value(BBOX)
    WFS20_FilterBBOX -> WFS_FILTER_CREATOR
    Standard_bbox -> WFS_FILTER_CREATOR
    Reprojected_BBOX -> WFS_FILTER_CREATOR
    Default_BBOX -> WFS_FILTER_CREATOR
Note: Different WFS versions have / different type name attributes
Note: Read objects from the database
Note: Counts features received
Tester_2
    BOOL_OP = OR
    TEST_DESCRIPTION = ""
    TEST_MODE = Automatic
    TEST_CLAUSE = TEST @Value(VERSION) = 2.0.0
    FAILED -> _FeatureReader_Source
    PASSED -> TestFilter
WFS_Reprojector
    SRSNAME = @Value(SRSNAME)
    Reprojector_3_Reprojected -> AttributeFilter_4
    Reprojector_2_Reprojected -> AttributeFilter_4
Note: Ulike GML-writere for ulike WFS-versjoner
AttributeFilter_4
    ATTR_NAME = VERSION
    ATTR_VALUES = <EMPTY>,<MISSING>,<NULL>,<UNFILTERED>,1.0.0,1.1.0
    1.1.0 -> GML3.1 (writer GML_2)
    1.0.0 -> GML2 (writer GML2_1)
Note: WFS 1.0.0
GML2 (writer GML2_1)
Note: WFS 1.1.0
GML3.1 (writer GML_2)

Bookmark: Filter as SQL
WFS_FILTER_CREATOR
    FILTER = @Value(FILTER)
    FeatureMerger_2_Merged -> Tester_2
    FeatureMerger_2_NotMerged -> Tester_2

Bookmark: Need to replace this with SQLCreator
_FeatureReader_Source: FeatureReader
    POSTGIS_USE_TRUE_POSTGIS_TYPES = yes
    POSTGIS_CLIP_TO_ENVELOPE = NO
    POSTGIS_DISABLE_COLLECTION_SPLITTING = yes
    POSTGIS_PORT = 5432
    COMBINE_GEOM = Use Result
    ATTR_ACCUM_MODE = Merge Initiator and Result
    DATASET = geonor01tst
    POSTGIS_QUERY_FEATURE_TYPES_FOR_MERGE_FILTERS = Yes
    POSTGIS_HOST = Nnridb504
    FEATURETYPES_RADIO = ATTR_NAME
    POSTGIS_SCHEMALIST = dekningsoversikt
    ATTR_NAME = _types
    ATTR_CONFLICT_RES = Use Result
    POSTGIS_PASSWORD =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
    INTERACT = Envelope Intersect
    FORMAT = POSTGIS
    POSTGIS_USE_SEARCH_ENVELOPE = NO
    WHERE = @Value(_where)
    POSTGIS_USER_NAME = geonortst
    <OTHER> -> Tester_9
    <OTHER> -> Counter_2
    INITIATOR -> Counter_2

Bookmark: Limit number of features returned
Tester_9
    BOOL_OP = OR
    TEST_DESCRIPTION = ""
    TEST_MODE = Automatic
    TEST_CLAUSE:
      TEST Teller ATTRIBUTE_IS_EMPTY ""
      TEST Teller ATTRIBUTE_IS_MISSING ""
      TEST Teller ATTRIBUTE_VALUE_NULL ""
    FAILED -> Counter
    PASSED -> Sampler
Sampler
    RATE = $(MAX_FEATURES)
    SAMPLE_TYPE_LONG = First N Features
    SAMPLED -> WFS_Reprojector
Counter
    DOMAIN = counter
    CNT_ATTR = _count
    SCOPE = Global
    START = 0
    -> Tester_8
Tester_8
    BOOL_OP = OR
    TEST_DESCRIPTION = ""
    TEST_MODE = Automatic
    TEST_CLAUSE = TEST @Value(_count) < @Value(Teller)
    PASSED -> WFS_Reprojector

Bookmark: WFS 2.0 GML with Application Schema
TestFilter
    TEST_LIST = BOOL_OP,OR,COMPOSITE_TEST,<Unused>,TEST_CLAUSE,"TEST @Value(_types) = KpOmråde",@Value(_types) = KpOmråde,BOOL_OP,OR,COMPOSITE_TEST,<Unused>,TEST_CLAUSE,"TEST @Value(_types) = RpOmråde",RpOmråde
    DEFAULT_VALUE = <UNFILTERED>
    <UNFILTERED> -> FeatureReader_2
    @Value(_types) = KpOmråde -> FeatureReader_3
    RpOmråde -> FeatureReader_2
    <UNFILTERED> -> FeatureReader_3

Bookmark: Joining in related data
FeatureReader_3
    POSTGIS_USE_TRUE_POSTGIS_TYPES = yes
    POSTGIS_CLIP_TO_ENVELOPE = NO
    POSTGIS_DISABLE_COLLECTION_SPLITTING = yes
    POSTGIS_PORT = 5432
    COMBINE_GEOM = Use Result
    ATTR_ACCUM_MODE = Only Use Result
    DATASET = geonor01tst
    POSTGIS_QUERY_FEATURE_TYPES_FOR_MERGE_FILTERS = Yes
    ATTRIBUTES = planomriss.kpomrade,"objid,objtype,landkode,fylkesnr,komm,planid,ikrafttredelsesdato,kunngjoringsdato,lovreferanse,lovreferansebeskrivelse,opprinneligadministrativenhet,opprinneligplanid,planbestemmelse,plannavn,planstatus,plantype,vedtakendeligplandato"
    POSTGIS_HOST = nnridb504
    FEATURETYPES_RADIO = FEATURETYPES
    OUTPUT_FEATURES_DISPLAY = Based on Connections
    POSTGIS_SCHEMALIST = planomriss
    POSTGIS_PASSWORD =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
    INTERACT = Intersects
    FORMAT = POSTGIS
    FEATURETYPES = planomriss.kpomrade
    POSTGIS_USE_SEARCH_ENVELOPE = NO
    WHERE = @Value(_where)
    POSTGIS_USER_NAME = geonortst
    planomriss.kpomrade -> FeatureMerger_2 [input 1]
    planomriss.kpomrade -> Tester_5
    planomriss.kpomrade -> Counter_2
    INITIATOR -> Counter_2
Tester_5
    BOOL_OP = AND
    TEST_DESCRIPTION = ""
    TEST_MODE = Automatic
    TEST_CLAUSE:
      TEST _clipper_file ATTRIBUTE_IS_EMPTY ""
      TEST _clippercoords ATTRIBUTE_IS_EMPTY ""
      TEST _fnr ATTRIBUTE_IS_EMPTY ""
      TEST _knr ATTRIBUTE_IS_EMPTY ""
    FAILED -> Aggregator
    PASSED -> Sampler_5
Aggregator
    CONCAT_ATTRS = objid
    MODE = Attributes Only
    ACCUM_ATTRS_NAME = No
    ORDERED = No
    SEP = ,
    AGGREGATE -> AttributeCreator_2
AttributeCreator_2
    ATTR_LIST = sql,select * from planomriss.sosi_objekt_planomrade_kp where objid in (@Value(objid));
    -> SQLExecutor
Sampler_5
    RATE = 1
    SAMPLE_TYPE_LONG = First N Features
    SAMPLED -> AttributeCreator_11
AttributeCreator_11
    ATTR_LIST = sql,select * from planomriss.sosi_objekt_planomrade_kp;
    -> SQLExecutor
SQLExecutor
    POSTGRES_QUERY_FEATURE_TYPES_FOR_MERGE_FILTERS = Yes
    POSTGRES_HOST = $(PG_HOST)
    POSTGRES_PASSWORD = $(PG_PWD)
    POSTGRES_USER_NAME = $(PG_USER)
    SQL_STATEMENT = @Value(sql)
    EXPOSED_ATTRIBUTE_LIST = forstedigitaliseringsdato,informasjon,kpomrade_fk,link,objid,oppdateringsdato,prosess_historie
    POSTGRES_PORT = $(PG_PORT)
    COMBINE_GEOM = Initiator Geometry Only
    COMBINE_ATTRS = Result Attributes Only
    FORMAT = POSTGRES
    DATASET = $(PG_DB)
    RESULT -> FeatureMerger_2 [input 2]
FeatureMerger_2
    ATTR_CONFLICT_RES = Use Requestor
    ATTR_ACCUM_MODE = Merge Supplier
    IGNORE_NULLS = No
    MERGE_TYPE = Attributes Only
    LIST_NAME = _list
    SUPPLIERS_FIRST = No
    GEOM_TYPE = Build Polygons
    PROCESS_DUPS = Yes
    JOIN_KEYS = @Value(objid) @Value(kpomrade_fk) AUTO
    MERGED -> AttributeRenamer_7
FeatureReader_2
    POSTGIS_USE_TRUE_POSTGIS_TYPES = yes
    POSTGIS_CLIP_TO_ENVELOPE = NO
    POSTGIS_DISABLE_COLLECTION_SPLITTING = yes
    POSTGIS_PORT = 5432
    COMBINE_GEOM = Use Result
    ATTR_ACCUM_MODE = Only Use Result
    DATASET = geonor01tst
    POSTGIS_QUERY_FEATURE_TYPES_FOR_MERGE_FILTERS = Yes
    ATTRIBUTES = planomriss.kpomrade,"objid,objtype,landkode,fylkesnr,komm,planid,ikrafttredelsesdato,kunngjoringsdato,lovreferanse,lovreferansebeskrivelse,opprinneligadministrativenhet,opprinneligplanid,planbestemmelse,plannavn,planstatus,plantype,vedtakendeligplandato",planomriss.rpomrade,"objid,objtype,landkode,fylkesnr,komm,planid,forslagsstillertype,gjennomforingsfrist,ikrafttredelsesdato,kunngjoringsdato,lovreferanse,lovreferansebeskrivelse,opprinneligadministrativenhet,opprinneligplanid,planbestemmelse,plannavn,planstatus,plantype,vedtakendeligplandato,vertikalniva"
    POSTGIS_HOST = nnridb504
    FEATURETYPES_RADIO = FEATURETYPES
    OUTPUT_FEATURES_DISPLAY = Based on Connections
    POSTGIS_SCHEMALIST = planomriss
    POSTGIS_PASSWORD =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
    INTERACT = Intersects
    FORMAT = POSTGIS
    FEATURETYPES = planomriss.kpomrade planomriss.rpomrade
    POSTGIS_USE_SEARCH_ENVELOPE = NO
    WHERE = @Value(_where)
    POSTGIS_USER_NAME = geonortst
    planomriss.rpomrade -> FeatureMerger_3 [input 1]
    planomriss.rpomrade -> Tester_7
    planomriss.rpomrade -> Counter_2
    INITIATOR -> Counter_2
Tester_7
    BOOL_OP = AND
    TEST_DESCRIPTION = ""
    TEST_MODE = Automatic
    TEST_CLAUSE:
      TEST _clipper_file ATTRIBUTE_IS_EMPTY ""
      TEST _clippercoords ATTRIBUTE_IS_EMPTY ""
      TEST _fnr ATTRIBUTE_IS_EMPTY ""
      TEST _knr ATTRIBUTE_IS_EMPTY ""
    FAILED -> Aggregator_3
    PASSED -> Sampler_3
Aggregator_3
    CONCAT_ATTRS = objid
    MODE = Attributes Only
    ACCUM_ATTRS_NAME = No
    ORDERED = No
    SEP = ,
    AGGREGATE -> AttributeCreator_3
AttributeCreator_3
    ATTR_LIST = sql,select * from planomriss.sosi_objekt_planomrade_rp where objid in (@Value(objid));
    -> SQLExecutor_3
Sampler_3
    RATE = 1
    SAMPLE_TYPE_LONG = First N Features
    SAMPLED -> AttributeCreator_9
AttributeCreator_9
    ATTR_LIST = sql,select * from planomriss.sosi_objekt_planomrade_rp;
    -> SQLExecutor_3
SQLExecutor_3
    POSTGRES_HOST = $(PG_HOST)
    POSTGRES_QUERY_FEATURE_TYPES_FOR_MERGE_FILTERS = Yes
    POSTGRES_PASSWORD = $(PG_PWD)
    POSTGRES_USER_NAME = $(PG_USER)
    SQL_STATEMENT = @Value(sql)
    EXPOSED_ATTRIBUTE_LIST = forstedigitaliseringsdato,informasjon,link,objid,oppdateringsdato,prosess_historie,rpomrade_fk
    POSTGRES_PORT = $(PG_PORT)
    COMBINE_GEOM = Initiator Geometry Only
    COMBINE_ATTRS = Result Attributes Only
    FORMAT = POSTGRES
    DATASET = $(PG_DB)
    RESULT -> FeatureMerger_3 [input 2]
FeatureMerger_3
    ATTR_CONFLICT_RES = Use Requestor
    ATTR_ACCUM_MODE = Merge Supplier
    IGNORE_NULLS = Yes
    MERGE_TYPE = Attributes Only
    LIST_NAME = _list
    SUPPLIERS_FIRST = No
    GEOM_TYPE = Build Polygons
    PROCESS_DUPS = Yes
    JOIN_KEYS = @Value(objid) @Value(rpomrade_fk) AUTO
    MERGED -> AttributeRenamer_6

Bookmark: Kommuneplan
AttributeRenamer_7
    ATTR_LIST = kunngjoringsdato,kunngjøringsdato,,vedtakendeligplandato,vedtakEndeligPlanDato,,komm,arealplanId.NasjonalArealplanId.administrativEnhet.AdministrativEnhetskode.kommunenummer,,lovreferansebeskrivelse,lovreferanseBeskrivelse,,planid,arealplanId.NasjonalArealplanId.planidentifikasjon,,forstedigitaliseringsdato,førsteDigitaliseringsdato,
    -> AttributeValueMapper_7
AttributeValueMapper_7
    VAL_ATTR = plantype
    LUT = 20,Kommuneplanens arealdel,21,Kommunedelplan,22,Mindre endring av kommune(del)plan
    SRC = plantype
    DIRECTION = Forward (Source To Destination)
    -> AttributeValueMapper_8
AttributeValueMapper_8
    VAL_ATTR = planbestemmelse
    LUT = 1,Med bestemmelser som egen tekst,2,Uten bestemmelser,3,Uten bestemmelser,4,Med bestemmelser som egen tekst
    SRC = planbestemmelse
    DIRECTION = Forward (Source To Destination)
    DEFAULT_VALUE = @Value(planbestemmelse)
    -> AttributeValueMapper_10
AttributeValueMapper_10
    VAL_ATTR = lovreferanse
    LUT = 1,Før BL 1924,2,BL 1924,3,BL 1965,4,PBL 1985,5,PBL 1985 eller før,6,PBL 2008
    SRC = lovreferanse
    DIRECTION = Forward (Source To Destination)
    DEFAULT_VALUE = other:
    -> AttributeValueMapper_9
AttributeValueMapper_9
    VAL_ATTR = planstatus
    LUT = 1,Planlegging igangsatt,2,Planforslag,3,Endelig vedtatt arealplan,4,Opphevet,5,Utgått/erstattet,6,Vedtatt plan med utsatt rettsvirkning,7,Endelig vedtatt plan underlagt tidsbegrensning,8,Overstyrt
    SRC = planstatus
    DIRECTION = Forward (Source To Destination)
    -> DateFormatter_2
DateFormatter_2
    SRCFMT = Unknown - Automatic Detection
    DATE_ATTR = ikrafttredelsesdato,kunngjøringsdato,vedtakEndeligPlanDato
    FMT = ISO Date (%Y-%m-%d)
    INVALID_DATE_VALUE = _FME_NO_OP_
    -> DateFormatter_3
DateFormatter_3
    SRCFMT = Unknown - Automatic Detection
    DATE_ATTR = førsteDigitaliseringsdato,oppdateringsdato
    FMT = ISO DateTime (%Y-%m-%dT%H:%M:%S)
    INVALID_DATE_VALUE = _FME_NO_OP_
    -> GeometryPropertySetter_2
GeometryPropertySetter_2
    OVERWRITE_CHOICE = Yes
    SETTYPE_PARAM = Geometry Name
    GEOM_NAME_FIELD = område
    SET -> ListRenamer_2
ListRenamer_2
    LEAVE_ORIG = No
    LIST_COMPONENT_NAMES = forstedigitaliseringsdato,forstedigitaliseringsdato{},informasjon,informasjon{},link,link{},objid,objid{},oppdateringsdato,oppdateringsdato{},prosess_historie,prosesshistorie{},rpomrade_fk,rpomrade_fk{}
    LIST_ACTION = Promote All Subcomponents
    LIST_NAME = _list{}
    -> NullAttributeMapper
NullAttributeMapper
    NULL_TREATMENT = Missing
    ATTRCHOICE = All Attributes
    SOURCE_ATTR_VAL = Null Empty
    -> KpOmråde (writer GML_3)
KpOmråde (writer GML_3)
    attributes: førsteDigitaliseringsdato xml_datetime, oppdateringsdato xml_datetime, prosesshistorie{} xml_buffer, informasjon{} xml_buffer, link{} xml_xml, område xml_geometry, posisjon xml_geometry, arealplanId.NasjonalArealplanId.administrativEnhet.AdministrativEnhetskode.kommunenummer xml_buffer, arealplanId.NasjonalArealplanId.administrativEnhet.AdministrativEnhetskode.kommunenummer.codeSpace xml_buffer, arealplanId.NasjonalArealplanId.administrativEnhet.AdministrativEnhetskode.fylkesnummer xml_buffer, arealplanId.NasjonalArealplanId.administrativEnhet.AdministrativEnhetskode.fylkesnummer.codeSpace xml_buffer, arealplanId.NasjonalArealplanId.administrativEnhet.AdministrativEnhetskode.landskode xml_buffer, arealplanId.NasjonalArealplanId.administrativEnhet.AdministrativEnhetskode.landskode.codeSpace xml_buffer, arealplanId.NasjonalArealplanId.planidentifikasjon xml_buffer, plantype xml_buffer, planstatus xml_buffer, planbestemmelse xml_buffer, lovreferanse xml_buffer, lovreferanseBeskrivelse xml_buffer, ikrafttredelsesdato xml_date, plannavn xml_buffer, vedtakEndeligPlanDato xml_date, kunngjøringsdato xml_date, opprinneligplanid xml_buffer, opprinneligadministrativenhet xml_xml, gml_metaDataProperty{}.about xml_buffer, gml_metaDataProperty{}.nilReason xml_buffer, gml_metaDataProperty{}.gml_remoteSchema xml_buffer, gml_metaDataProperty{}.xlink_href xml_buffer, gml_metaDataProperty{}.gml_GenericMetaData xml_xml,
      gml_metaDataProperty{}.gml_GenericMetaData.gml_id xml_buffer, gml_description xml_buffer, gml_description.nilReason xml_buffer, gml_description.gml_remoteSchema xml_buffer, gml_description.xlink_href xml_buffer, gml_descriptionReference.owns xml_boolean, gml_descriptionReference.nilReason xml_buffer, gml_descriptionReference.gml_remoteSchema xml_buffer, gml_descriptionReference.xlink_href xml_buffer, gml_identifier xml_buffer, gml_identifier.codeSpace xml_buffer, gml_name{} xml_buffer, gml_name{}.codeSpace xml_buffer, gml_boundedBy xml_geometry, gml_location xml_geometry

Bookmark: Errorhandling 0 features returned
Counter_2
    DOMAIN = counter
    CNT_ATTR = _count
    SCOPE = Global
    START = 0
    -> StatisticsCalculator_2
StatisticsCalculator_2
    PASS_THROUGH = No
    COUNT_ATTR = FeatureCount
    STATS_ATTR = _count
    STATISTICS -> Tester
Tester
    BOOL_OP = OR
    TEST_DESCRIPTION = ""
    TEST_MODE = Automatic
    TEST_CLAUSE = TEST @Value(FeatureCount) = 1
    PASSED -> XMLTemplater
XMLTemplater
    RESULT_ATTRIBUTE = text_line_data
    ROOT_QUERY_EXPR:
      <ows:ExceptionReport xmlns:ows="http://www.opengis.net/ows/1.1" xmlns:xsi="http://www.w3.org/2001/XMLSchema-instance" xsi:schemaLocation="http://www.opengis.net/ows/1.1 http://schemas.opengis.net/ows/1.1.0/owsExceptionReport.xsd" version="2.0.0">
        <ows:Exception exceptionCode="NotFound" locator="request">
          <ows:ExceptionText>No features returned.</ows:ExceptionText>
        </ows:Exception>
      </ows:ExceptionReport>
    VISIBLE_QUERY_VALIDATE = Yes
    OUTPUT_XML_HEADER = Yes
    -> text_line (writer TEXTLINE_1)

Bookmark: Reguleringsplan
AttributeRenamer_6
    ATTR_LIST = vertikalniva,vertikalnivå,,lovreferansebeskrivelse,lovreferanseBeskrivelse,,gjennomforingsfrist,gjennomføringsfrist,,vedtakendeligplandato,vedtakEndeligPlanDato,,forslagsstillertype,forslagsstillerType,,planid,arealplanId.NasjonalArealplanId.planidentifikasjon,,komm,arealplanId.NasjonalArealplanId.administrativEnhet.AdministrativEnhetskode.kommunenummer,,kunngjoringsdato,kunngjøringsdato,,forstedigitaliseringsdato,førsteDigitaliseringsdato,
    -> DateFormatter
GeometryPropertySetter
    OVERWRITE_CHOICE = No
    SETTYPE_PARAM = Geometry Name
    GEOM_NAME_FIELD = område
    SET -> ListRenamer
ListRenamer
    LEAVE_ORIG = No
    LIST_COMPONENT_NAMES = forstedigitaliseringsdato,forstedigitaliseringsdato{},informasjon,informasjon{},link,link{},objid,objid{},oppdateringsdato,oppdateringsdato{},prosess_historie,prosesshistorie{},rpomrade_fk,rpomrade_fk{}
    LIST_ACTION = Promote All Subcomponents
    LIST_NAME = _list{}
    -> NullAttributeMapper_3
NullAttributeMapper_3
    NULL_TREATMENT = Missing
    ATTRCHOICE = All Attributes
    SOURCE_ATTR_VAL = Empty Null
    -> RpOmråde (writer GML_3)
RpOmråde (writer GML_3)
    attributes: førsteDigitaliseringsdato xml_datetime, oppdateringsdato xml_datetime, prosesshistorie{} xml_buffer, informasjon{} xml_buffer, link{} xml_xml, område xml_geometry, posisjon xml_geometry, arealplanId.NasjonalArealplanId.administrativEnhet.AdministrativEnhetskode.kommunenummer xml_buffer, arealplanId.NasjonalArealplanId.administrativEnhet.AdministrativEnhetskode.kommunenummer.codeSpace xml_buffer, arealplanId.NasjonalArealplanId.administrativEnhet.AdministrativEnhetskode.fylkesnummer xml_buffer, arealplanId.NasjonalArealplanId.administrativEnhet.AdministrativEnhetskode.fylkesnummer.codeSpace xml_buffer, arealplanId.NasjonalArealplanId.administrativEnhet.AdministrativEnhetskode.landskode xml_buffer, arealplanId.NasjonalArealplanId.administrativEnhet.AdministrativEnhetskode.landskode.codeSpace xml_buffer, arealplanId.NasjonalArealplanId.planidentifikasjon xml_buffer, plantype xml_buffer, planstatus xml_buffer, plannavn xml_buffer, planbestemmelse xml_buffer, ikrafttredelsesdato xml_date, vertikalnivå xml_buffer, lovreferanse xml_buffer, lovreferanseBeskrivelse xml_buffer, gjennomføringsfrist xml_date, forslagsstillerType xml_char(9), vedtakEndeligPlanDato xml_date, kunngjøringsdato xml_date, opprinneligplanid xml_buffer, opprinneligadministrativenhet xml_buffer

Bookmark: Datoformatering
DateFormatter
    SRCFMT = Unknown - Automatic Detection
    DATE_ATTR = ikrafttredelsesdato,kunngjøringsdato,vedtakEndeligPlanDato,gjennomføringsfrist
    FMT = ISO Date (%Y-%m-%d)
    INVALID_DATE_VALUE = _FME_NO_OP_
    -> DateFormatter_4
DateFormatter_4
    SRCFMT = Unknown - Automatic Detection
    DATE_ATTR = førsteDigitaliseringsdato,oppdateringsdato
    FMT = ISO DateTime (%Y-%m-%dT%H:%M:%S)
    INVALID_DATE_VALUE = _FME_NO_OP_
    -> AttributeValueMapper

Bookmark: Koder til tekst
AttributeValueMapper
    VAL_ATTR = lovreferanse
    LUT = 1,Før BL 1924,2,BL 1924,3,BL 1965,4,PBL 1985,5,PBL 1985 eller før,6,PBL 2008
    SRC = lovreferanse
    DIRECTION = Forward (Source To Destination)
    -> AttributeValueMapper_2
AttributeValueMapper_2
    VAL_ATTR = plantype
    LUT = 30,Eldre reguleringsplan,31,Mindre reguleringsendring,32,Bebyggelsesplan ihht. Reguleringsplan,33,Bebyggelsesplan ihht kommunepl. arealdel,34,Områderegulering,35,Detaljregulering
    SRC = plantype
    DIRECTION = Forward (Source To Destination)
    -> AttributeValueMapper_3
AttributeValueMapper_3
    VAL_ATTR = planstatus
    LUT = 1,Planlegging igangsatt,2,Planforslag,3,Endelig vedtatt arealplan,4,Opphevet,5,Utgått/erstattet,6,Vedtatt plan med utsatt rettsvirkning,7,Endelig vedtatt plan underlagt tidsbegrensning,8,Overstyrt
    SRC = planstatus
    DIRECTION = Forward (Source To Destination)
    DEFAULT_VALUE = other: @Value(planstatus)Ukjent
    -> AttributeValueMapper_4
AttributeValueMapper_4
    VAL_ATTR = planbestemmelse
    LUT = 3,Planbestemmelser fremgår kun av kartet,4,Planbestemmelser både kart og tekst,1,Planbestemmelser både kart og tekst,2,Planbestemmelser fremgår kun av kartet
    SRC = planbestemmelse
    DIRECTION = Forward (Source To Destination)
    DEFAULT_VALUE = other: Ukjent
    -> AttributeValueMapper_5
AttributeValueMapper_5
    VAL_ATTR = vertikalnivå
    LUT = 1,Under grunnen (tunnel),2,På grunnen/vannoverflate,3,Over grunnen (bru),4,På bunnen (vann/sjø),5,I vannsøylen
    SRC = vertikalnivå
    DIRECTION = Forward (Source To Destination)
    -> AttributeValueMapper_6
AttributeValueMapper_6
    VAL_ATTR = forslagsstillerType
    LUT = 1,offentlig,2,privat
    SRC = forslagsstillerType
    DIRECTION = Forward (Source To Destination)
    -> GeometryPropertySetter

FME custom transformer WFS_FILTER_CREATOR

Parameters:
- FILTER = @Value(FILTER)

BulkAttributeRemover_Input (input)
    -> BulkAttributeRemover
Note: "Renser" XML-attributter
BulkAttributeRemover
    ATTR_EXP = xml_
    -> Tester_6
    -> FeatureMerger_2 [input 1]
Note: Sjekker om filter er satt
Tester_6
    BOOL_OP = OR
    TEST_DESCRIPTION = ""
    TEST_MODE = Automatic
    TEST_CLAUSE:
      TEST FILTER ATTRIBUTE_VALUE_NULL ""
      TEST FILTER ATTRIBUTE_IS_EMPTY ""
      TEST FILTER ATTRIBUTE_IS_MISSING ""
    PASSED -> AttributeCreator_5
    FAILED -> XMLFragmenter_2
Note: Trekker ut filterspørringe
XMLFragmenter_2
    ATTRIBUTE_XML = FILTER
    NEW_ATTRIBUTES = PropertyName Literal LowerBoundary.Literal UpperBoundary.Literal
    XML_SOURCE_TYPE = Attribute with XML document
    MERGE_ATTRS = Yes
    EMBEDDED_EXPRESSIONS = Filter/*
    FLATTEN_OPTIONS = <structure separator="." map-empty-elements="yes" matched-prefix="attributes" matched-attributes="yes" cardinality="+{?}" structure-prefix="" child-position-attribute="" except-expression="" ui-mode="basic" matched-ancestor-attributes=""/>
    FRAGMENTS -> AttributeValueMapper
AttributeValueMapper
    VAL_ATTR = PropertyName
    LUT = kommunenummer,komm
    SRC = PropertyName
    DIRECTION = Forward (Source To Destination)
    DEFAULT_VALUE = @Value(PropertyName)
    -> AttributeFilter_7
AttributeFilter_7
    ATTR_NAME = xml_matched_element
    ATTR_VALUES = <EMPTY>,<MISSING>,<NULL>,<UNFILTERED>,PropertyIsEqualTo,PropertyIsNotEqualTo,PropertyIsLessThan,PropertyIsLessThanOrEqualTo,PropertyIsGreaterThan,PropertyIsGreaterThanOrEqualTo,PropertyIsLike,PropertyIsNull,PropertyIsBetween
    PropertyIsEqualTo -> AttributeValueMapper_4
    PropertyIsNull -> AttributeCreator_3
    PropertyIsBetween -> AttributeCreator_4
    PropertyIsNotEqualTo -> AttributeValueMapper_4
    PropertyIsLessThan -> AttributeValueMapper_4
    PropertyIsLessThanOrEqualTo -> AttributeValueMapper_4
    PropertyIsGreaterThan -> AttributeValueMapper_4
    PropertyIsGreaterThanOrEqualTo -> AttributeValueMapper_4
    PropertyIsLike -> AttributeValueMapper_4
    <UNFILTERED> -> AttributeCreator_5
    <NULL> -> AttributeCreator_5
    <MISSING> -> AttributeCreator_5
    <EMPTY> -> AttributeCreator_5
Note: Lager "dummy" where-clause
AttributeCreator_5
    ATTR_LIST = _where,1=1
    -> FeatureMerger_2 [input 2]
Note: Mapper operatorer til SQL
AttributeValueMapper_4
    VAL_ATTR = _operator
    LUT = PropertyIsEqualTo,=,PropertyIsNotEqualTo,<>,PropertyIsLessThan,<,PropertyIsLessThanOrEqualTo,<=,PropertyIsGreaterThan,>,PropertyIsGreaterThanOrEqualTo,>=,PropertyIsLike,LIKE
    SRC = xml_matched_element
    DIRECTION = Forward (Source To Destination)
    -> AttributeCreator_2
Note: Lager where-clause
AttributeCreator_2
    ATTR_LIST = _where,@Value(PropertyName) @Value(_operator) @Value(Literal)
    -> FeatureMerger_2 [input 2]
Note: Lager where-clause
AttributeCreator_3
    ATTR_LIST = _where,@Value(PropertyName) IS NULL
    -> FeatureMerger_2 [input 2]
Note: Lager where-clause
AttributeCreator_4
    ATTR_LIST = _where,@Value(PropertyName) BETWEEN @Value(LowerBoundary.Literal) AND @Value(UpperBoundary.Literal)
    -> FeatureMerger_2 [input 2]
FeatureMerger_2
    ATTR_CONFLICT_RES = Use Requestor
    ATTR_ACCUM_MODE = Merge Supplier
    IGNORE_NULLS = No
    MERGE_TYPE = Attributes Only
    SUPPLIERS_FIRST = No
    PROCESS_DUPS = No
    JOIN_KEYS = 1 1 AUTO
    MERGED -> FeatureMerger_2_Merged (output)
    NOT_MERGED -> FeatureMerger_2_NotMerged (output)
FeatureMerger_2_Merged (output)
FeatureMerger_2_NotMerged (output)

FME custom transformer DescribeFeatureType

Parameters:
- VERSION = @Value(VERSION)
- TYPENAMES = @Value(TYPENAMES)
- TYPENAME = @Value(TYPENAME)
- GML_OUT_TARGET_NS_URI_GML = http://skjema.geonorge.no/SOSI/produktspesifikasjon/   # Target Namespace URI
- GML_OUT_TARGET_NS_PREFIX_GML = app   # Target Namespace Prefix

AttributeExposer_2_Input (input)
    -> AttributeExposer_2
AttributeExposer_2
    ATTR_LIST = fme_feature_type_name,attribute{}.name,attribute{}.fme_type,attribute{}.native_data_type
    -> DuplicateRemover_2
DuplicateRemover_2
    KEYATTR = fme_feature_type_name
    UNIQUE -> AttributeFilter_5
AttributeFilter_5
    ATTR_NAME = VERSION
    ATTR_VALUES = <EMPTY>,<MISSING>,<NULL>,<UNFILTERED>,1.0.0,1.1.0,2.0.0
    1.0.0 -> Tester
    1.1.0 -> Tester_2
    2.0.0 -> Tester_3
Note: Pretty-Print the XML output
XMLFormatter_2
    SCHEMALOC_CLEANUP = No
    XML_OUTPUT_ATTR = text_line_data
    REMOVE_EMPTY_ELEMENT = No
    COLLAPSE_EMPTY_ELEMENT = No
    OUTPUT_ENCODING = utf-8
    XML_INPUT_TYPE = Attribute Specifying XML Text
    XML_OUTPUT_TYPE = Attribute
    REMOVE_ALL_COMMENT = No
    WHITESPACE_HANDLING = Preserve all whitespace
    LIST_NAME = _xml_error
    NAMESPACE_CLEANUP = No
    XML_ATTR_TEXT = DescFeatType
    FORMATTING_CHOICE = Pretty-Print XML
    PASSED -> XMLFormatter_2_Passed (output)
XMLFormatter_2_Passed (output)

Bookmark: WFS 1.0.0
Note: Keep only requested features
Tester
    BOOL_OP = OR
    TEST_DESCRIPTION = ""
    TEST_MODE = Automatic
    TEST_CLAUSE:
      TEST @Value(fme_feature_type_name) IN @Value(TYPENAME)
      TEST @Value(fme_feature_type_name) IN @Value(TYPENAMES)
    PASSED -> ListExploder
    PASSED -> AttributeFilter_8
AttributeFilter_8
    ATTR_NAME = fme_feature_type_name
    ATTR_VALUES = <EMPTY>,<MISSING>,<NULL>,<UNFILTERED>,dekningsoversikt.dekningsoversikt,dsb.brannstasjoner
    dekningsoversikt.dekningsoversikt -> XMLTemplater [input 1]
    dsb.brannstasjoner -> XMLTemplater_11 [input 1]
Note: Explode list of attributes
ListExploder
    MODE = List Elements and Original Attributes
    LIST_ATTR = attribute{}
    LIST_FOUND -> StringSearcher_2
Note: Decimal, String / and other attribtes
StringSearcher_2
    CASE = no
    MATCHED_RESULT_ATTR = _matched_characters
    REGEXP = [(]([0-9]*),([0-9]*)[)]
    STRING_TO_SEARCH = @Value(fme_data_type)
    MATCHED_PARTS_ATTR = _matched_parts
    NOT_MATCHED -> StringSearcher
    MATCHED -> XMLTemplater [input 2]
    MATCHED -> XMLTemplater_10 [input 2]
    MATCHED -> XMLTemplater_11 [input 2]
StringSearcher
    CASE = no
    MATCHED_RESULT_ATTR = _matched_characters
    REGEXP = [(]([0-9]*)[)]
    STRING_TO_SEARCH = @Value(fme_data_type)
    MATCHED_PARTS_ATTR = _matched_parts
    NOT_MATCHED -> AttributeValueMapper
    MATCHED -> XMLTemplater [input 3]
    MATCHED -> XMLTemplater_10 [input 3]
    MATCHED -> XMLTemplater_11 [input 3]
AttributeValueMapper
    VAL_ATTR = wfs_data_type
    LUT = fme_buffer,string,fme_char,string,fme_int64,long,fme_uint64,unsignedLong,fme_int32,int,fme_uint32,unsignedInt,fme_int16,short,fme_uint16,unsignedShort,fme_uint8,unsignedByte,fme_real32,float,fme_real64,double,fme_boolean,boolean,fme_datetime,string,fme_date,string,fme_time,string,fme_int32,PRIKEY,int,fme_int32,BTREE,int
    SRC = fme_data_type
    DIRECTION = Forward (Source To Destination)
    -> XMLTemplater_11 [input 4]
    -> XMLTemplater_10 [input 4]
    -> XMLTemplater [input 4]
Note: Create feature type areas
XMLTemplater
    RESULT_ATTRIBUTE = _result
    GROUP_BY = fme_feature_type_name
    ROOT_QUERY_EXPR:
      	<complexType xmlns="http://www.w3.org/2001/XMLSchema" name="{fme:get-attribute("fme_feature_type_name")}Type">
      		<complexContent>
      			<extension base="gml:AbstractFeatureType">
      				<sequence>

                          {fme:process-features("DECIMAL")}
                          {fme:process-features("COMPLEX")}
                          {fme:process-features("SIMPLE")}

       <!--                   <element name="lineStringProperty" type="gml:GeometryPropertyType"></element>
                          <element name="multiLineStringProperty" type="gml:GeometryPropertyType"></element>
                          <element name="polygonProperty" type="gml:GeometryPropertyType"></element>
                          <element name="multiPolygonProperty" type="gml:GeometryPropertyType"></element>
                          <element name="multiPointProperty" type="gml:GeometryPropertyType"></element>-->
      					<choice>
      						<element ref="gml:lineStringProperty" type="gml:GeometryPropertyType"></element>
      						<element ref="gml:multiLineStringProperty" type="gml:GeometryPropertyType"></element>
      						<element ref="gml:polygonProperty" type="gml:GeometryPropertyType"></element>
      						<element ref="gml:multiPolygonProperty" type="gml:GeometryPropertyType"></element>
      						<element ref="gml:pointProperty" type="gml:GeometryPropertyType"></element>
      						<element ref="gml:multiPointProperty" type="gml:GeometryPropertyType"></element>
      					</choice>
                          <element name="polygonProperty" type="gml:GeometryPropertyType"></element>
                      </sequence>
      			</extension>
      		</complexContent>
      	</complexType>
    SIMPLE_QUERY_EXPR = <element xmlns="http://www.w3.org/2001/XMLSchema" minOccurs="0" name="{fme:get-attribute("name")}" type="{fme:get-attribute("wfs_data_type")}"></element>
    DECIMAL_QUERY_EXPR:
      					<element xmlns="http://www.w3.org/2001/XMLSchema" minOccurs="0" name="{fme:get-attribute("name")}">
      						<simpleType>
      							<restriction base="decimal">
      								<totalDigits value="{fme:get-attribute("_matched_parts{0}")}"></totalDigits>
      								<fractionDigits value="{fme:get-attribute("_matched_parts{1}")}"></fractionDigits>
      							</restriction>
      						</simpleType>
      					</element>
    VISIBLE_QUERY_VALIDATE = Yes
    COMPLEX_QUERY_EXPR:
      					<element xmlns="http://www.w3.org/2001/XMLSchema" minOccurs="0" name="{fme:get-attribute("name")}">
      						<simpleType>
      							<restriction base="string">
      								<maxLength value="{fme:get-attribute("_matched_parts{0}")}"></maxLength>
      							</restriction>
      						</simpleType>
      					</element>
    CONSECUTIVE_GROUPS = No
    OUTPUT_XML_HEADER = Yes
    -> Sampler
    -> XMLTemplater_3 [input 2]
Note: Create feature type lines
XMLTemplater_10
    RESULT_ATTRIBUTE = _result
    GROUP_BY = fme_feature_type_name
    ROOT_QUERY_EXPR:
      	<complexType xmlns="http://www.w3.org/2001/XMLSchema" name="{fme:get-attribute("fme_feature_type_name")}Type">
      		<complexContent>
      			<extension base="gml:AbstractFeatureType">
      				<sequence>

                          {fme:process-features("DECIMAL")}
                          {fme:process-features("COMPLEX")}
                          {fme:process-features("SIMPLE")}

       <!--                   <element name="lineStringProperty" type="gml:GeometryPropertyType"></element>
                          <element name="multiLineStringProperty" type="gml:GeometryPropertyType"></element>
                          <element name="polygonProperty" type="gml:GeometryPropertyType"></element>
                          <element name="multiPolygonProperty" type="gml:GeometryPropertyType"></element>
                          <element name="multiPointProperty" type="gml:GeometryPropertyType"></element>-->
      					<choice>
      						<element ref="gml:lineStringProperty" type="gml:GeometryPropertyType"></element>
      						<element ref="gml:multiLineStringProperty" type="gml:GeometryPropertyType"></element>
      						<element ref="gml:polygonProperty" type="gml:GeometryPropertyType"></element>
      						<element ref="gml:multiPolygonProperty" type="gml:GeometryPropertyType"></element>
      						<element ref="gml:pointProperty" type="gml:GeometryPropertyType"></element>
      						<element ref="gml:multiPointProperty" type="gml:GeometryPropertyType"></element>
      					</choice>
                          <element name="lineStringProperty" type="gml:GeometryPropertyType"></element>
                      </sequence>
      			</extension>
      		</complexContent>
      	</complexType>
    SIMPLE_QUERY_EXPR = <element xmlns="http://www.w3.org/2001/XMLSchema" minOccurs="0" name="{fme:get-attribute("name")}" type="{fme:get-attribute("wfs_data_type")}"></element>
    DECIMAL_QUERY_EXPR:
      					<element xmlns="http://www.w3.org/2001/XMLSchema" minOccurs="0" name="{fme:get-attribute("name")}">
      						<simpleType>
      							<restriction base="decimal">
      								<totalDigits value="{fme:get-attribute("_matched_parts{0}")}"></totalDigits>
      								<fractionDigits value="{fme:get-attribute("_matched_parts{1}")}"></fractionDigits>
      							</restriction>
      						</simpleType>
      					</element>
    VISIBLE_QUERY_VALIDATE = Yes
    COMPLEX_QUERY_EXPR:
      					<element xmlns="http://www.w3.org/2001/XMLSchema" minOccurs="0" name="{fme:get-attribute("name")}">
      						<simpleType>
      							<restriction base="string">
      								<maxLength value="{fme:get-attribute("_matched_parts{0}")}"></maxLength>
      							</restriction>
      						</simpleType>
      					</element>
    CONSECUTIVE_GROUPS = No
    OUTPUT_XML_HEADER = Yes
    -> Sampler
    -> XMLTemplater_3 [input 2]
Note: Create feature type points
XMLTemplater_11
    RESULT_ATTRIBUTE = _result
    GROUP_BY = fme_feature_type_name
    ROOT_QUERY_EXPR:
      	<complexType xmlns="http://www.w3.org/2001/XMLSchema" name="{fme:get-attribute("fme_feature_type_name")}Type">
      		<complexContent>
      			<extension base="gml:AbstractFeatureType">
      				<sequence>

                          {fme:process-features("DECIMAL")}
                          {fme:process-features("COMPLEX")}
                          {fme:process-features("SIMPLE")}

       <!--                   <element name="lineStringProperty" type="gml:GeometryPropertyType"></element>
                          <element name="multiLineStringProperty" type="gml:GeometryPropertyType"></element>
                          <element name="polygonProperty" type="gml:GeometryPropertyType"></element>
                          <element name="multiPolygonProperty" type="gml:GeometryPropertyType"></element>
                          <element name="multiPointProperty" type="gml:GeometryPropertyType"></element>-->
      					<choice>
      						<element ref="gml:lineStringProperty" type="gml:GeometryPropertyType"></element>
      						<element ref="gml:multiLineStringProperty" type="gml:GeometryPropertyType"></element>
      						<element ref="gml:polygonProperty" type="gml:GeometryPropertyType"></element>
      						<element ref="gml:multiPolygonProperty" type="gml:GeometryPropertyType"></element>
      						<element ref="gml:pointProperty" type="gml:GeometryPropertyType"></element>
      						<element ref="gml:multiPointProperty" type="gml:GeometryPropertyType"></element>
      					</choice>
                          <element name="pointProperty" type="gml:GeometryPropertyType"></element>
                      </sequence>
      			</extension>
      		</complexContent>
      	</complexType>
    SIMPLE_QUERY_EXPR = <element xmlns="http://www.w3.org/2001/XMLSchema" minOccurs="0" name="{fme:get-attribute("name")}" type="{fme:get-attribute("wfs_data_type")}"></element>
    DECIMAL_QUERY_EXPR:
      					<element xmlns="http://www.w3.org/2001/XMLSchema" minOccurs="0" name="{fme:get-attribute("name")}">
      						<simpleType>
      							<restriction base="decimal">
      								<totalDigits value="{fme:get-attribute("_matched_parts{0}")}"></totalDigits>
      								<fractionDigits value="{fme:get-attribute("_matched_parts{1}")}"></fractionDigits>
      							</restriction>
      						</simpleType>
      					</element>
    VISIBLE_QUERY_VALIDATE = Yes
    COMPLEX_QUERY_EXPR:
      					<element xmlns="http://www.w3.org/2001/XMLSchema" minOccurs="0" name="{fme:get-attribute("name")}">
      						<simpleType>
      							<restriction base="string">
      								<maxLength value="{fme:get-attribute("_matched_parts{0}")}"></maxLength>
      							</restriction>
      						</simpleType>
      					</element>
    CONSECUTIVE_GROUPS = No
    OUTPUT_XML_HEADER = Yes
    -> Sampler
    -> XMLTemplater_3 [input 2]
Sampler
    RATE = 1
    SAMPLE_TYPE_LONG = First N Features
    SAMPLED -> XMLTemplater_3 [input 1]
Note: Create DescribeFeatures
XMLTemplater_3
    RESULT_ATTRIBUTE = DescFeatType
    ROOT_QUERY_EXPR:
      <?xml version="1.0" encoding="UTF-8"?>
      <schema xmlns:xlink="http://www.w3.org/1999/xlink" xmlns:$(GML_OUT_TARGET_NS_PREFIX_GML)="$(GML_OUT_TARGET_NS_URI_GML)" xmlns:gml="http://www.opengis.net/gml" xmlns="http://www.w3.org/2001/XMLSchema" elementFormDefault="qualified" targetNamespace="$(GML_OUT_TARGET_NS_URI_GML)">
      	<import namespace="http://www.opengis.net/gml" schemaLocation="http://schemas.opengis.net/gml/2.1.2/feature.xsd"></import>

          {fme:process-features("ELEMENTS")}

      </schema>
    VISIBLE_QUERY_VALIDATE = Yes
    OUTPUT_XML_HEADER = Yes
    ELEMENTS_QUERY_EXPR:
      	<element xmlns="http://www.w3.org/2001/XMLSchema" name="{fme:get-attribute("fme_feature_type_name")}" substitutionGroup="gml:_Feature" type="$(GML_OUT_TARGET_NS_PREFIX_GML):{fme:get-attribute("fme_feature_type_name")}Type"></element>
          ,{fme:get-xml-attribute("_result")}
    -> XMLFormatter_2

Bookmark: WFS 1.1.0
Note: Keep only requested features
Tester_2
    BOOL_OP = OR
    TEST_DESCRIPTION = ""
    TEST_MODE = Automatic
    TEST_CLAUSE:
      TEST $(GML_OUT_TARGET_NS_PREFIX_GML):@Value(fme_feature_type_name) IN @Value(TYPENAME)
      TEST $(GML_OUT_TARGET_NS_PREFIX_GML):@Value(fme_feature_type_name) IN @Value(TYPENAMES)
    PASSED -> ListExploder_2
    PASSED -> XMLTemplater_6 [input 1]
Note: Explode list of attributes
ListExploder_2
    MODE = List Elements and Original Attributes
    LIST_ATTR = attribute{}
    LIST_FOUND -> StringSearcher_4
Note: Decimal, String / and other attribtes
StringSearcher_4
    CASE = no
    MATCHED_RESULT_ATTR = _matched_characters
    REGEXP = [(]([0-9]*),([0-9]*)[)]
    STRING_TO_SEARCH = @Value(fme_data_type)
    MATCHED_PARTS_ATTR = _matched_parts
    NOT_MATCHED -> StringSearcher_3
    MATCHED -> XMLTemplater_6 [input 2]
StringSearcher_3
    CASE = no
    MATCHED_RESULT_ATTR = _matched_characters
    REGEXP = [(]([0-9]*)[)]
    STRING_TO_SEARCH = @Value(fme_data_type)
    MATCHED_PARTS_ATTR = _matched_parts
    NOT_MATCHED -> AttributeValueMapper_2
    MATCHED -> XMLTemplater_6 [input 3]
AttributeValueMapper_2
    VAL_ATTR = wfs_data_type
    LUT = fme_buffer,string,fme_char,string,fme_int64,long,fme_uint64,unsignedLong,fme_int32,int,fme_uint32,unsignedInt,fme_int16,short,fme_uint16,unsignedShort,fme_uint8,unsignedByte,fme_real32,float,fme_real64,double,fme_boolean,boolean,fme_datetime,string,fme_date,string,fme_time,string,fme_int32,PRIKEY,int,fme_int32,BTREE,int
    SRC = native_data_type
    DIRECTION = Forward (Source To Destination)
    DEFAULT_VALUE = @Value(native_data_type)
    -> XMLTemplater_6 [input 4]
Note: Create feature type
XMLTemplater_6
    RESULT_ATTRIBUTE = _result
    GROUP_BY = fme_feature_type_name
    ROOT_QUERY_EXPR:
      	<complexType name="{fme:get-attribute("fme_feature_type_name")}Type">
      		<complexContent>
      			<extension base="gml:AbstractFeatureType">
      				<sequence>

                          {fme:process-features("DECIMAL")}
                          {fme:process-features("COMPLEX")}
                          {fme:process-features("SIMPLE")}

      					<element minOccurs="0" ref="gml:curveProperty"></element>
      					<element minOccurs="0" ref="gml:multiCurveProperty"></element>
      					<element minOccurs="0" ref="gml:surfaceProperty"></element>
      					<element minOccurs="0" ref="gml:multiSurfaceProperty"></element>
      					<element minOccurs="0" ref="gml:pointProperty"></element>
      					<element minOccurs="0" ref="gml:multiPointProperty"></element>
      				</sequence>
      			</extension>
      		</complexContent>
      	</complexType>
    SIMPLE_QUERY_EXPR = <element minOccurs="0" name="{fme:get-attribute("name")}" type="{fme:get-attribute("wfs_data_type")}"></element>
    DECIMAL_QUERY_EXPR:
      					<element minOccurs="0" name="{fme:get-attribute("name")}">
      						<simpleType>
      							<restriction base="decimal">
      								<totalDigits value="{fme:get-attribute("_matched_parts{0}")}"></totalDigits>
      								<fractionDigits value="{fme:get-attribute("_matched_parts{1}")}"></fractionDigits>
      							</restriction>
      						</simpleType>
      					</element>
    VISIBLE_QUERY_VALIDATE = Yes
    COMPLEX_QUERY_EXPR:
      					<element minOccurs="0" name="{fme:get-attribute("name")}">
      						<simpleType>
      							<restriction base="string">
      								<maxLength value="{fme:get-attribute("_matched_parts{0}")}"></maxLength>
      							</restriction>
      						</simpleType>
      					</element>
    CONSECUTIVE_GROUPS = No
    OUTPUT_XML_HEADER = Yes
    -> XMLTemplater_7 [input 2]
    -> Sampler_2
Sampler_2
    RATE = 1
    SAMPLE_TYPE_LONG = First N Features
    SAMPLED -> XMLTemplater_7 [input 1]
Note: Create DescribeFeatures
XMLTemplater_7
    RESULT_ATTRIBUTE = DescFeatType
    ROOT_QUERY_EXPR:
      <schema xmlns:xlink="http://www.w3.org/1999/xlink" xmlns:gml="http://www.opengis.net/gml" xmlns="http://www.w3.org/2001/XMLSchema" xmlns:$(GML_OUT_TARGET_NS_PREFIX_GML)="$(GML_OUT_TARGET_NS_URI_GML)" elementFormDefault="qualified" targetNamespace="$(GML_OUT_TARGET_NS_URI_GML)">
      	<import namespace="http://www.opengis.net/gml" schemaLocation="http://schemas.opengis.net/gml/3.1.1/base/gml.xsd"></import>

          {fme:process-features("ELEMENTS")}

      </schema>
    VISIBLE_QUERY_VALIDATE = Yes
    OUTPUT_XML_HEADER = Yes
    ELEMENTS_QUERY_EXPR:
      	<element name="{fme:get-attribute("fme_feature_type_name")}" substitutionGroup="gml:_Feature" type="$(GML_OUT_TARGET_NS_PREFIX_GML):{fme:get-attribute("fme_feature_type_name")}Type"></element>
          ,{fme:get-xml-attribute("_result")}
    -> XMLFormatter_2

Bookmark: WFS 2.0.0
Note: Keep only requested features
Tester_3
    BOOL_OP = OR
    TEST_DESCRIPTION = ""
    TEST_MODE = Automatic
    TEST_CLAUSE:
      TEST $(GML_OUT_TARGET_NS_PREFIX_GML):@Value(fme_feature_type_name) IN @Value(TYPENAME)
      TEST $(GML_OUT_TARGET_NS_PREFIX_GML):@Value(fme_feature_type_name) IN @Value(TYPENAMES)
    PASSED -> ListExploder_3
    PASSED -> XMLTemplater_8 [input 1]
Note: Explode list of attributes
ListExploder_3
    MODE = List Elements and Original Attributes
    LIST_ATTR = attribute{}
    LIST_FOUND -> StringSearcher_6
Note: Decimal, String / and other attribtes
StringSearcher_6
    CASE = no
    MATCHED_RESULT_ATTR = _matched_characters
    REGEXP = [(]([0-9]*),([0-9]*)[)]
    STRING_TO_SEARCH = @Value(native_data_type)
    MATCHED_PARTS_ATTR = _matched_parts
    NOT_MATCHED -> StringSearcher_5
    MATCHED -> XMLTemplater_8 [input 2]
StringSearcher_5
    CASE = no
    MATCHED_RESULT_ATTR = _matched_characters
    REGEXP = [(]([0-9]*)[)]
    STRING_TO_SEARCH = @Value(native_data_type)
    MATCHED_PARTS_ATTR = _matched_parts
    NOT_MATCHED -> AttributeValueMapper_3
    MATCHED -> XMLTemplater_8 [input 3]
    NOT_MATCHED -> Tester_4
Tester_4
    BOOL_OP = AND
    TEST_DESCRIPTION = ""
    TEST_MODE = Automatic
    TEST_CLAUSE:
      TEST @Value(name) NOT_BEGINS_WITH fme_
      TEST @Value(name) NOT_BEGINS_WITH gml_
    PASSED -> XMLTemplater_8 [input 4]
AttributeValueMapper_3 [off]
    VAL_ATTR = wfs_data_type
    LUT = fme_buffer,string,fme_char,string,fme_int64,long,fme_uint64,unsignedLong,fme_int32,int,fme_uint32,unsignedInt,fme_int16,short,fme_uint16,unsignedShort,fme_uint8,unsignedByte,fme_real32,float,fme_real64,double,fme_boolean,boolean,fme_datetime,string,fme_date,string,fme_time,string,fme_int32,PRIKEY,int,fme_int64,PRIKEY,long,fme_int32,BTREE,int
    SRC = native_data_type
    DIRECTION = Forward (Source To Destination)
    DEFAULT_VALUE = @Value(native_data_type)
    -> XMLTemplater_8 [input 4]
Note: Create feature type
XMLTemplater_8
    RESULT_ATTRIBUTE = _result
    GROUP_BY = fme_feature_type_name
    ROOT_QUERY_EXPR:
      	<complexType name="{fme:get-attribute("fme_feature_type_name")}Type">
      		<complexContent>
      			<extension base="gml:AbstractFeatureType">
      				<sequence>

                          {fme:process-features("DECIMAL")}
                          {fme:process-features("COMPLEX")}
                          {fme:process-features("SIMPLE")}

      					<element minOccurs="0" ref="gml:curveProperty"></element>
      					<element minOccurs="0" ref="gml:multiCurveProperty"></element>
      					<element minOccurs="0" ref="gml:surfaceProperty"></element>
      					<element minOccurs="0" ref="gml:multiSurfaceProperty"></element>
      					<element minOccurs="0" ref="gml:pointProperty"></element>
      					<element minOccurs="0" ref="gml:multiPointProperty"></element>
      				</sequence>
      			</extension>
      		</complexContent>
      	</complexType>
    SIMPLE_QUERY_EXPR = <element minOccurs="0" name="{fme:get-attribute("name")}" type="{fme:get-attribute("native_data_type")}"></element>
    DECIMAL_QUERY_EXPR:
      					<element minOccurs="0" name="{fme:get-attribute("name")}">
      						<simpleType>
      							<restriction base="decimal">
      								<totalDigits value="{fme:get-attribute("_matched_parts{0}")}"></totalDigits>
      								<fractionDigits value="{fme:get-attribute("_matched_parts{1}")}"></fractionDigits>
      							</restriction>
      						</simpleType>
      					</element>
    VISIBLE_QUERY_VALIDATE = Yes
    COMPLEX_QUERY_EXPR:
      					<element minOccurs="0" name="{fme:get-attribute("name")}">
      						<simpleType>
      							<restriction base="string">
      								<maxLength value="{fme:get-attribute("_matched_parts{0}")}"></maxLength>
      							</restriction>
      						</simpleType>
      					</element>
    CONSECUTIVE_GROUPS = No
    OUTPUT_XML_HEADER = Yes
    -> XMLTemplater_9 [input 2]
    -> Sampler_3
Sampler_3
    RATE = 1
    SAMPLE_TYPE_LONG = First N Features
    SAMPLED -> XMLTemplater_9 [input 1]
Note: Create DescribeFeatures
XMLTemplater_9
    RESULT_ATTRIBUTE = DescFeatType
    ROOT_QUERY_EXPR:
      <schema xmlns:gml="http://www.opengis.net/gml/3.2" xmlns:xlink="http://www.w3.org/1999/xlink" xmlns:$(GML_OUT_TARGET_NS_PREFIX_GML)="$(GML_OUT_TARGET_NS_URI_GML)"  xmlns="http://www.w3.org/2001/XMLSchema" targetNamespace="$(GML_OUT_TARGET_NS_URI_GML)" elementFormDefault="qualified">
      	<import namespace="http://www.opengis.net/gml/3.2" schemaLocation="http://schemas.opengis.net/gml/3.2.1/gml.xsd"></import>
      	<include namespace="http://skjema.geonorge.no/SOSI/produktspesifikasjon/Planomriss/4.5" schemaLocation="http://skjema.geonorge.no/SOSI/produktspesifikasjon/Planomriss/4.5/Planomriss.xsd"></include>

          {fme:process-features("ELEMENTS")}

      </schema>
    VISIBLE_QUERY_VALIDATE = Yes
    OUTPUT_XML_HEADER = Yes
    ELEMENTS_QUERY_EXPR:
      	<element name="{fme:get-attribute("fme_feature_type_name")}" substitutionGroup="gml:AbstractFeature" type="$(GML_OUT_TARGET_NS_PREFIX_GML):{fme:get-attribute("fme_feature_type_name")}Type"></element>
          ,{fme:get-xml-attribute("_result")}
    -> XMLFormatter_2

FME custom transformer WFS_Reprojector

Parameters:
- SRSNAME = @Value(SRSNAME)

Tester_7_Input (input)
    -> Tester_7
Note: Is SRSNAME provided?
Tester_7
    BOOL_OP = OR
    TEST_DESCRIPTION = ""
    TEST_MODE = Automatic
    TEST_CLAUSE = TEST SRSNAME ATTRIBUTE_IS_EMPTY ""
    PASSED -> Reprojector_3
    FAILED -> AttributeValueMapper_5
Note: Reprojects to default coordinate system
Reprojector_3
    DEST = EPSG:4258
    RASTER_CELL_SIZE = Preserve Cells
    INTERPOLATION_TYPE_NAME = Nearest Neighbor
    SOURCE = EPSG:4258
    REPROJECTED -> Reprojector_3_Reprojected (output)
Reprojector_3_Reprojected (output)
Note: If urn-notation is provided, map to standard EPSG
AttributeValueMapper_5
    VAL_ATTR = SRSNAME
    LUT = urn:ogc:def:crs:EPSG::4258,EPSG:4258,urn:ogc:def:crs:EPSG::4326,EPSG:4326,urn:ogc:def:crs:EPSG::25830,EPSG:25830,urn:ogc:def:crs:EPSG::25831,EPSG:25831,urn:ogc:def:crs:EPSG::25832,EPSG:25832,urn:ogc:def:crs:EPSG::25833,EPSG:25833,urn:ogc:def:crs:EPSG::25834,EPSG:25834,urn:ogc:def:crs:EPSG::25835,EPSG:25835,urn:ogc:def:crs:EPSG::25836,EPSG:25836,urn:ogc:def:crs:EPSG::3044,EPSG:3044,urn:ogc:def:crs:EPSG::3045,EPSG:3045
    SRC = SRSNAME
    DIRECTION = Forward (Source To Destination)
    DEFAULT_VALUE = @Value(SRSNAME)
    -> Reprojector_2
Note: Reprojects to destination coordinate system
Reprojector_2
    DEST = @Value(SRSNAME)
    RASTER_CELL_SIZE = Preserve Cells
    INTERPOLATION_TYPE_NAME = Nearest Neighbor
    SOURCE = EPSG:4258
    REPROJECTED -> Reprojector_2_Reprojected (output)
Reprojector_2_Reprojected (output)

FME custom transformer WFS_BBOX_CREATOR

Parameters:
- BBOX = @Value(BBOX)
- FILTER = @Value(FILTER)
- SRSNAME = @Value(SRSNAME)

Tester_5_Input (input)
    -> Tester_5
Note: Finnes BBOX?
Tester_5
    BOOL_OP = OR
    TEST_DESCRIPTION = ""
    TEST_MODE = Automatic
    TEST_CLAUSE:
      TEST BBOX ATTRIBUTE_IS_EMPTY ""
      TEST BBOX ATTRIBUTE_IS_MISSING ""
      TEST BBOX ATTRIBUTE_VALUE_NULL ""
    FAILED -> AttributeSplitter_2
    PASSED -> Tester_11
Note: WFS 2.0 BBOX?
Tester_11
    BOOL_OP = OR
    TEST_DESCRIPTION = ""
    TEST_MODE = Automatic
    TEST_CLAUSE = TEST @Value(FILTER) CONTAINS fes:BBOX
    FAILED -> 2DBoxReplacer
    PASSED -> StringReplacer_3

Bookmark: WFS 2.0 Filter BBOX
StringReplacer_3
    FIND_TEXT = +
    CASE = no
    REGEXP = no
    NO_MATCH = _FME_NO_OP_
    SRC_ATTRS = FILTER
    REPLACE_TEXT = " "
    -> XMLFragmenter_4
Note: Extracts filter with BBOX
XMLFragmenter_4
    ATTRIBUTE_XML = FILTER
    NEW_ATTRIBUTES = lowerCorner upperCorner Envelope.srsName
    XML_SOURCE_TYPE = Attribute with XML document
    MERGE_ATTRS = Yes
    EMBEDDED_EXPRESSIONS = fes:BBOX/*
    FLATTEN_OPTIONS = <structure separator="." map-empty-elements="yes" matched-prefix="attributes" matched-attributes="yes" cardinality="+{?}" structure-prefix="" child-position-attribute="" except-expression="" ui-mode="basic" matched-ancestor-attributes=""/>
    FRAGMENTS -> AttributeCreator_7
AttributeCreator_7
    ATTR_LIST = gml_bbox,@Value(lowerCorner) @Value(upperCorner)
    -> AttributeSplitter_3
AttributeSplitter_3
    ATTR_NAME = gml_bbox
    DELIMITER = " "
    DROP_EMPTY_PARTS = No
    TRIM_OPTION = Both
    LIST_NAME = gml_bboxlist
    -> Tester_2
Tester_2
    BOOL_OP = OR
    TEST_DESCRIPTION = ""
    TEST_MODE = Automatic
    TEST_CLAUSE:
      TEST @Value(Envelope.srsName) = urn:ogc:def:crs:EPSG::4258
      TEST @Value(Envelope.srsName) = EPSG:4258
      TEST @Value(Envelope.srsName) = urn:ogc:def:crs:EPSG::4326
      TEST @Value(Envelope.srsName) = EPSG:4326
      TEST @Value(Envelope.srsName) = urn:ogc:def:crs:EPSG::3044
      TEST @Value(Envelope.srsName) = urn:ogc:def:crs:EPSG::3045
      TEST @Value(Envelope.srsName) = EPSG:3044
      TEST @Value(Envelope.srsName) = EPSG:3045
    PASSED -> 2DBoxReplacer_4
    FAILED -> 2DBoxReplacer_5
Note: Create boundary from BBOX
2DBoxReplacer_4
    MINYVALATTR = @Value(gml_bboxlist{0})
    MINXVALATTR = @Value(gml_bboxlist{1})
    MAXYVALATTR = @Value(gml_bboxlist{2})
    MAXXVALATTR = @Value(gml_bboxlist{3})
    BOX -> AttributeValueMapper_7
Note: Create boundary from BBOX
2DBoxReplacer_5
    MINYVALATTR = @Value(gml_bboxlist{1})
    MINXVALATTR = @Value(gml_bboxlist{0})
    MAXYVALATTR = @Value(gml_bboxlist{3})
    MAXXVALATTR = @Value(gml_bboxlist{2})
    BOX -> AttributeValueMapper_7
Note: If urn-notation is provided, map to standard EPSG
AttributeValueMapper_7
    VAL_ATTR = Envelope.srsName
    LUT = urn:ogc:def:crs:EPSG::4258,EPSG:4258,urn:ogc:def:crs:EPSG::4326,EPSG:4326,urn:ogc:def:crs:EPSG::25830,EPSG:25830,urn:ogc:def:crs:EPSG::25831,EPSG:25831,urn:ogc:def:crs:EPSG::25832,EPSG:25832,urn:ogc:def:crs:EPSG::25833,EPSG:25833,urn:ogc:def:crs:EPSG::25834,EPSG:25834,urn:ogc:def:crs:EPSG::25835,EPSG:25835,urn:ogc:def:crs:EPSG::25836,EPSG:25836,urn:ogc:def:crs:EPSG::3044,EPSG:3044,urn:ogc:def:crs:EPSG::3045,EPSG:3045
    SRC = Envelope.srsName
    DIRECTION = Forward (Source To Destination)
    DEFAULT_VALUE = @Value(Envelope.srsName)
    -> Reprojector_4
Note: Reprojects to default coordinate system
Reprojector_4
    DEST = EPSG:4258
    RASTER_CELL_SIZE = Preserve Cells
    INTERPOLATION_TYPE_NAME = Nearest Neighbor
    SOURCE = @Value(Envelope.srsName)
    REPROJECTED -> WFS20_FilterBBOX (output)
WFS20_FilterBBOX (output)

Bookmark: Default BBOX
Note: Ingen BBOX - bruker veldig stor BBOX
2DBoxReplacer
    MINYVALATTR = -1000000000000
    MINXVALATTR = -1000000000000
    MAXYVALATTR = 1000000000000
    MAXXVALATTR = 1000000000000
    BOX -> Default_BBOX (output)
Default_BBOX (output)

Bookmark: Standard BBOX-parameters provided
Note: Get BBOX coords from parameter
AttributeSplitter_2
    ATTR_NAME = BBOX
    DELIMITER = ,
    DROP_EMPTY_PARTS = No
    TRIM_OPTION = Both
    LIST_NAME = _bbox
    -> Tester_12
Note: Tekes care of axis order
Tester_12
    BOOL_OP = OR
    TEST_DESCRIPTION = ""
    TEST_MODE = Automatic
    TEST_CLAUSE:
      TEST @Value(_bbox{4}) = urn:ogc:def:crs:EPSG::4258
      TEST @Value(_bbox{4}) = urn:ogc:def:crs:EPSG::4326
      TEST @Value(_bbox{4}) = urn:ogc:def:crs:EPSG::3044
      TEST @Value(_bbox{4}) = urn:ogc:def:crs:EPSG::3045
    PASSED -> 2DBoxReplacer_3
    FAILED -> 2DBoxReplacer_2
Note: Create boundary from BBOX
2DBoxReplacer_3
    MINYVALATTR = @Value(_bbox{0})
    MINXVALATTR = @Value(_bbox{1})
    MAXYVALATTR = @Value(_bbox{2})
    MAXXVALATTR = @Value(_bbox{3})
    BOX -> Tester_10
Note: Create boundary from BBOX
2DBoxReplacer_2
    MINYVALATTR = @Value(_bbox{1})
    MINXVALATTR = @Value(_bbox{0})
    MAXYVALATTR = @Value(_bbox{3})
    MAXXVALATTR = @Value(_bbox{2})
    BOX -> Tester_10
Note: Is SRSNAME provided?
Tester_10
    BOOL_OP = OR
    TEST_DESCRIPTION = ""
    TEST_MODE = Automatic
    TEST_CLAUSE = TEST SRSNAME ATTRIBUTE_IS_EMPTY ""
    FAILED -> AttributeValueMapper_6
    PASSED -> Standard_bbox (output)
Standard_bbox (output)
Note: If urn-notation is provided, map to standard EPSG
AttributeValueMapper_6
    VAL_ATTR = SRSNAME
    LUT = urn:ogc:def:crs:EPSG::4258,EPSG:4258,urn:ogc:def:crs:EPSG::4326,EPSG:4326,urn:ogc:def:crs:EPSG::25830,EPSG:25830,urn:ogc:def:crs:EPSG::25831,EPSG:25831,urn:ogc:def:crs:EPSG::25832,EPSG:25832,urn:ogc:def:crs:EPSG::25833,EPSG:25833,urn:ogc:def:crs:EPSG::25834,EPSG:25834,urn:ogc:def:crs:EPSG::25835,EPSG:25835,urn:ogc:def:crs:EPSG::25836,EPSG:25836,urn:ogc:def:crs:EPSG::3044,EPSG:3044,urn:ogc:def:crs:EPSG::3045,EPSG:3045
    SRC = SRSNAME
    DIRECTION = Forward (Source To Destination)
    DEFAULT_VALUE = @Value(SRSNAME)
    -> Reprojector_5
Note: Reprojects to default coordinate system
Reprojector_5
    DEST = EPSG:4258
    RASTER_CELL_SIZE = Preserve Cells
    INTERPOLATION_TYPE_NAME = Nearest Neighbor
    SOURCE = @Value(SRSNAME)
    REPROJECTED -> Reprojected_BBOX (output)
Reprojected_BBOX (output)

FME custom transformer FMEServerURLSplitter
This transformer is useful for breaking up the full URI request that is sent to FME Server. The transformer actually takes any URL and breaks it up into pieces, so it could be applied elsewhere.
With FME Server the entire request URL is passed to the workspace in the FME_SERVER_REQUEST_URI parameter so that it can be used within the workspace. This is useful in cases where extra parameters are tacked onto a URL or the URL path doesn't end with .fmw.
This capability makes it possible for FME Server to be used to satisfy new types of requests where the full request cannot be known until runtime.
Input:
Request URI: the full URI request made to FME Server, in string or attribute form
URL Parameter Name Case: Will case of the URL Parameter Names to the case specified. This is useful to make your service "case insensitve".  Specify Upper or lower case and then your service is not case sensitive with Parameter Names. Parameter Values are left untouched.
Decode URL Parameters: If set to "Decode" then both url parameter attribute names and attribute values will be decoded. 
Output
base_url - This is the entire URL up to the starts of URL parameters. 
fme_server_base_url - The FME Server base url. Is the same as above if the base_url ends at .fmw. This is only present if the url has .fmw in it. 
fme_server_extra_url_path - the additional components of the path if it is from FME Server. This is present if the base_url is different from the fme_server_base_url.
fme_server_extra_url{} list - fme_server_extra_url_path broken up into a list for convenience
url_raw_parameters - These are all the url parameters as one string.
num_parms - The number of URL parameters after they have been parsed out. 
decoded parameters - The parameters themselves are also parsed out and turned into FME attributes.  These must be explicitly exposed after this transformer. 
Example
Given the url 
http://dondemo/fmejobsubmitter/webdump/PublishParameterDump.fmw/another/value?DestDataset_TEXTLINE=output.txt&opt_showresult=false&opt_servicemode=sync&anotherparm=here
base_url has value `http://dondemo/fmejobsubmitter/webdump/PublishParameterDump.fmw/another/value'
fme_server_base_url has value `http://dondemo/fmejobsubmitter/webdump/PublishParameterDump.fmw/'
fme_server_extra_url_path' has value `another/value'
fme_server_extra_url{0}' has value 'another'
fme_server_extra_url{1}' has value 'value'
url_raw_parameters' has value 'DestDataset_TEXTLINE=output.txt&opt_showresult=false&opt_servicemode=sync&anotherparm=here'
num_parms' has value '4'
DestDataset_TEXTLINE has value 'output.txt'
anotherparm has value 'here'
opt_servicemode has value 'sync'
opt_showresult has value 'false'
Copyright (c) 2014 Safe Software Inc.
Permission is granted to anyone, free of charge, to use, modify and distribute the object code form of this transformer for any purpose, subject to the following restrictions:
1) The origin of this transformer and associated FME(R) software must not be misrepresented.
2) This transformer may only be used in conjunction with a validly licensed copy of FME software.
THIS SOFTWARE IS PROVIDED BY SAFE SOFTWARE INC. "AS IS" AND ANY EXPRESS OR IMPLIED WARRANTIES, INCLUDING, BUT NOT LIMITED TO, THE IMPLIED WARRANTIES OF MERCHANTABILITY, NONINFRINGEMENT AND FITNESS FOR A PARTICULAR PURPOSE ARE DISCLAIMED. IN NO EVENT SHALL SAFE SOFTWARE INC. BE LIABLE FOR ANY DIRECT, INDIRECT, INCIDENTAL, SPECIAL, EXEMPLARY, OR CONSEQUENTIAL DAMAGES (INCLUDING, BUT NOT LIMITED TO, PROCUREMENT OF SUBSTITUTE GOODS OR SERVICES; LOSS OF USE, DATA, OR PROFITS; OR BUSINESS INTERRUPTION) HOWEVER CAUSED AND ON ANY THEORY OF LIABILITY, WHETHER IN CONTRACT, STRICT LIABILITY, OR TORT (INCLUDING NEGLIGENCE OR OTHERWISE) ARISING IN ANY WAY OUT OF THE USE OF THIS SOFTWARE, EVEN IF ADVISED OF THE POSSIBILITY OF SUCH DAMAGE.

Parameters:
- _FME_SERVER_REQUEST_URI =   # Request URI
- URL_PARAM_NAME_CASE = Untouched   # case"%"Full Title Case"%Untouched URL Parameter Name Case
- DECODE_URL_TEXT = Don't Decode   # Decode" Decode URL Parameters

Input (input)
    -> AttributeSplitter
Output (output)

Bookmark: First split url up into two peices ("base url" and "parm string")
AttributeSplitter
    ATTR_NAME = _FME_SERVER_REQUEST_URI
    DELIMITER = ?
    DROP_EMPTY_PARTS = No
    TRIM_OPTION = Both
    LIST_NAME = _list
    -> AttributeRenamer
AttributeRenamer
    ATTR_LIST = _list{0},base_url,"",_list{1},url_raw_parameters,""
    -> AttributeSplitter_2

Bookmark: Check if Parms and build list
Note: Now we split the parm string into a list.
AttributeSplitter_2
    ATTR_NAME = url_raw_parameters
    DELIMITER = &
    DROP_EMPTY_PARTS = No
    TRIM_OPTION = Both
    LIST_NAME = _paramList
    -> TestFilter
TestFilter
    TEST_LIST = BOOL_OP,OR,COMPOSITE_TEST,<Unused>,TEST_CLAUSE,"TEST _paramList{0} NOT_ATTRIBUTE_IS_EMPTY """"",Parameters
    DEFAULT_VALUE = NoParameters
    Parameters -> ListElementCounter
    NoParameters -> Remove_Empty_Argument
Note: No Parms so remove attribute
Remove_Empty_Argument: AttributeRemover
    REMOVE_ATTRS = url_raw_parameters
    -> StringSearcher

Bookmark: Loop Initialization
ListElementCounter
    CNT_ATTR = num_parms
    LIST_NAME = _paramList{}
    -> InitializeCounter
InitializeCounter: Counter
    DOMAIN = AttributeCount
    CNT_ATTR = currentListPos
    SCOPE = Global
    START = 0
    -> AttributeCreator_2

Bookmark: Iterate over all the parameters that were set
AttributeLooper (input)
    -> AttributeCreator_2

Bookmark: Extract a value and build attribute
AttributeCreator_2
    ATTR_LIST = curListEntry,@Value(_paramList{@Value(currentListPos)})
    -> AttributeSplitter_3
AttributeSplitter_3
    ATTR_NAME = curListEntry
    DELIMITER = =
    DROP_EMPTY_PARTS = No
    TRIM_OPTION = Both
    LIST_NAME = paramEntry
    -> AreWeChangingCase
AreWeDecodingURLText: TestFilter
    TEST_LIST = BOOL_OP,OR,COMPOSITE_TEST,<Unused>,TEST_CLAUSE,"TEST $(DECODE_URL_TEXT) = Decode",Decode
    DEFAULT_VALUE = Don't Decode
    Don't Decode -> AttributeCreator
    Decode -> DecodeParamName
DecodeParamName: TextDecoder
    STRING_TO_DECODE = @Value(paramEntry{0})
    ENCODING_TYPE = URL (Percent Encoding)
    DEST_ATTR = paramEntry{0}
    -> DecodeParamValue
DecodeParamValue: TextDecoder
    STRING_TO_DECODE = @Value(paramEntry{1})
    ENCODING_TYPE = URL (Percent Encoding)
    DEST_ATTR = paramEntry{1}
    -> AttributeCreator
AttributeCreator
    ATTR_LIST = @Value(paramEntry{0}),@Value(paramEntry{1})
    -> IncrementCounter
IncrementCounter: Counter
    DOMAIN = AttributeCount
    CNT_ATTR = currentListPos
    SCOPE = Global
    START = 0
    -> TestForMoreParms

Bookmark: Change Case
AreWeChangingCase: TestFilter
    TEST_LIST = BOOL_OP,OR,COMPOSITE_TEST,<Unused>,TEST_CLAUSE,"TEST $(URL_PARAM_NAME_CASE) = Untouched",No case change
    DEFAULT_VALUE = change case
    change case -> StringCaseChanger
    No case change -> AreWeDecodingURLText
StringCaseChanger
    ATTRCHOICE = Selected Attributes
    CHANGE_TYPE = $(URL_PARAM_NAME_CASE)
    ATTRLIST = paramEntry{0}
    -> AreWeDecodingURLText

Bookmark: Another Iteration?
TestForMoreParms: TestFilter
    TEST_LIST = BOOL_OP,OR,COMPOSITE_TEST,<Unused>,TEST_CLAUSE,"TEST @Value(currentListPos) < @Value(num_parms)",More Params
    DEFAULT_VALUE = All Done
    More Params -> AttributeLooper (output)
    All Done -> StringSearcher
AttributeLooper (output)

Bookmark: Extract URL Path after the *.fmw.
StringSearcher
    CASE = no
    MATCHED_RESULT_ATTR = _matched_characters
    REGEXP = ^(.*[.]fmw/)(.*)$
    STRING_TO_SEARCH = @Value(base_url)
    MATCHED_PARTS_ATTR = _matched_parts
    MATCHED -> AttributeRenamer_2
    NOT_MATCHED -> AttributeRemover
AttributeRenamer_2
    ATTR_LIST = _matched_parts{0},fme_server_base_url,"",_matched_parts{1},fme_server_extra_url_path,""
    -> AttributeSplitter_4
AttributeSplitter_4
    ATTR_NAME = fme_server_extra_url_path
    DELIMITER = /
    DROP_EMPTY_PARTS = No
    TRIM_OPTION = Both
    LIST_NAME = fme_server_extra_url
    -> AreWeDecodingURLText_2
AreWeDecodingURLText_2: TestFilter
    TEST_LIST = BOOL_OP,OR,COMPOSITE_TEST,<Unused>,TEST_CLAUSE,"TEST $(DECODE_URL_TEXT) = Decode",Decode
    DEFAULT_VALUE = Don't Decode
    Don't Decode -> AttributeRemover
    Decode -> DecodeExxtraURL
DecodeExxtraURL: TextDecoder
    STRING_TO_DECODE = @Value(fme_server_extra_url_path)
    ENCODING_TYPE = URL (Percent Encoding)
    DEST_ATTR = fme_server_extra_url_path
    -> AttributeRemover
AttributeRemover
    REMOVE_ATTRS = currentListPos,curListEntry,_matched_characters
    LIST_ATTRS = _paramList{} _matched_parts{} paramEntry{} _list{}
    -> Output (output)
