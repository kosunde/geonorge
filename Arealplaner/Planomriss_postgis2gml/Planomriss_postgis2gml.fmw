FME workspace Planomriss_postgis2gml.fmw
Shutdown Python:
      # -*- coding: utf-8 -*-
      #-------------------------------------------------------------------------------
      # Name:        zipfiles.py
      # Purpose:     Pakker filer i output folderen
      #
      # Author:      xsunknu
      #
      # Created:     18.09.2015
      # Copyright:   (c) xsunknu 2015
      # Licence:     <your licence>
      #-------------------------------------------------------------------------------

      import sys, os, zipfile, fme

      def zip(gmlfile, zfile):
          from os.path import basename

          # Lager korresponderende zip-fil av SOSI-fil
          if os.path.isfile(zfile):
              os.remove(zfile)

          zf = zipfile.ZipFile(zfile, "w", zipfile.ZIP_DEFLATED)

          # Ønsker ikke full sti inn i ZIP-filen
          arcname = basename(gmlfile)

          # ZIP-formatet støtter ikke non-ascii tegn
          # Erstatter AØÅæøå med ascii-tegn
          arcname = arcname.replace('\xc6', 'E')
          arcname = arcname.replace('\xd8', 'O')
          arcname = arcname.replace('\xc5', 'A')
          arcname = arcname.replace('\xe6', 'e')
          arcname = arcname.replace('\xf8', 'o')
          arcname = arcname.replace('\xe5', 'a')

          zf.write(gmlfile, arcname)
          zf.close()
          os.remove(gmlfile)

          return

      def main():

          # Kjøres ikke på FME Server, da FME Server selv sørger for pakkingen
          if not 'FME_SERVER_DEST_DIR' in fme.macroValues:
              if 'FANOUT_FOLDER' in fme.macroValues:
                  path = fme.macroValues['FANOUT_FOLDER']
                  for dirpath, dnames, fnames in os.walk(path):
                      for f in fnames:
                          if f.endswith(".gml"):
                              # Scanner gjennom alle SOSI-filer
                              gmlfile = os.path.join(path, f)
                              zfile = os.path.splitext(gmlfile)[0] + '.zip'
                              if os.path.isfile(zfile):

                                  # Korresponderende ZIP-fil finnes, sjekker timestamps
                                  sositstamp = os.stat(gmlfile).st_mtime
                                  ziptstamp = os.stat(zfile).st_mtime

                                  if sositstamp > ziptstamp:
                                      # SOSI-fil er nyere enn ZIP-fila, ZIP-fila oppdateres
                                      # SOSI-fila slettes
                                      try:
                                          zip(gmlfile, zfile)
                                      except:
                                          print 'Kunne ikke pakke: ' + gmlfile
                                  else:
                                      # SOSI-fila er eldre enn ZIP-fila
                                      # SOSI-fila slettes
                                      try:
                                          os.remove(gmlfile)
                                      except:
                                          print 'Kunne ikke slette: ' + gmlfile
                              else:
                                  # ZIP-fila eksisterer ikke og lages
                                  # SOSI-fila slettes
                                  try:
                                      zip(gmlfile, zfile)
                                  except:
                                      print 'Kunne ikke pakke: ' + gmlfile


      if __name__ == '__main__':
          main()

Parameters:
- KNR =   # Kommune(r)
- FNR =   # Fylke(r)
- CLIPPERCOORDS =   # Clipper coordinates
- CLIPPER_EPSG_CODE =   # Clipper coordinate system
- CLIPPER_FILE =   # "" Clipper file (any format)
- OUTPUT_EPSG_CODE = 25832   # Destination coordinate system
- FANOUT =   # Fanout områder
- DestDataset_GML = $(FME_MF_DIR)Planomriss.gml   # Destination Geography Markup Language (GML) File
- CONFIG_FILE:   # Python Script
      #-------------------------------------------------------------------------------
      # Name:        GetConfigFile
      # Purpose:
      #
      # Author:      xsunknu
      #
      # Created:     21.08.2015
      # Copyright:   (c) xsunknu 2015
      # Licence:     <your licence>
      #-------------------------------------------------------------------------------
      
      import os, fme
      
      fmwdir = fme.macroValues['FME_MF_DIR']
      fmwfile = fme.macroValues['FME_MF_NAME']
      
      fmwfile = os.path.join(fmwdir, fmwfile)
      configfile = os.path.splitext(fmwfile)[0] + '_config.xml'
      
      return configfile
- PG_DB:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgdb').text
      
      return value
- PG_HOST:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pghost').text
      
      return value
- PG_PORT:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgport').text
      
      return value
- PG_PWD:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgpwd').text
      
      return value
- FIXEDCLIPPERCOORDS:   # Python Script
      #-------------------------------------------------------------------------------
      # Name:        FixClipperCoords
      # Purpose:
      #
      # Author:      xsunknu
      #
      # Created:     21.08.2015
      # Copyright:   (c) xsunknu 2015
      # Licence:     <your licence>
      #-------------------------------------------------------------------------------
      
      import fme
      clippercoords = fme.macroValues['CLIPPERCOORDS']
      
      if clippercoords == '':
          clippercoords = '1 1'
      
      return clippercoords
- PG_USER:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pguser').text
      
      return value
- CLIPPERCOORDSYS:   # Python Script
      #-------------------------------------------------------------------------------
      # Name:        SetCoordinateSystem
      # Purpose:
      #
      # Author:      xsunknu
      #
      # Created:     21.08.2015
      # Copyright:   (c) xsunknu 2015
      # Licence:     <your licence>
      #-------------------------------------------------------------------------------
      
      import os, fme
      
      EPSGvalue = fme.macroValues['CLIPPER_EPSG_CODE']
      EPSGcode  = 'EPSG:' + EPSGvalue
      
      return EPSGcode
- DESTCOORDSYS:   # Python Script
      #-------------------------------------------------------------------------------
      # Name:        SetCoordinateSystem
      # Purpose:
      #
      # Author:      xsunknu
      #
      # Created:     21.08.2015
      # Copyright:   (c) xsunknu 2015
      # Licence:     <your licence>
      #-------------------------------------------------------------------------------
      
      import os, fme
      
      EPSGvalue = fme.macroValues['OUTPUT_EPSG_CODE']
      EPSGcode  = 'EPSG:' + EPSGvalue
      
      return EPSGcode
- FANOUT_FOLDER:   # Python Script
      #-------------------------------------------------------------------------------
      # Name:        GetConfigFile
      # Purpose:
      #
      # Author:      xsunknu
      #
      # Created:     21.08.2015
      # Copyright:   (c) xsunknu 2015
      # Licence:     <your licence>
      #-------------------------------------------------------------------------------
      
      import os, fme
      from xml.etree import ElementTree as ET
      
      if 'FME_SERVER_DEST_DIR' in fme.macroValues:
          value = fme.macroValues['FME_SERVER_DEST_DIR']
      else:
          #Read XML config file
          configtree = ET.parse(fme.macroValues['CONFIG_FILE'])
          configdoc = configtree.getroot()
          value = configdoc.find('destdir').text
      
      return value
- SOSI_FILE = Planomriss   # SOSI file
- LOG_FILE:   # Python Script
      #-------------------------------------------------------------------------------
      # Name:        GetConfigFile
      # Purpose:
      #
      # Author:      xsunknu
      #
      # Created:     21.08.2015
      # Copyright:   (c) xsunknu 2015
      # Licence:     <your licence>
      #-------------------------------------------------------------------------------
      
      import os, uuid, fme
      
      fmwdir = fme.macroValues['FME_MF_DIR']
      fmwfile = fme.macroValues['FME_MF_NAME']
      
      logdir = os.path.join(fmwdir, 'log')
      if not os.path.isdir(logdir):
          os.mkdir(logdir)
      
      logfile = os.path.splitext(fmwfile)[0] + '_' + str(uuid.uuid1()).replace('-','') + '.log'
      logfile = os.path.join(logdir, logfile)
      
      return logfile

Readers:
- POSTGIS_1: POSTGIS from $(PG_DB)

Writers:
- GML_1: GML to $(DestDataset_GML) in $(DESTCOORDSYS)

CreateClipper
    CLIPPERCOORDSYS = $(CLIPPERCOORDSYS)
    CLIPPERCOORDS = $(FIXEDCLIPPERCOORDS)
    DESTCOORDSYS = $(DESTCOORDSYS)
    -> Clipper [input 1]
    -> FeatureReader_2

Bookmark: Fylke and/or kommune clippers
admingrense.fylkeflate (reader POSTGIS_1)
    attributes: fylkeid int4, navn varchar(80)
    -> Tester
    -> AttributeCreator_7
AttributeCreator_7
    ATTR_LIST = _clippercoords,$(CLIPPERCOORDS),_clipper_file,$(CLIPPER_FILE),_fnr,$(FNR),_knr,$(KNR)
    -> Tester_4
Note: Sender inn hele landet som initiator / dersom alle klippeparametrene er / blanke
Tester_4
    TEST_DESCRIPTION = ""
    TEST_CLAUSE:
      TEST _clipper_file ATTRIBUTE_IS_EMPTY ""
      TEST _clippercoords ATTRIBUTE_IS_EMPTY ""
      TEST _fnr ATTRIBUTE_IS_EMPTY ""
      TEST _knr ATTRIBUTE_IS_EMPTY ""
    TEST_MODE = Automatic
    BOOL_OP = AND
    PASSED -> Reprojector_2
Tester
    TEST_DESCRIPTION = ""
    TEST_CLAUSE = TEST @Value(fylkeid) IN $(FNR)
    TEST_MODE = Automatic
    BOOL_OP = OR
    PASSED -> Reprojector_2
admingrense.kommuneflate (reader POSTGIS_1)
    attributes: kommuneid int4, navn varchar(80)
    -> Tester_2
Tester_2
    TEST_DESCRIPTION = ""
    TEST_CLAUSE = TEST @Value(kommuneid) IN $(KNR)
    TEST_MODE = Automatic
    BOOL_OP = OR
    PASSED -> Reprojector_2
Reprojector_2
    SOURCE = Read from feature
    DEST = EPSG:4258
    RASTER_CELL_SIZE = Preserve Cells
    INTERPOLATION_TYPE_NAME = Nearest Neighbor
    REPROJECTED -> FeatureReader_2

Bookmark: Clipper file (any format)
Creator
    GEOMTYPE = Geometry Object
    NUM = 1
    CREATED -> FeatureReader
FeatureReader
    INTERACT = <No Spatial Filter>
    OUTPUT_FEATURES_DISPLAY = Based on Connections
    FEATURETYPES_RADIO = FEATURETYPES
    FORMAT = GENERIC
    ATTRIBUTES = NewFeatureType,
    COMBINE_GEOM = Use Result
    GENERIC_REAL_FORMAT = GUESS_FROM_EXTENSION
    DATASET = $(CLIPPER_FILE)
    ATTR_ACCUM_MODE = Only Use Result
    <OTHER> -> Reprojector_3
Reprojector_3
    SOURCE = Read from feature
    DEST = EPSG:4258
    RASTER_CELL_SIZE = Preserve Cells
    INTERPOLATION_TYPE_NAME = Nearest Neighbor
    REPROJECTED -> FeatureReader_2
    REPROJECTED -> Clipper [input 1]

Bookmark: Lesing, klipping og transformasjon
FeatureReader_2
    POSTGIS_USER_NAME = $(PG_USER)
    ATTR_ACCUM_MODE = Only Use Result
    INTERACT = Intersects
    DATASET = $(PG_DB)
    POSTGIS_PORT = $(PG_PORT)
    FORMAT = POSTGIS
    COMBINE_GEOM = Use Result
    POSTGIS_USE_TRUE_POSTGIS_TYPES = yes
    POSTGIS_SCHEMALIST = planomriss
    POSTGIS_CLIP_TO_ENVELOPE = NO
    POSTGIS_HOST = $(PG_HOST)
    POSTGIS_DISABLE_COLLECTION_SPLITTING = yes
    ATTRIBUTES = planomriss.kpgrense,"objid,objtype",planomriss.kpomrade,"objid,objtype,landkode,fylkesnr,komm,planid,ikrafttredelsesdato,kunngjoringsdato,lovreferanse,lovreferansebeskrivelse,opprinneligadministrativenhet,opprinneligplanid,planbestemmelse,plannavn,planstatus,plantype,vedtakendeligplandato",planomriss.rpgrense,"objid,objtype",planomriss.rpomrade,"objid,objtype,landkode,fylkesnr,komm,planid,forslagsstillertype,gjennomforingsfrist,ikrafttredelsesdato,kunngjoringsdato,lovreferanse,lovreferansebeskrivelse,opprinneligadministrativenhet,opprinneligplanid,planbestemmelse,plannavn,planstatus,plantype,vedtakendeligplandato,vertikalniva"
    POSTGIS_USE_SEARCH_ENVELOPE = NO
    OUTPUT_FEATURES_DISPLAY = Based on Connections
    POSTGIS_QUERY_FEATURE_TYPES_FOR_MERGE_FILTERS = Yes
    FEATURETYPES = planomriss.kpgrense planomriss.kpomrade planomriss.rpgrense planomriss.rpomrade
    FEATURETYPES_RADIO = FEATURETYPES
    POSTGIS_PASSWORD = $(PG_PWD)
    planomriss.kpgrense -> AttributeCreator_6
    planomriss.kpomrade -> AttributeCreator_6
    planomriss.rpgrense -> AttributeCreator_6
    planomriss.rpomrade -> AttributeCreator_6
AttributeCreator_6
    ATTR_LIST = _clippercoords,$(CLIPPERCOORDS),_clipper_file,$(CLIPPER_FILE),_fnr,$(FNR),_knr,$(KNR)
    -> TestFilter
TestFilter
    TEST_LIST:
      BOOL_OP,AND,COMPOSITE_TEST,<Unused>,TEST_CLAUSE,"TEST _clipper_file ATTRIBUTE_IS_EMPTY """"
      TEST _clippercoords ATTRIBUTE_IS_EMPTY """"
      TEST _fnr ATTRIBUTE_IS_EMPTY """"
      TEST _knr ATTRIBUTE_IS_EMPTY """"",Landsdekkende,BOOL_OP,AND,COMPOSITE_TEST,<Unused>,TEST_CLAUSE,"TEST _clipper_file ATTRIBUTE_IS_EMPTY """"
      TEST _clippercoords ATTRIBUTE_IS_EMPTY """"
      TEST _fnr NOT_ATTRIBUTE_IS_EMPTY """"
      TEST _knr ATTRIBUTE_IS_EMPTY """"",Fylkesvis,BOOL_OP,AND,COMPOSITE_TEST,<Unused>,TEST_CLAUSE,"TEST _clipper_file ATTRIBUTE_IS_EMPTY """"
      TEST _clippercoords ATTRIBUTE_IS_EMPTY """"
      TEST _fnr ATTRIBUTE_IS_EMPTY """"
      TEST _knr NOT_ATTRIBUTE_IS_EMPTY """"",Kommunevis
    DEFAULT_VALUE = <UNFILTERED>
    Landsdekkende -> Reprojector
    <UNFILTERED> -> Clipper [input 2]
    Fylkesvis -> FeatureTypeFilter_2
    Kommunevis -> FeatureTypeFilter_3
Clipper
    ATTR_ACCUM_MODE = Merge Clipper
    CLIP_TYPE = Multiple Clippers
    CLIPPED_ATTR = _clipped
    PRESERVE_CLIPPEE_EXTENTS = No
    ATTR_CONFLICT_RES = Use Clipper
    CREATE_AGGREGATES = No
    BOUNDARY_CASES = Treat as Inside
    INSIDE -> Reprojector
FeatureTypeFilter_2
    ATTRIBUTES = planomriss.kpomrade,planomriss.kpgrense,planomriss.rpomrade,planomriss.rpgrense,<BLANK>,<UNFILTERED>
    planomriss.kpomrade -> Tester_3
    planomriss.rpomrade -> Tester_9
    planomriss.kpgrense -> SpatialRelator [input 1]
    planomriss.rpgrense -> SpatialRelator_2 [input 1]
Tester_3
    TEST_DESCRIPTION = ""
    TEST_CLAUSE = TEST @Value(fylkesnr) IN @Value(_fnr)
    TEST_MODE = Automatic
    BOOL_OP = OR
    PASSED -> SpatialRelator [input 2]
    PASSED -> Tester_13
SpatialRelator
    CALC_CARD = No
    PREDICATES = TOUCHES
    CURVE_BOUNDARY_RULE_PARAM = Default Rule
    LIST_NAME = _relationships
    SUCCESS_ATTR = _related_candidates
    -> Tester_13
Tester_9
    TEST_DESCRIPTION = ""
    TEST_CLAUSE = TEST @Value(fylkesnr) IN @Value(_fnr)
    TEST_MODE = Automatic
    BOOL_OP = OR
    PASSED -> SpatialRelator_2 [input 2]
    PASSED -> Tester_13
SpatialRelator_2
    CALC_CARD = No
    PREDICATES = TOUCHES
    CURVE_BOUNDARY_RULE_PARAM = Default Rule
    LIST_NAME = _relationships
    SUCCESS_ATTR = _related_candidates
    -> Tester_13
FeatureTypeFilter_3
    ATTRIBUTES = planomriss.kpomrade,planomriss.kpgrense,planomriss.rpomrade,planomriss.rpgrense,<BLANK>,<UNFILTERED>
    planomriss.kpomrade -> Tester_10
    planomriss.rpomrade -> Tester_11
    planomriss.kpgrense -> SpatialRelator_3 [input 1]
    planomriss.rpgrense -> SpatialRelator_4 [input 1]
Tester_10
    TEST_DESCRIPTION = ""
    TEST_CLAUSE = TEST @Value(komm) IN @Value(_knr)
    TEST_MODE = Automatic
    BOOL_OP = OR
    PASSED -> SpatialRelator_3 [input 2]
    PASSED -> Tester_13
SpatialRelator_3
    CALC_CARD = No
    PREDICATES = INTERSECTS
    CURVE_BOUNDARY_RULE_PARAM = Curve Boundary Includes All Endpoints
    LIST_NAME = _relationships
    SUCCESS_ATTR = _related_candidates
    -> Tester_13
Tester_11
    TEST_DESCRIPTION = ""
    TEST_CLAUSE = TEST @Value(komm) IN @Value(_knr)
    TEST_MODE = Automatic
    BOOL_OP = OR
    PASSED -> SpatialRelator_4 [input 2]
    PASSED -> Tester_13
SpatialRelator_4
    CALC_CARD = No
    PREDICATES = INTERSECTS
    CURVE_BOUNDARY_RULE_PARAM = Curve Boundary Includes All Endpoints
    LIST_NAME = _relationships
    SUCCESS_ATTR = _related_candidates
    -> Tester_13
Tester_13
    TEST_DESCRIPTION = ""
    TEST_CLAUSE:
      TEST komm NOT_ATTRIBUTE_IS_MISSING ""
      TEST fylkesnr NOT_ATTRIBUTE_IS_MISSING ""
    TEST_MODE = Automatic
    BOOL_OP = OR
    PASSED -> AttributeCreator_12
AttributeCreator_12
    ATTR_LIST = kommuneid,@Value(komm),fylkeid,@Value(fylkesnr)
    -> Reprojector
Reprojector
    SOURCE = Read from feature
    DEST = $(DESTCOORDSYS)
    RASTER_CELL_SIZE = Preserve Cells
    INTERPOLATION_TYPE_NAME = Nearest Neighbor
    REPROJECTED -> AttributeCreator_5
AttributeCreator_5
    ATTR_LIST = komm,@PadLeft(@Value(komm),4,0),opprinneligadministrativenhet,"FME_CONDITIONAL:DEFAULT_VALUE'@PadLeft(@Value(opprinneligadministrativenhet),4,0)'BOOL_OP;OR;COMPOSITE_TEST;<Unused>;TEST opprinneligadministrativenhet ATTRIBUTE_VALUE_NULL _FME_BLANK_STRING_'FME_NULL_VALUE'FME_NUM_CONDITIONS2___"
    -> SosiFilenameSetter
SosiFilenameSetter
    FORSLAGSSTILLERTYPE = @Value(forslagsstillertype)
    KOMMUNEID = @Value(kommuneid)
    PLANID = @Value(planid)
    FANOUT = $(FANOUT)
    _KNR = @Value(_knr)
    KOMM = @Value(komm)
    PG_USER:
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------

      import fme
      from xml.etree import ElementTree as ET

      #Read XML config file
      configtree = ET.parse(fme.macroValues['CONFIG_FILE'])
      configdoc = configtree.getroot()
      value = configdoc.find('pguser').text

      return value
    _RELATED_CANDIDATES = @Value(_related_candidates)
    LANDKODE = @Value(landkode)
    LOVREFERANSE = @Value(lovreferanse)
    OBJTYPE = @Value(objtype)
    FYLKEID = @Value(fylkeid)
    LOVREFERANSEBESKRIVELSE = @Value(lovreferansebeskrivelse)
    _CREATION_INSTANCE = @Value(_creation_instance)
    _FNR = @Value(_fnr)
    SOSI_FILE = Planomriss
    PLANSTATUS = @Value(planstatus)
    OPPRINNELIGPLANID = @Value(opprinneligplanid)
    PLANBESTEMMELSE = @Value(planbestemmelse)
    GJENNOMFORINGSFRIST = @Value(gjennomforingsfrist)
    VEDTAKENDELIGPLANDATO = @Value(vedtakendeligplandato)
    PG_DB:
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------

      import fme
      from xml.etree import ElementTree as ET

      #Read XML config file
      configtree = ET.parse(fme.macroValues['CONFIG_FILE'])
      configdoc = configtree.getroot()
      value = configdoc.find('pgdb').text

      return value
    PG_PORT:
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------

      import fme
      from xml.etree import ElementTree as ET

      #Read XML config file
      configtree = ET.parse(fme.macroValues['CONFIG_FILE'])
      configdoc = configtree.getroot()
      value = configdoc.find('pgport').text

      return value
    OBJID = @Value(objid)
    PLANNAVN = @Value(plannavn)
    _CLIPPER_FILE = @Value(_clipper_file)
    IKRAFTTREDELSESDATO = @Value(ikrafttredelsesdato)
    OPPRINNELIGADMINISTRATIVENHET = @Value(opprinneligadministrativenhet)
    VERTIKALNIVA = @Value(vertikalniva)
    PLANTYPE = @Value(plantype)
    FYLKESNR = @Value(fylkesnr)
    _CLIPPED = @Value(_clipped)
    KUNNGJORINGSDATO = @Value(kunngjoringsdato)
    OUTPUT_EPSG_CODE = $(OUTPUT_EPSG_CODE)
    PG_HOST:
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------

      import fme
      from xml.etree import ElementTree as ET

      #Read XML config file
      configtree = ET.parse(fme.macroValues['CONFIG_FILE'])
      configdoc = configtree.getroot()
      value = configdoc.find('pghost').text

      return value
    _CLIPPERCOORDS = @Value(_clippercoords)
    PG_PWD:
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------

      import fme
      from xml.etree import ElementTree as ET

      #Read XML config file
      configtree = ET.parse(fme.macroValues['CONFIG_FILE'])
      configdoc = configtree.getroot()
      value = configdoc.find('pgpwd').text

      return value
    -> FeatureTypeFilter

Bookmark: Kobler inn relaterte tabeller
FeatureTypeFilter
    ATTRIBUTES = planomriss.kpomrade,planomriss.kpgrense,planomriss.rpomrade,planomriss.rpgrense,<BLANK>,<UNFILTERED>
    planomriss.kpomrade -> FeatureMerger [input 1]
    planomriss.rpomrade -> FeatureMerger_3 [input 1]
    planomriss.kpomrade -> Tester_5
    planomriss.rpomrade -> Tester_7
Tester_5
    TEST_DESCRIPTION = ""
    TEST_CLAUSE:
      TEST _clipper_file ATTRIBUTE_IS_EMPTY ""
      TEST _clippercoords ATTRIBUTE_IS_EMPTY ""
      TEST _fnr ATTRIBUTE_IS_EMPTY ""
      TEST _knr ATTRIBUTE_IS_EMPTY ""
    TEST_MODE = Automatic
    BOOL_OP = AND
    FAILED -> Aggregator
    PASSED -> Sampler_5
Aggregator
    SEP = ,
    ACCUM_ATTRS_NAME = No
    MODE = Attributes Only
    CONCAT_ATTRS = objid
    ORDERED = No
    AGGREGATE -> AttributeCreator
AttributeCreator
    ATTR_LIST = sql,select * from planomriss.sosi_objekt_planomrade_kp where objid in (@Value(objid));
    -> SQLExecutor
Sampler_5
    RATE = 1
    SAMPLE_TYPE_LONG = First N Features
    SAMPLED -> AttributeCreator_11
AttributeCreator_11
    ATTR_LIST = sql,select * from planomriss.sosi_objekt_planomrade_kp;
    -> SQLExecutor
SQLExecutor
    COMBINE_ATTRS = Result Attributes Only
    POSTGRES_QUERY_FEATURE_TYPES_FOR_MERGE_FILTERS = Yes
    FORMAT = POSTGRES
    POSTGRES_HOST = $(PG_HOST)
    DATASET = $(PG_DB)
    COMBINE_GEOM = Initiator Geometry Only
    POSTGRES_USER_NAME = $(PG_USER)
    SQL_STATEMENT = @Value(sql)
    EXPOSED_ATTRIBUTE_LIST = forstedigitaliseringsdato,informasjon,kpomrade_fk,link,objid,oppdateringsdato,prosess_historie
    POSTGRES_PASSWORD = $(PG_PWD)
    POSTGRES_PORT = $(PG_PORT)
    RESULT -> FeatureMerger [input 2]
FeatureMerger
    IGNORE_NULLS = No
    MERGE_TYPE = Attributes Only
    SUPPLIERS_FIRST = No
    LIST_NAME = _list
    ATTR_CONFLICT_RES = Use Requestor
    GEOM_TYPE = Build Polygons
    ATTR_ACCUM_MODE = Merge Supplier
    JOIN_KEYS = @Value(objid) @Value(kpomrade_fk) AUTO
    PROCESS_DUPS = Yes
    MERGED -> AttributeRenamer_3
Tester_7
    TEST_DESCRIPTION = ""
    TEST_CLAUSE:
      TEST _clipper_file ATTRIBUTE_IS_EMPTY ""
      TEST _clippercoords ATTRIBUTE_IS_EMPTY ""
      TEST _fnr ATTRIBUTE_IS_EMPTY ""
      TEST _knr ATTRIBUTE_IS_EMPTY ""
    TEST_MODE = Automatic
    BOOL_OP = AND
    FAILED -> Aggregator_3
    PASSED -> Sampler_3
Aggregator_3
    SEP = ,
    ACCUM_ATTRS_NAME = No
    MODE = Attributes Only
    CONCAT_ATTRS = objid
    ORDERED = No
    AGGREGATE -> AttributeCreator_3
AttributeCreator_3
    ATTR_LIST = sql,select * from planomriss.sosi_objekt_planomrade_rp where objid in (@Value(objid));
    -> SQLExecutor_3
Sampler_3
    RATE = 1
    SAMPLE_TYPE_LONG = First N Features
    SAMPLED -> AttributeCreator_9
AttributeCreator_9
    ATTR_LIST = sql,select * from planomriss.sosi_objekt_planomrade_rp;
    -> SQLExecutor_3
SQLExecutor_3
    COMBINE_ATTRS = Result Attributes Only
    POSTGRES_QUERY_FEATURE_TYPES_FOR_MERGE_FILTERS = Yes
    FORMAT = POSTGRES
    POSTGRES_HOST = $(PG_HOST)
    DATASET = $(PG_DB)
    COMBINE_GEOM = Initiator Geometry Only
    POSTGRES_USER_NAME = $(PG_USER)
    SQL_STATEMENT = @Value(sql)
    EXPOSED_ATTRIBUTE_LIST = forstedigitaliseringsdato,informasjon,link,objid,oppdateringsdato,prosess_historie,rpomrade_fk
    POSTGRES_PASSWORD = $(PG_PWD)
    POSTGRES_PORT = $(PG_PORT)
    RESULT -> FeatureMerger_3 [input 2]
FeatureMerger_3
    IGNORE_NULLS = Yes
    MERGE_TYPE = Attributes Only
    SUPPLIERS_FIRST = No
    LIST_NAME = _list
    ATTR_CONFLICT_RES = Use Requestor
    GEOM_TYPE = Build Polygons
    ATTR_ACCUM_MODE = Merge Supplier
    JOIN_KEYS = @Value(objid) @Value(rpomrade_fk) AUTO
    PROCESS_DUPS = Yes
    MERGED -> AttributeRenamer_4

Bookmark: Kommuneplan
AttributeRenamer_3
    ATTR_LIST = kunngjoringsdato,kunngjøringsdato,,vedtakendeligplandato,vedtakEndeligPlanDato,,komm,arealplanId.NasjonalArealplanId.administrativEnhet.AdministrativEnhetskode.kommunenummer,,lovreferansebeskrivelse,lovreferanseBeskrivelse,,planid,arealplanId.NasjonalArealplanId.planidentifikasjon,,forstedigitaliseringsdato,førsteDigitaliseringsdato,
    -> AttributeValueMapper_7
AttributeValueMapper_7
    SRC = plantype
    DIRECTION = Forward (Source To Destination)
    LUT = 20,Kommuneplanens arealdel,21,Kommunedelplan,22,Mindre endring av kommune(del)plan
    VAL_ATTR = plantype
    -> AttributeValueMapper_8
AttributeValueMapper_8
    SRC = planbestemmelse
    DIRECTION = Forward (Source To Destination)
    LUT = 1,Med bestemmelser som egen tekst,2,Uten bestemmelser,3,Uten bestemmelser,4,Med bestemmelser som egen tekst
    VAL_ATTR = planbestemmelse
    DEFAULT_VALUE = @Value(planbestemmelse)
    -> AttributeValueMapper_10
AttributeValueMapper_10
    SRC = lovreferanse
    DIRECTION = Forward (Source To Destination)
    LUT = 1,Før BL 1924,2,BL 1924,3,BL 1965,4,PBL 1985,5,PBL 1985 eller før,6,PBL 2008
    VAL_ATTR = lovreferanse
    DEFAULT_VALUE = other:
    -> AttributeValueMapper_9
AttributeValueMapper_9
    SRC = planstatus
    DIRECTION = Forward (Source To Destination)
    LUT = 1,Planlegging igangsatt,2,Planforslag,3,Endelig vedtatt arealplan,4,Opphevet,5,Utgått/erstattet,6,Vedtatt plan med utsatt rettsvirkning,7,Endelig vedtatt plan underlagt tidsbegrensning,8,Overstyrt
    VAL_ATTR = planstatus
    -> DateFormatter_2
DateFormatter_2
    FMT = ISO Date (%Y-%m-%d)
    INVALID_DATE_VALUE = _FME_NO_OP_
    DATE_ATTR = ikrafttredelsesdato,kunngjøringsdato,vedtakEndeligPlanDato,gjennomforingsfrist
    SRCFMT = Unknown - Automatic Detection
    -> DateFormatter_3
DateFormatter_3
    FMT = ISO DateTime (%Y-%m-%dT%H:%M:%S)
    INVALID_DATE_VALUE = _FME_NO_OP_
    DATE_ATTR = førsteDigitaliseringsdato,oppdateringsdato
    SRCFMT = Unknown - Automatic Detection
    -> GeometryPropertySetter_2
GeometryPropertySetter_2
    SETTYPE_PARAM = Geometry Name
    OVERWRITE_CHOICE = Yes
    GEOM_NAME_FIELD = område
    SET -> ListRenamer_2
ListRenamer_2
    LEAVE_ORIG = No
    LIST_COMPONENT_NAMES = forstedigitaliseringsdato,forstedigitaliseringsdato{},informasjon,informasjon{},link,link{},objid,objid{},oppdateringsdato,oppdateringsdato{},prosess_historie,prosesshistorie{},rpomrade_fk,rpomrade_fk{}
    LIST_NAME = _list{}
    LIST_ACTION = Promote All Subcomponents
    -> KpOmråde (writer GML_1)
KpOmråde (writer GML_1)
    attributes: førsteDigitaliseringsdato xml_datetime, oppdateringsdato xml_datetime, prosesshistorie{} xml_buffer, informasjon{} xml_buffer, link{} xml_xml, område xml_geometry, posisjon xml_geometry, arealplanId.NasjonalArealplanId.administrativEnhet.AdministrativEnhetskode.kommunenummer xml_buffer, arealplanId.NasjonalArealplanId.administrativEnhet.AdministrativEnhetskode.kommunenummer.codeSpace xml_buffer, arealplanId.NasjonalArealplanId.administrativEnhet.AdministrativEnhetskode.fylkesnummer xml_buffer, arealplanId.NasjonalArealplanId.administrativEnhet.AdministrativEnhetskode.fylkesnummer.codeSpace xml_buffer, arealplanId.NasjonalArealplanId.administrativEnhet.AdministrativEnhetskode.landskode xml_buffer, arealplanId.NasjonalArealplanId.administrativEnhet.AdministrativEnhetskode.landskode.codeSpace xml_buffer, arealplanId.NasjonalArealplanId.planidentifikasjon xml_buffer, plantype xml_buffer, planstatus xml_buffer, planbestemmelse xml_buffer, lovreferanse xml_buffer, lovreferanseBeskrivelse xml_buffer, ikrafttredelsesdato xml_date, plannavn xml_buffer, vedtakEndeligPlanDato xml_date, kunngjøringsdato xml_date, opprinneligplanid xml_buffer, opprinneligadministrativenhet xml_xml, gml_metaDataProperty{}.about xml_buffer, gml_metaDataProperty{}.nilReason xml_buffer, gml_metaDataProperty{}.gml_remoteSchema xml_buffer, gml_metaDataProperty{}.xlink_href xml_buffer, gml_metaDataProperty{}.gml_GenericMetaData xml_xml,
      gml_metaDataProperty{}.gml_GenericMetaData.gml_id xml_buffer, gml_description xml_buffer, gml_description.nilReason xml_buffer, gml_description.gml_remoteSchema xml_buffer, gml_description.xlink_href xml_buffer, gml_descriptionReference.owns xml_boolean, gml_descriptionReference.nilReason xml_buffer, gml_descriptionReference.gml_remoteSchema xml_buffer, gml_descriptionReference.xlink_href xml_buffer, gml_identifier xml_buffer, gml_identifier.codeSpace xml_buffer, gml_name{} xml_buffer, gml_name{}.codeSpace xml_buffer, gml_boundedBy xml_geometry, gml_location xml_geometry

Bookmark: Reguleringsplan
AttributeRenamer_4
    ATTR_LIST = vertikalniva,vertikalnivå,,lovreferansebeskrivelse,lovreferanseBeskrivelse,,gjennomforingsfrist,gjennomføringsfrist,,vedtakendeligplandato,vedtakEndeligPlanDato,,forslagsstillertype,forslagsstillerType,,planid,arealplanId.NasjonalArealplanId.planidentifikasjon,,komm,arealplanId.NasjonalArealplanId.administrativEnhet.AdministrativEnhetskode.kommunenummer,,kunngjoringsdato,kunngjøringsdato,,forstedigitaliseringsdato,førsteDigitaliseringsdato,
    -> DateFormatter
DateFormatter
    FMT = ISO Date (%Y-%m-%d)
    INVALID_DATE_VALUE = _FME_NO_OP_
    DATE_ATTR = ikrafttredelsesdato,kunngjøringsdato,vedtakEndeligPlanDato,gjennomføringsfrist
    SRCFMT = Unknown - Automatic Detection
    -> DateFormatter_4
DateFormatter_4
    FMT = ISO DateTime (%Y-%m-%dT%H:%M:%S)
    INVALID_DATE_VALUE = _FME_NO_OP_
    DATE_ATTR = førsteDigitaliseringsdato,oppdateringsdato
    SRCFMT = Unknown - Automatic Detection
    -> AttributeValueMapper
AttributeValueMapper
    SRC = lovreferanse
    DIRECTION = Forward (Source To Destination)
    LUT = 1,Før BL 1924,2,BL 1924,3,BL 1965,4,PBL 1985,5,PBL 1985 eller før,6,PBL 2008
    VAL_ATTR = lovreferanse
    -> AttributeValueMapper_2
AttributeValueMapper_2
    SRC = plantype
    DIRECTION = Forward (Source To Destination)
    LUT = 30,Eldre reguleringsplan,31,Mindre reguleringsendring,32,Bebyggelsesplan ihht. Reguleringsplan,33,Bebyggelsesplan ihht kommunepl. arealdel,34,Områderegulering,35,Detaljregulering
    VAL_ATTR = plantype
    -> AttributeValueMapper_3
AttributeValueMapper_3
    SRC = planstatus
    DIRECTION = Forward (Source To Destination)
    LUT = 1,Planlegging igangsatt,2,Planforslag,3,Endelig vedtatt arealplan,4,Opphevet,5,Utgått/erstattet,6,Vedtatt plan med utsatt rettsvirkning,7,Endelig vedtatt plan underlagt tidsbegrensning,8,Overstyrt
    VAL_ATTR = planstatus
    DEFAULT_VALUE = other: @Value(planstatus)Ukjent
    -> AttributeValueMapper_4
AttributeValueMapper_4
    SRC = planbestemmelse
    DIRECTION = Forward (Source To Destination)
    LUT = 3,Planbestemmelser fremgår kun av kartet,4,Planbestemmelser både kart og tekst,1,Planbestemmelser både kart og tekst,2,Planbestemmelser fremgår kun av kartet
    VAL_ATTR = planbestemmelse
    -> AttributeValueMapper_5
AttributeValueMapper_5
    SRC = vertikalnivå
    DIRECTION = Forward (Source To Destination)
    LUT = 1,Under grunnen (tunnel),2,På grunnen/vannoverflate,3,Over grunnen (bru),4,På bunnen (vann/sjø),5,I vannsøylen
    VAL_ATTR = vertikalnivå
    -> GeometryPropertySetter
GeometryPropertySetter
    SETTYPE_PARAM = Geometry Name
    OVERWRITE_CHOICE = No
    GEOM_NAME_FIELD = område
    SET -> Tester_12
Tester_12
    TEST_DESCRIPTION = ""
    TEST_CLAUSE:
      TEST gjennomføringsfrist ATTRIBUTE_IS_MISSING ""
      TEST gjennomføringsfrist ATTRIBUTE_IS_EMPTY ""
      TEST gjennomføringsfrist ATTRIBUTE_VALUE_NULL ""
    TEST_MODE = Automatic
    BOOL_OP = OR
    PASSED -> AttributeRemover
    FAILED -> Tester_14
AttributeRemover
    REMOVE_ATTRS = gjennomføringsfrist
    -> Tester_14
Tester_14
    TEST_DESCRIPTION = ""
    TEST_CLAUSE:
      TEST forslagsstillerType ATTRIBUTE_IS_MISSING ""
      TEST forslagsstillerType ATTRIBUTE_IS_EMPTY ""
      TEST forslagsstillerType ATTRIBUTE_VALUE_NULL ""
    TEST_MODE = Automatic
    BOOL_OP = OR
    PASSED -> AttributeRemover_2
    FAILED -> AttributeValueMapper_6
AttributeRemover_2
    REMOVE_ATTRS = forslagsstillerType
    -> ListRenamer
AttributeValueMapper_6
    SRC = forslagsstillerType
    DIRECTION = Forward (Source To Destination)
    LUT = 1,offentlig,2,privat
    VAL_ATTR = forslagsstillerType
    -> ListRenamer
ListRenamer
    LEAVE_ORIG = No
    LIST_COMPONENT_NAMES = forstedigitaliseringsdato,forstedigitaliseringsdato{},informasjon,informasjon{},link,link{},objid,objid{},oppdateringsdato,oppdateringsdato{},prosess_historie,prosesshistorie{},rpomrade_fk,rpomrade_fk{}
    LIST_NAME = _list{}
    LIST_ACTION = Promote All Subcomponents
    -> RpOmråde (writer GML_1)
RpOmråde (writer GML_1)
    attributes: førsteDigitaliseringsdato xml_datetime, oppdateringsdato xml_datetime, prosesshistorie{} xml_buffer, informasjon{} xml_buffer, link{} xml_xml, område xml_geometry, posisjon xml_geometry, arealplanId.NasjonalArealplanId.administrativEnhet.AdministrativEnhetskode.kommunenummer xml_buffer, arealplanId.NasjonalArealplanId.administrativEnhet.AdministrativEnhetskode.kommunenummer.codeSpace xml_buffer, arealplanId.NasjonalArealplanId.administrativEnhet.AdministrativEnhetskode.fylkesnummer xml_buffer, arealplanId.NasjonalArealplanId.administrativEnhet.AdministrativEnhetskode.fylkesnummer.codeSpace xml_buffer, arealplanId.NasjonalArealplanId.administrativEnhet.AdministrativEnhetskode.landskode xml_buffer, arealplanId.NasjonalArealplanId.administrativEnhet.AdministrativEnhetskode.landskode.codeSpace xml_buffer, arealplanId.NasjonalArealplanId.planidentifikasjon xml_buffer, plantype xml_buffer, planstatus xml_buffer, plannavn xml_buffer, planbestemmelse xml_buffer, ikrafttredelsesdato xml_date, vertikalnivå xml_buffer, lovreferanse xml_buffer, lovreferanseBeskrivelse xml_buffer, gjennomføringsfrist xml_date, forslagsstillerType xml_char(9), vedtakEndeligPlanDato xml_date, kunngjøringsdato xml_date, opprinneligplanid xml_buffer, opprinneligadministrativenhet xml_buffer

FME custom transformer CreateClipper

Parameters:
- CLIPPERCOORDS = 253577 6650999 253577 6651246 253763 6651246 253763 6650999 253577 6650999   # Clipper Coordinate List
- CLIPPERCOORDSYS = EPSG:25833   # Clipper Coordinate System
- DESTCOORDSYS = "ESRIWKT|ETRS_1989_UTM_Zone_35N|PROJCS["ETRS_1989_UTM_Zone_35N",GEOGCS["GCS_ETRS_1989",DATUM["D_ETRS_1989",SPHEROID["GRS_1980",6378137.0,298.257222101]],PRIMEM["Greenwich",0.0],UNIT["Degree",0.0174532925199433]],PROJECTION["Transverse_Mercator"],PARAMETER["False_Easting",500000.0],PARAMETER["False_Northing",0.0],PARAMETER["Central_Meridian",27.0],PARAMETER["Scale_Factor",0.9996],PARAMETER["Latitude_Of_Origin",0.0],UNIT["Meter",1.0]]"   # Destination Coordinate System

Note: Creating geometry from / the Clipper coords
Creator
    COORDS = $(CLIPPERCOORDS)
    GEOMTYPE = 2D Coordinate List
    NUM = 1
    COORDSYS = $(CLIPPERCOORDSYS)
    CREATED -> BoundingBoxAccumulator
Note: Calculating the bounding / box (envelope) from the geometry
BoundingBoxAccumulator
    TOPFER_INDEX = No
    BOUNDING_BOX -> SpatialFilter [input 1]
    ORIGINAL -> SpatialFilter [input 2]
Note: If the geometry is equal to its / own bounding box - it is a rectangle!
SpatialFilter
    USE_BOUNDING_BOX = No
    PASS_CRITERIA = Pass Against One Base
    MERGE_ATTRS = No
    PREDATTR = _predicate
    BASE_TYPE = Single Base
    PREDICATES = EQUALS
    CURVE_BOUNDARY_RULE_PARAM = Default Rule
    PASSED -> Reprojector
    FAILED -> Reprojector_2
Note: If rectangle, reproject the / geometry to the destination / coordinate system
Reprojector
    STROKE_ARCS = Yes
    SOURCE = Read from feature
    DEST = $(DESTCOORDSYS)
    RASTER_CELL_SIZE = Preserve Cells
    INTERPOLATION_TYPE_NAME = Nearest Neighbor
    REPROJECTED -> BoundingBoxAccumulator_2
Note: Then calculate the bounding / box from the projected geoemtry
BoundingBoxAccumulator_2
    TOPFER_INDEX = No
    BOUNDING_BOX -> Reprojector_3
Note: Reproject the geometry back to / the DB coordsys (LL/EUREF89)
Reprojector_3
    STROKE_ARCS = Yes
    SOURCE = Read from feature
    DEST = EPSG:4258
    RASTER_CELL_SIZE = Preserve Cells
    INTERPOLATION_TYPE_NAME = Nearest Neighbor
    REPROJECTED -> GeometryFilter
Note: Reproject clipper to / the DB coordsys (LL/EUREF89)
Reprojector_2
    STROKE_ARCS = Yes
    SOURCE = Read from feature
    DEST = EPSG:4258
    RASTER_CELL_SIZE = Preserve Cells
    INTERPOLATION_TYPE_NAME = Nearest Neighbor
    REPROJECTED -> GeometryFilter
Note: Getting rid of dummies
GeometryFilter
    BREAK_AGG = No
    GEOM_PORT_NAMES = Area
    AREA -> Output (output)
Output (output)

FME custom transformer SosiFilenameSetter

Parameters:
- OUTPUT_EPSG_CODE = 25832   # Destination coordinate system
- FANOUT = Kommuner   # Fanout områder
- KOMMUNEID = @Value(kommuneid)   # kommuneid
- FYLKEID = @Value(fylkeid)   # fylkeid
- _CLIPPED = @Value(_clipped)   # Clipped
- _CLIPPER_FILE = @Value(_clipper_file)   # Clipper File
- _CLIPPERCOORDS = @Value(_clippercoords)   # Clippercoords
- _CREATION_INSTANCE = @Value(_creation_instance)   # Creation Instance
- _FNR = @Value(_fnr)   # Fnr
- _KNR = @Value(_knr)   # Knr
- _RELATED_CANDIDATES = @Value(_related_candidates)   # Related Candidates
- FORSLAGSSTILLERTYPE = @Value(forslagsstillertype)   # forslagsstillertype
- FYLKESNR = @Value(fylkesnr)   # fylkesnr
- GJENNOMFORINGSFRIST = @Value(gjennomforingsfrist)   # gjennomforingsfrist
- IKRAFTTREDELSESDATO = @Value(ikrafttredelsesdato)   # ikrafttredelsesdato
- KOMM = @Value(komm)   # komm
- KUNNGJORINGSDATO = @Value(kunngjoringsdato)   # kunngjoringsdato
- LANDKODE = @Value(landkode)   # landkode
- LOVREFERANSE = @Value(lovreferanse)   # lovreferanse
- LOVREFERANSEBESKRIVELSE = @Value(lovreferansebeskrivelse)   # lovreferansebeskrivelse
- OBJID = @Value(objid)   # objid
- OBJTYPE = @Value(objtype)   # objtype
- OPPRINNELIGADMINISTRATIVENHET = @Value(opprinneligadministrativenhet)   # opprinneligadministrativenhet
- OPPRINNELIGPLANID = @Value(opprinneligplanid)   # opprinneligplanid
- PLANBESTEMMELSE = @Value(planbestemmelse)   # planbestemmelse
- PLANID = @Value(planid)   # planid
- PLANNAVN = @Value(plannavn)   # plannavn
- PLANSTATUS = @Value(planstatus)   # planstatus
- PLANTYPE = @Value(plantype)   # plantype
- VEDTAKENDELIGPLANDATO = @Value(vedtakendeligplandato)   # vedtakendeligplandato
- VERTIKALNIVA = @Value(vertikalniva)   # vertikalniva
- PG_DB:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgdb').text
      
      return value
- PG_HOST:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pghost').text
      
      return value
- PG_PORT:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgport').text
      
      return value
- PG_PWD:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgpwd').text
      
      return value
- PG_USER:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pguser').text
      
      return value
- SOSI_FILE = Planomriss   # SOSI file

Input (input)
    -> ParameterFetcher
ParameterFetcher
    ATTR_LIST = _output_epsg_code {$(OUTPUT_EPSG_CODE)} _fanout {$(FANOUT)}
    -> AttributeValueMapper
Note: Fikser kjente feil i kommunenummer
AttributeValueMapper
    SRC = kommuneid
    DIRECTION = Forward (Source To Destination)
    LUT = 1901,1903
    VAL_ATTR = kommuneid
    DEFAULT_VALUE = @Value(kommuneid)
    -> TestFilter_2
TestFilter_2
    TEST_LIST = BOOL_OP,OR,COMPOSITE_TEST,<Unused>,TEST_CLAUSE,"TEST $(FANOUT) = Kommuner",Kommuner,BOOL_OP,OR,COMPOSITE_TEST,<Unused>,TEST_CLAUSE,"TEST $(FANOUT) = Fylker",Fylker
    DEFAULT_VALUE = Ufiltrert
    Kommuner -> Joiner
    Ufiltrert -> AttributeCreator_13
    Fylker -> Joiner_2
Joiner
    POSTGIS_HOST = $(PG_HOST)
    CACHE_SIZE = 5000
    ADDED_FIELDS = navn
    FORMAT = POSTGIS
    MATCH_RULE_DISPLAY = Must Match Exactly One (1:1)
    POSTGIS_PASSWORD = $(PG_PWD)
    POSTGIS_PORT = $(PG_PORT)
    PREFETCH_EXHAUSTIVE = Yes
    POSTGIS_USER_NAME = $(PG_USER)
    DATASET = $(PG_DB)
    POSTGIS_QUERY_FEATURE_TYPES_FOR_MERGE_FILTERS = Yes
    JOIN_KEYS = kommuneid kommuneid
    POSTGIS_USE_TRUE_POSTGIS_TYPES = yes
    TABLE = admingrense.kommuner
    POSTGIS_DISABLE_COLLECTION_SPLITTING = yes
    JOINED -> StringReplacer
Joiner_2
    POSTGIS_HOST = $(PG_HOST)
    CACHE_SIZE = 5000
    ADDED_FIELDS = navn
    FORMAT = POSTGIS
    MATCH_RULE_DISPLAY = Must Match Exactly One (1:1)
    POSTGIS_PASSWORD = $(PG_PWD)
    POSTGIS_PORT = $(PG_PORT)
    PREFETCH_EXHAUSTIVE = Yes
    POSTGIS_USER_NAME = $(PG_USER)
    DATASET = $(PG_DB)
    POSTGIS_QUERY_FEATURE_TYPES_FOR_MERGE_FILTERS = Yes
    JOIN_KEYS = fylkeid fylkeid
    POSTGIS_USE_TRUE_POSTGIS_TYPES = yes
    TABLE = admingrense.fylkeflate
    POSTGIS_DISABLE_COLLECTION_SPLITTING = yes
    JOINED -> StringReplacer
StringReplacer
    CASE = no
    FIND_TEXT = " "
    REGEXP = no
    NO_MATCH = _FME_NO_OP_
    SRC_ATTRS = navn
    REPLACE_TEXT = _
    -> AttributeCreator_13
AttributeCreator_13
    ATTR_LIST = sosifile,"FME_CONDITIONAL:DEFAULT_VALUE'Arealplaner_$(OUTPUT_EPSG_CODE)_$(SOSI_FILE)_GML'BOOL_OP;OR;COMPOSITE_TEST;<Unused>;TEST $(FANOUT) LIKE Kommuner'Arealplaner_@PadLeft(@Value(kommuneid),4,0)_@Value(navn)_$(OUTPUT_EPSG_CODE)_$(SOSI_FILE)_GML'BOOL_OP;OR;COMPOSITE_TEST;<Unused>;TEST $(FANOUT) LIKE Fylker'Arealplaner_@PadLeft(@Value(fylkeid),2,0)_@Value(navn)_$(OUTPUT_EPSG_CODE)_$(SOSI_FILE)_GML'BOOL_OP;OR;COMPOSITE_TEST;<Unused>;TEST $(FANOUT) LIKE Norge'Arealplaner_Norge_$(OUTPUT_EPSG_CODE)_$(SOSI_FILE)_GML'FME_NUM_CONDITIONS4___"
    -> Output (output)
Output (output)
