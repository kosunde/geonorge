FME workspace Planomriss_AtomFeedGML.fmw
Title: Planomriss GML ATOM Data Download Feed
Description: Planomriss
Requirements: FME 2015.0+
History: 23/02/2015,N Wlock,Created

Parameters:
- CONFIG_FILE:   # Python Script
      #-------------------------------------------------------------------------------
      # Name:        GetConfigFile
      # Purpose:
      #
      # Author:      xsunknu
      #
      # Created:     21.08.2015
      # Copyright:   (c) xsunknu 2015
      # Licence:     <your licence>
      #-------------------------------------------------------------------------------
      
      import os, fme
      
      fmwdir = fme.macroValues['FME_MF_DIR']
      fmwfile = fme.macroValues['FME_MF_NAME']
      
      fmwfile = os.path.join(fmwdir, fmwfile)
      configfile = os.path.splitext(fmwfile)[0] + '_config.xml'
      
      return configfile
- DESCRIPTION:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('description').text
      
      return value
- TITLE:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('title').text
      
      return value
- AUTHOR:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('author').text
      
      return value
- COPYRIGHT:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('copyright').text
      
      return value
- HTTPPATH:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('httppath').text
      
      return value
- UNCPATH:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('uncpath').text
      
      return value
- HOVEDTEMA:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('hovedtema').text
      
      return value
- UNDERTEMA:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('undertema').text
      
      return value
- PG_DB:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgdb').text
      
      return value
- FORMAT:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('format').text
      
      return value
- EXTENSION:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('extension').text
      
      return value
- GENERATORURL:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('generatoruri').text
      
      return value
- UPDATED:   # Python Script
      #-------------------------------------------------------------------------------
      # Name:        GetUTCTimeStamp
      # Purpose:
      #
      # Author:      xsunknu
      #
      # Created:     25.09.2015
      # Copyright:   (c) xsunknu 2015
      # Licence:     <your licence>
      #-------------------------------------------------------------------------------
      
      import datetime
      
      # Finner og formaterer Zulu-tid (UTC)
      ztime = datetime.datetime.utcnow()
      timestring = ztime.strftime('%Y-%m-%dT%H:%MZ')
      
      return timestring
- LINKURL:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('linkuri').text
      
      return value
- FMEVERSION:   # Python Script
      #-------------------------------------------------------------------------------
      # Name:        GetFMEVerrsion
      #
      # Author:      xsunknu
      #
      # Created:     25.92015
      # Copyright:   (c) xsunknu 2015
      # Licence:     <your licence>
      #-------------------------------------------------------------------------------
      
      import os, fme
      
      fmeversion = fme.macroValues['FME_PRODUCT_NAME'].split(' ')[1]
      
      return fmeversion

Readers:
- POSTGRES_1: POSTGRES from $(PG_DB)

Writers:
- GEORSS_1: GEORSS to D:\scratch\Skytebanestoysone_AtomFeed.xml

Entry (writer GEORSS_1)

Bookmark: Feed
Creator_2
    NUM = 1
    GEOMTYPE = Geometry Object
    CREATED -> AttributeCreator
AttributeCreator
    ATTR_LIST = Title,$(TITLE),Description,$(DESCRIPTION),LinkURI,$(LINKURL),Id,$(LINKURL),LastUpdate,$(UPDATED),LinkRelation,self,LinkType,application/atom+xml,Copyright,$(COPYRIGHT),GeneratorURI,$(GENERATORURL),GeneratorVersion,$(FMEVERSION)
    -> Feed (writer GEORSS_1)
Feed (writer GEORSS_1)

Bookmark: Hele landet
Note: Lager nedlastingsURL for hele landet
Note: Sjekker om fila eksisterer
Creator_3
    NUM = 1
    GEOMTYPE = Geometry Object
    CREATED -> AttributeCreator_10

Bookmark: Set Up Entry Content with Download Link
AttributeCreator_10
    ATTR_LIST = koordsys,25833
    -> PythonCaller_2
PythonCaller_2
    PYTHONSOURCE:
      import fme
      import fmeobjects
      import os, time

      def FileExists(feature):
          uncpath = fme.macroValues['UNCPATH']
          hovedtema = fme.macroValues['HOVEDTEMA']
          undertema = fme.macroValues['UNDERTEMA']
          format = fme.macroValues['FORMAT']
          extension = fme.macroValues['EXTENSION']

          koordsys = str(feature.getAttribute("koordsys"))

          fn = hovedtema + '_0000_Norge_25833_' + undertema + '_' + format + extension
          filename = os.path.join(uncpath, fn)

          if os.path.isfile(filename):
              exists = 1
              file_updated = time.ctime(os.lstat(filename).st_mtime)
              feature.setAttribute("file_updated", file_updated)
          else:
              exists = 0

          feature.setAttribute("exists", exists)
    PYTHONSYMBOL = FileExists
    NEW_ATTRIBUTES = exists file_updated
    -> Tester_3
Tester_3
    TEST_DESCRIPTION = ""
    BOOL_OP = OR
    TEST_CLAUSE = TEST @Value(exists) = 1
    TEST_MODE = Automatic
    PASSED -> DateFormatter_3
DateFormatter_3
    INVALID_DATE_VALUE = _FME_NO_OP_
    DATE_ATTR = file_updated
    FMT = ISO DateTime (%Y-%m-%dT%H:%M:%S)
    SRCFMT = Unknown - Automatic Detection
    -> AttributeCreator_5
AttributeCreator_5
    ATTR_LIST = DownloadUrl,$(HTTPPATH)$(HOVEDTEMA)_0000_Norge_@Value(koordsys)_$(UNDERTEMA)_$(FORMAT)$(EXTENSION),name,$(TITLE) - Norge,value,$(DESCRIPTION), Landsdekkende
    -> AttributeCreator_2
AttributeCreator_2
    ATTR_LIST = Title,@Value(value),Content,Trykk på linken for å laste ned landsdekkende data i koordinatsystemet EPSG:25833. <br />  <a href="@Value(DownloadUrl)">@Value(value)<\a>,Description,$(DESCRIPTION). Trykk på linken for nedlasting: @Value(value),ContentType,html,LastUpdate,@Value(file_updated),Id,@Value(DownloadUrl)_@Value(file_updated),Category{0}.Category,EPSG:25833,Category{0}.Domain,http://www.opengis.net/def/crs/,Category{0}.Label,EPSG/0/25833,Author,$(AUTHOR),Copyright,$(COPYRIGHT),LinkURI,@Value(DownloadUrl),LinkType,application/gml+xml;version=3.2.1,LinkTitle,Datasettet som GML-fil i EPSG:@Value(koordsys),LinkRelation,alternate
    -> Entry (writer GEORSS_1)

Bookmark: Fylker
admingrense.fylker (reader POSTGRES_1)
    attributes: fylkeid int2,PRIKEY, navn varchar(80)
    -> StringReplacer
StringReplacer
    REPLACE_TEXT = _
    FIND_TEXT = " "
    REGEXP = no
    CASE = no
    NO_MATCH = _FME_NO_OP_
    SRC_ATTRS = navn
    -> AttributeCreator_8
AttributeCreator_8
    ATTR_LIST = koordsys,"FME_CONDITIONAL:DEFAULT_VALUE'_FME_NO_OP_'BOOL_OP;OR;COMPOSITE_TEST;<Unused>;TEST @Value(fylkeid) IN 1-17'25832'BOOL_OP;OR;COMPOSITE_TEST;<Unused>;TEST @Value(fylkeid) IN 18-19'25833'BOOL_OP;OR;COMPOSITE_TEST;<Unused>;TEST @Value(fylkeid) IN 20'25835'FME_NUM_CONDITIONS4___"
    -> PythonCaller_5
Note: Sjekker om fila eksisterer
PythonCaller_5
    PYTHONSOURCE:
      # -*- coding: utf-8 -*-
      import fme
      import fmeobjects
      import os, time

      def FileExists(feature):
          uncpath = fme.macroValues['UNCPATH']
          hovedtema = fme.macroValues['HOVEDTEMA']
          undertema = fme.macroValues['UNDERTEMA']
          format = fme.macroValues['FORMAT']
          extension = fme.macroValues['EXTENSION']

          fylkeid = str(feature.getAttribute("fylkeid")).zfill(2)

          navn = feature.getAttribute("navn").replace(' ','_')
          navn = navn.replace(u'\xc6', 'E')
          navn = navn.replace(u'\xd8', 'O')
          navn = navn.replace(u'\xc5', 'A')
          navn = navn.replace(u'\xe6', 'e')
          navn = navn.replace(u'\xf8', 'o')
          navn = navn.replace(u'\xe5', 'a')

          koordsys = str(feature.getAttribute("koordsys"))

          fn = hovedtema + '_' + fylkeid + '_' + navn + '_' + koordsys + '_' + undertema + '_' + format + extension
          filename = os.path.join(uncpath, fn)

          if os.path.isfile(filename):
              exists = 1
              file_updated = time.ctime(os.lstat(filename).st_mtime)
              feature.setAttribute("file_updated", file_updated)
          else:
              exists = 0

          feature.setAttribute("exists", exists)
      #    feature.setAttribute("navn", navn)
    PYTHONSYMBOL = FileExists
    NEW_ATTRIBUTES = exists file_updated
    -> Tester_2
Tester_2
    TEST_DESCRIPTION = ""
    BOOL_OP = OR
    TEST_CLAUSE = TEST @Value(exists) = 1
    TEST_MODE = Automatic
    PASSED -> DateFormatter_2
DateFormatter_2
    INVALID_DATE_VALUE = _FME_NO_OP_
    DATE_ATTR = file_updated
    FMT = ISO DateTime (%Y-%m-%dT%H:%M:%S)
    SRCFMT = Unknown - Automatic Detection
    -> AttributeCreator_3
Note: Lager nedlastingsURL
AttributeCreator_3
    ATTR_LIST = value,$(DESCRIPTION), @PadLeft(@Value(fylkeid),2,0) @Value(navn),DownloadUrl,$(HTTPPATH)$(HOVEDTEMA)_@PadLeft(@Value(fylkeid),2,0)_@Value(navn)_@Value(koordsys)_$(UNDERTEMA)_$(FORMAT)$(EXTENSION),name,$(TITLE)
    -> AttributeCreator_4
AttributeCreator_4
    ATTR_LIST = Title,@Value(value),Content,Trykk på linken for å laste ned data for fylke @PadLeft(@Value(fylkeid),2,0), @Value(navn) i koordinatsystemet EPSG:@Value(koordsys). <br />  <a href="@Value(DownloadUrl)">@Value(value)<\a>,Description,$(DESCRIPTION),ContentType,html,LastUpdate,@Value(file_updated),Id,@Value(DownloadUrl)_@Value(file_updated),Category{0}.Category,EPSG:@Value(koordsys),Category{0}.Domain,http://www.opengis.net/def/crs/,Category{0}.Label,EPSG/0/@Value(koordsys),Author,$(AUTHOR),Copyright,$(COPYRIGHT),LinkURI,@Value(DownloadUrl),Category{1}.Category,Fylke,Category{1}.Label,@Value(navn),LinkType,application/gml+xml;version=3.2.1,LinkTitle,Datasettet som GML-fil i EPSG:@Value(koordsys),LinkRelation,alternate
    -> Entry (writer GEORSS_1)

Bookmark: Kommuner
admingrense.kommuner (reader POSTGRES_1)
    attributes: kommuneid int2,PRIKEY, navn varchar(80)
    -> StringReplacer_2
StringReplacer_2
    REPLACE_TEXT = _
    FIND_TEXT = " "
    REGEXP = no
    CASE = no
    NO_MATCH = _FME_NO_OP_
    SRC_ATTRS = navn
    -> AttributeCreator_9
AttributeCreator_9
    ATTR_LIST = koordsys,"FME_CONDITIONAL:DEFAULT_VALUE'_FME_NO_OP_'BOOL_OP;OR;COMPOSITE_TEST;<Unused>;TEST @Value(kommuneid) IN 100-1799'25832'BOOL_OP;OR;COMPOSITE_TEST;<Unused>;TEST @Value(kommuneid) IN 1800-1999'25833'BOOL_OP;OR;COMPOSITE_TEST;<Unused>;TEST @Value(kommuneid) IN 2000-2099'25835'FME_NUM_CONDITIONS4___"
    -> PythonCaller_4
Note: Sjekker om fila eksisterer
PythonCaller_4
    PYTHONSOURCE:
      import fme
      import fmeobjects
      import os

      def FileExists(feature):
          uncpath = fme.macroValues['UNCPATH']
          hovedtema = fme.macroValues['HOVEDTEMA']
          undertema = fme.macroValues['UNDERTEMA']
          format = fme.macroValues['FORMAT']
          extension = fme.macroValues['EXTENSION']

          kommuneid = str(feature.getAttribute("kommuneid")).zfill(4)

          navn = feature.getAttribute("navn").replace(' ','_')
          navn = navn.replace(u'\xc6', 'E')
          navn = navn.replace(u'\xd8', 'O')
          navn = navn.replace(u'\xc5', 'A')
          navn = navn.replace(u'\xe6', 'e')
          navn = navn.replace(u'\xf8', 'o')
          navn = navn.replace(u'\xe5', 'a')

          koordsys = str(feature.getAttribute("koordsys"))

          fn = hovedtema + '_' + kommuneid + '_' + navn + '_' + koordsys + '_' + undertema + '_' + format + extension
          filename = os.path.join(uncpath, fn)

          if os.path.isfile(filename):
              exists = 1
              file_updated = time.ctime(os.path.getmtime(filename))
              feature.setAttribute("file_updated", file_updated)
          else:
              exists = 0

          feature.setAttribute("exists", exists)
      #    feature.setAttribute("navn", navn)
    PYTHONSYMBOL = FileExists
    NEW_ATTRIBUTES = exists file_updated
    -> Tester
Tester
    TEST_DESCRIPTION = ""
    BOOL_OP = OR
    TEST_CLAUSE = TEST @Value(exists) = 1
    TEST_MODE = Automatic
    PASSED -> DateFormatter
DateFormatter
    INVALID_DATE_VALUE = _FME_NO_OP_
    DATE_ATTR = file_updated
    FMT = ISO DateTime (%Y-%m-%dT%H:%M:%S)
    SRCFMT = Unknown - Automatic Detection
    -> AttributeCreator_6
Note: Lager nedlastingsURL
AttributeCreator_6
    ATTR_LIST = DownloadUrl,$(HTTPPATH)$(HOVEDTEMA)_@PadLeft(@Value(kommuneid),4,0)_@Value(navn)_@Value(koordsys)_$(UNDERTEMA)_$(FORMAT)$(EXTENSION),name,$(TITLE),value,$(DESCRIPTION),  @PadLeft(@Value(kommuneid),4,0), @Value(navn)
    -> AttributeCreator_7
AttributeCreator_7
    ATTR_LIST = Title,@Value(value),Content,Trykk på linken for å laste ned data for kommune @PadLeft(@Value(kommuneid),4,0), @Value(navn) i koordinatsystemet EPSG:@Value(koordsys). <br />  <a href="@Value(DownloadUrl)">@Value(value)<\a>,Description,$(DESCRIPTION). Trykk på linken for nedlasting: @Value(value),ContentType,html,LastUpdate,@Value(file_updated),Id,@Value(DownloadUrl)_@Value(file_updated),Category{0}.Category,EPSG:@Value(koordsys),Category{0}.Domain,http://www.opengis.net/def/crs/,Category{0}.Label,EPSG/0/@Value(koordsys),Author,$(AUTHOR),Copyright,DSB - Sivilforsvaret og brannvesenet.,LinkURI,@Value(DownloadUrl),Category{1}.Category,Kommune,Category{1}.Label,@Value(navn),LinkType,application/gml+xml;version=3.2.1,LinkTitle,Datasettet som GML-fil i EPSG:@Value(koordsys),LinkRelation,alternate
    -> Entry (writer GEORSS_1)
