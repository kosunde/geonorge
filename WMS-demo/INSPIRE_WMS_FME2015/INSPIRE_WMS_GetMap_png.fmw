FME workspace INSPIRE_WMS_GetMap_png.fmw
Title: INSPIRE_WMS.fmw
Description: This WMS workspace reads from an INSPIRE staging PostGIS database and uses WFS to publish GML via the data streaming service, based on the query parameters provided by the WFS client. The Loader workspaces (INSPIRE_WFS_A1.CadastralParcels.Loader.fmw, INSPIRE_WFS_A1.GeoNames.Loader.fmw) handle data loading, reprojection and schema mapping to the databases 'INSPIRE like' data model. 
INSPIRE_WFS.fmw is a WFS 'service broker' workspace. This just needs to be published to the data streaming service and will accept WFS GET or POST requests (GetCapabilities, DescribeFeature and GetFeatrue) and generate the appropriate responses as XML or GML data streams (GetCapabilities, Describe feature XML docs or GML features). Supports XMLfilters which is something our built in WFS did not do. 
Also, configured to support FME Data Inspector as a WFS client. Note that 
this requires FME Server 2014 or later to function. This is required 
to support the new GML writer.
Requirements: FME 2014 14229+
History: 1/8/2014,Dean,Created / published

Parameters:
- SERVICE = WMS   # Service
- REQUEST = GetMap   # Request
- VERSION = 1.1.1   # Version
- LAYERS = NamedPlace   # Layer
- _WorkspaceURL = $(FME_SERVER_WEB_URL)/fmedatastreaming/INSPIRE/INSPIRE_WMS.fmw   # Workspace URL
- bboxWest = 0   # Bounding box - minimum X coordinate
- bboxSouth = 35   # Bounding box - minimum Y coordinate
- bboxEast = 25   # Bounding box - maximum X coordinate
- bboxNorth = 47   # Bounding box - maximum Y coordinate
- bboxCRS =   # Bounding box - coordinate system
- BBOX = 0%252C30%252C10%252C50   # Bounding box
- MAXFEATURES = 5000   # MaxFeatures
- WIDTH = 1500   # Width
- HEIGHT = 1500   # Height
- DestDataset_PNGRASTER = $(FME_MF_DIR)output_Jan_2015   # Destination PNG (Portable Network Graphics) Directory
- FORMAT = image/png   # Format

Readers:
- TEXTLINE_1: TEXTLINE from \\bester\pserv\Projects\INSPIRE\Demos\WebServices\WMSservice\WMS_SDF\source_get.txt

Writers:
- PNGRASTER_1: PNGRASTER to $(DestDataset_PNGRASTER) in LL84

Bookmark: Client Input
text_line (reader TEXTLINE_1)
    attributes: text_line_data buffer
    -> Logger_text_line
    -> ParameterFetcher
Logger_text_line
    MAXCOORDS = 20
    MESSAGE = Source text stream feature is:
    MAXFEATS = 2

Bookmark: Process GET Request
ParameterFetcher
    ATTR_LIST = _VERSION {$(VERSION)} _REQUEST {$(REQUEST)} _SERVICE {$(SERVICE)} _LAYERS {$(LAYERS)} _BBOX {$(BBOX)} _bboxWest {$(bboxWest)}
    -> TestFilter
TestFilter
    TEST_LIST = BOOL_OP,OR,COMPOSITE_TEST,<Unused>,TEST_CLAUSE,"TEST @Value(_REQUEST) LIKE GetCapabilities",GetCapabilities,BOOL_OP,OR,COMPOSITE_TEST,<Unused>,TEST_CLAUSE,"TEST @Value(_REQUEST) LIKE GetMap",GetMap
    DEFAULT_VALUE = <UNFILTERED>
    GetMap -> AttributeFilter
    GetCapabilities -> TestFilter_GetCapabilities

Bookmark: Error Response
TestFilter_GetCapabilities: Logger
    MAXCOORDS = 20
    MESSAGE = ERROR Feature is:
    MAXFEATS = 20

Bookmark: GetMap Request
AttributeFilter
    ATTR_NAME = _LAYERS
    ATTR_VALUES = NamedPlace,CadastralParcel,<EMPTY>,<MISSING>,<NULL>,<UNFILTERED>
    NamedPlace -> NamedPlace
    CadastralParcel -> CadastralParcel
NamedPlace
    bboxWest = $(bboxWest)
    BBOX = $(BBOX)
    bboxNorth = $(bboxNorth)
    POSTbody = text_line_data
    bboxEast = $(bboxEast)
    bboxSouth = $(bboxSouth)
    NamedPlace -> MapnikRasterizer [input 1]
CadastralParcel
    bboxWest = $(bboxWest)
    BBOX = $(BBOX)
    bboxNorth = $(bboxNorth)
    bboxEast = $(bboxEast)
    bboxSouth = $(bboxSouth)
    CadastralParcel -> MapnikRasterizer [input 2]

Bookmark: Style Layers
MapnikRasterizer
    INTERPRETATION_TYPE = RGBA32
    BACKGROUND_COLOR = 1,1,1
    MAPNIK_CONFIG = NamedPlace;text;text-properties-group;;name;name_geographicalname_spelling_spellingofname_text;face-name;Tahoma,Normal;size;8;color-group;;fill;0,0.333333,1;opacity;1;halo-fill;1,1,1;halo-radius;0;positioning-group;;text-ratio;0;wrap-width;0;wrap-before;No;spacing;0;character-spacing;0;line-spacing;0;label-position-tolerance;0;dx;0;dy;0;avoid-edges;Yes;minimum-distance;0;minimum-padding;0;minimum-path-length;0;allow-overlap;No;orientation;0;placement;point;placement-type;dummy;placements;<Unused>;max-char-angle-delta;<Unused>;horizontal-alignment;auto;justify-alignment;auto;vertical-alignment;auto;comp-group;;comp-op;src-over;CadastralParcel;polygon;color-group;;fill;0,0.666667,0;fill-opacity;1;smoothing-group;;gamma;1;gamma-method;power;smooth;0;comp-group;;comp-op;src-over
    NUM_ROWS = $(HEIGHT)
    BACKGROUND_COLOR_ALPHA = 1.0
    SPECIFY_GROUND_EXTENTS = Use input data ground extents
    NUM_COLUMNS = $(WIDTH)
    COLROW_OR_SPACING = Columns and Rows
    RASTER -> ParameterFetcher_3

Bookmark: Output to WMS Image
ParameterFetcher_3
    ATTR_LIST = _VERSION {$(VERSION)} _REQUEST {$(REQUEST)} _SERVICE {$(SERVICE)} _LAYERS {$(LAYERS)} _BBOX {$(BBOX)} _bboxWest {$(bboxWest)}
    -> GetMapResult (writer PNGRASTER_1)
GetMapResult (writer PNGRASTER_1)

FME custom transformer GetBBOX
Generate bounding box depending on values of bbox parameters

Parameters:
- bboxWest =   # Bounding box - minimum X coordinate
- bboxSouth =   # Bounding box - minimum Y coordinate
- bboxEast =   # Bounding box - maximum X coordinate
- bboxNorth =   # Bounding box - maximum Y coordinate
- BBOX =

INPUT (input)
    -> ParameterFetcher

Bookmark: Determine BBox Type
ParameterFetcher
    ATTR_LIST = _BBOX {$(BBOX)} _bboxWest {$(bboxWest)} _bboxSouth {$(bboxSouth)} _bboxEast {$(bboxEast)} _bboxNorth {$(bboxNorth)}
    -> AttributeExposer
AttributeExposer
    ATTR_LIST = _bbox.coord{0},_bbox.coord{1},_bbox.coord{2},_bbox.coord{3},_bbox.coord{4}
    -> TestFilter_2
TestFilter_2
    TEST_LIST = BOOL_OP,OR,COMPOSITE_TEST,<Unused>,TEST_CLAUSE,"TEST @Value(_BBOX) != """"",BBOX,BOOL_OP,OR,COMPOSITE_TEST,<Unused>,TEST_CLAUSE,"TEST @Value(_bboxWest) != """"",bboxCoords
    DEFAULT_VALUE = <UNFILTERED>
    bboxCoords -> 2DBoxReplacer_coords
    BBOX -> Tester_7
    <UNFILTERED> -> <UNFILTERED> (output)
<UNFILTERED> (output)

Bookmark: Generate BBox Polygon from Parameters
Tester_7
    TEST_MODE = Automatic
    TEST_DESCRIPTION = ""
    TEST_CLAUSE = TEST @Value(_BBOX) NOT_CONTAINS %
    BOOL_OP = OR
    PASSED -> AttributeSplitter_2
    FAILED -> TextDecoder_2
TextDecoder_2
    ENCODING_TYPE = URL (Percent Encoding)
    STRING_TO_DECODE = @Value(_BBOX)
    DEST_ATTR = _BBOX
    -> Tester_2
AttributeSplitter_2
    ATTR_NAME = _BBOX
    DELIMITER = ,
    TRIM_OPTION = Both
    DROP_EMPTY_PARTS = No
    LIST_NAME = _bbox.coord
    -> AttributeCopier
AttributeCopier
    ATTR_LIST = Xmin,_bbox.coord{0},Ymin,_bbox.coord{1},Xmax,_bbox.coord{2},Ymax,_bbox.coord{3},epsg,_bbox.coord{4}
    -> 2DBoxReplacer_bbox
2DBoxReplacer_bbox
    MINXVALATTR = @Value(Xmin)
    MINYVALATTR = @Value(Ymin)
    MAXXVALATTR = @Value(Xmax)
    MAXYVALATTR = @Value(Ymax)
    BOX -> BBox (output)
2DBoxReplacer_coords
    MINXVALATTR = $(bboxWest)
    MINYVALATTR = $(bboxSouth)
    MAXXVALATTR = $(bboxEast)
    MAXYVALATTR = $(bboxNorth)
    BOX -> BBox (output)
BBox (output)

Bookmark: Double encoding bug from FME WMS
Tester_2
    TEST_MODE = Automatic
    TEST_DESCRIPTION = ""
    TEST_CLAUSE = TEST @Value(_BBOX) NOT_CONTAINS %
    BOOL_OP = OR
    PASSED -> AttributeSplitter_2
    FAILED -> TextDecoder_3
TextDecoder_3
    ENCODING_TYPE = URL (Percent Encoding)
    STRING_TO_DECODE = @Value(_BBOX)
    DEST_ATTR = _BBOX
    -> AttributeSplitter_2

FME custom transformer CadastralParcel
Cadastral Parcel GET request handling

Parameters:
- bboxWest =   # Bounding box - minimum X coordinate
- bboxSouth =   # Bounding box - minimum Y coordinate
- bboxEast =   # Bounding box - maximum X coordinate
- bboxNorth =   # Bounding box - maximum Y coordinate
- BBOX =   # Bounding box

GetFeature_GET (input)
    -> GetBBOX
CadastralParcel (output)

Bookmark: Parse GetFeature
GetBBOX
    bboxWest = $(bboxWest)
    BBOX = $(BBOX)
    bboxNorth = $(bboxNorth)
    bboxEast = $(bboxEast)
    bboxSouth = $(bboxSouth)
    BBox -> FeatureReader_3
    <UNFILTERED> -> FeatureReader_3

Bookmark: Query database and apply extent filter
FeatureReader_3
    SDF3_TABLELIST = CadastralParcel
    DATASET = \\bester\pserv\Projects\INSPIRE\Demos\WebServices\WMSservice\WMS_SDF\INSPIREdb.sdf
    SUPPORTED_SPATIAL_INTERACTIONS = ENVELOPE_INTERSECT%ENVELOPE_INTERSECT%INTERSECTS%CONTAINS%CROSSES%DISJOINT%EQUALS%OVERLAPS%TOUCHES%WITHIN
    SDF3_DUMMY = YES
    COMBINE_ATTRS = Keep result attributes only
    COMBINE_GEOM = Keep result geometry only
    SDF3_REMOVE_SCHEMA_QUALIFIER = YES
    FEATURETYPES = CadastralParcel
    FORMAT = SDF3
    ATTRIBUTES = CadastralParcel,"gml_parent_id,gml_id,areavalue,areavalue_nilreason,areavalue_uom,areavalue_xsi_nil,beginlifespanversion,beginlifespanversion_nilreason,beginlifespanversion_xsi_nil,endlifespanversion,endlifespanversion_nilreason,endlifespanversion_xsi_nil,geometry,inspireid_identifier_localid,inspireid_identifier_namespace,inspireid_identifier_versionid,inspireid_identifier_versionid_nilreason,inspireid_identifier_versionid_xsi_nil,label,nationalcadastralreference,referencepoint,validfrom,validfrom_nilreason,validfrom_xsi_nil,validto,validto_nilreason,validto_xsi_nil,basicpropertyunit{}_owns,basicpropertyunit{}_nilreason,basicpropertyunit{}_gml_remoteschema,basicpropertyunit{}_xlink_href,basicpropertyunit{}_xsi_nil,administrativeunit_owns,administrativeunit_nilreason,administrativeunit_gml_remoteschema,administrativeunit_xlink_href,administrativeunit_xsi_nil,zoning_owns,zoning_nilreason,zoning_gml_remoteschema,zoning_xlink_href,zoning_xsi_nil,PRIMARYINDEX"
    INTERACT = ENVELOPE_INTERSECT
    CadastralParcel -> CadastralParcel (output)

FME custom transformer NamedPlace
NamedPlace GetFeature request handling

Parameters:
- bboxWest =   # Bounding box - minimum X coordinate
- bboxSouth =   # Bounding box - minimum Y coordinate
- bboxEast =   # Bounding box - maximum X coordinate
- bboxNorth =   # Bounding box - maximum Y coordinate
- BBOX =   # Bounding box
- POSTbody = text_line_data   # " " "" POSTbody

GetFeatureGET (input)
    -> GetBBOX
NamedPlace (output)
GetBBOX_BBox: Logger
    MAXCOORDS = 20
    MESSAGE = Feature is:
    MAXFEATS = 20

Bookmark: Query Database
GetBBOX
    bboxWest = $(bboxWest)
    BBOX = $(BBOX)
    bboxNorth = $(bboxNorth)
    bboxEast = $(bboxEast)
    bboxSouth = $(bboxSouth)
    BBox -> FeatureReader_3
    <UNFILTERED> -> FeatureReader_3
    BBox -> GetBBOX_BBox
    BBox -> GetBBOX_BBox_2
Note: With extents
FeatureReader_3
    SDF3_TABLELIST = NamedPlace
    DATASET = \\bester\pserv\Projects\INSPIRE\Demos\WebServices\WMSservice\WMS_SDF\INSPIREdb.sdf
    SUPPORTED_SPATIAL_INTERACTIONS = ENVELOPE_INTERSECT%ENVELOPE_INTERSECT%INTERSECTS%CONTAINS%CROSSES%DISJOINT%EQUALS%OVERLAPS%TOUCHES%WITHIN
    SDF3_DUMMY = YES
    COMBINE_ATTRS = Keep result attributes only
    COMBINE_GEOM = Keep result geometry only
    SDF3_REMOVE_SCHEMA_QUALIFIER = YES
    FEATURETYPES = NamedPlace
    FORMAT = SDF3
    ATTRIBUTES = NamedPlace,"beginlifespanversion,geographicalname_language,geographicalname_namestatus,geographicalname_nativeness,geographicalname_pronounciation,geographicalname_script,geographicalname_source_nilreason,geographicalname_spellingofname_text,gml_id,inspireid_identifier_localid,inspireid_identifier_namespace,localtype_localisedcharacterstring,localtype_localisedcharacterstring_locale,name_geographicalname_language,name_geographicalname_namestatus,name_geographicalname_nativeness,name_geographicalname_pronunciation_pronunciationofname_pron,name_geographicalname_sourceofname,name_geographicalname_sourceofname_nilreason,name_geographicalname_spelling_spellingofname_script,name_geographicalname_spelling_spellingofname_text,namedplace_beginlifespanversion,namedplace_featureid,namedplace_localid,namedplace_localtype,namedplace_localtype_locale,namedplace_namespace,namedplace_pointid,namedplace_type,type,PRIMARYINDEX"
    INTERACT = ENVELOPE_INTERSECT
    NamedPlace -> NamedPlace (output)
GetBBOX_BBox_2: Inspector
