FME workspace DBSwfs2postgisKartverket.fmw

Parameters:
- SourceDataset_WFS = http://kart.dsb.no/wfs.aspx?service=wfs&request=getcapabilities   # Source WFS (Web Feature Service) URL
- DestDataset_POSTGIS_1 = dsb   # Database

Readers:
- WFS_1: WFS from $(SourceDataset_WFS) in EPSG:32633

Writers:
- POSTGIS_1: POSTGIS to $(DestDataset_POSTGIS_1)

layer_307 (reader WFS_1)
    attributes: gml_parent_id xml_buffer, gml_id xml_buffer, msGeometry xml_geometry, SIVDISTRIK xml_buffer, URL xml_buffer, NAVN xml_buffer
    -> sivilforsvarsdistrikter (writer POSTGIS_1)
sivilforsvarsdistrikter (writer POSTGIS_1)
    attributes: gml_parent_id text, gml_id text, msgeometry text, sivdistrik text, url text, navn text
layer_309 (reader WFS_1)
    attributes: gml_parent_id xml_buffer, gml_id xml_buffer, msGeometry xml_geometry, TYPE xml_buffer, KOMMUNE xml_buffer, URL xml_buffer, NAVN xml_buffer, DATO xml_buffer
    -> sivilforsvaret_distriktskontor (writer POSTGIS_1)
sivilforsvaret_distriktskontor (writer POSTGIS_1)
    attributes: gml_parent_id text, gml_id text, msgeometry text, type text, kommune text, url text, navn text, dato text
layer_394 (reader WFS_1)
    attributes: gml_parent_id xml_buffer, gml_id xml_buffer, msGeometry xml_geometry, BRANNSTASJ xml_buffer, KASERNERT xml_buffer, BRANNVESEN xml_buffer, ANLEGGID xml_buffer, AJOURDATO xml_buffer, INFORMASJ xml_buffer, OPPHAV xml_buffer, STASJONSTY xml_buffer, OBJTYPE xml_buffer, DATO xml_buffer, BRANNSTA_ xml_buffer
    -> brannstasjoner (writer POSTGIS_1)
brannstasjoner (writer POSTGIS_1)
    attributes: gml_parent_id text, gml_id text, msgeometry text, brannstasj text, kasernert text, brannvesen text, anleggid text, ajourdato text, informasj text, opphav text, stasjonsty text, objtype text, dato text, brannsta_ text
layer_395 (reader WFS_1)
    attributes: gml_parent_id xml_buffer, gml_id xml_buffer, msGeometry xml_geometry, BRANNSTASJ xml_buffer, KASERNERT xml_buffer, BRANNVESEN xml_buffer, ANLEGGID xml_buffer, AJOURDATO xml_buffer, INFORMASJ xml_buffer, OPPHAV xml_buffer, STASJONSTY xml_buffer, OBJTYPE xml_buffer, DATO xml_buffer, BRANNSTA_ xml_buffer
    -> brannstasjonkasernering (writer POSTGIS_1)
brannstasjonkasernering (writer POSTGIS_1)
    attributes: gml_parent_id text, gml_id text, msgeometry text, brannstasj text, kasernert text, brannvesen text, anleggid text, ajourdato text, informasj text, opphav text, stasjonsty text, objtype text, dato text, brannsta_ text
layer_511 (reader WFS_1)
    attributes: gml_parent_id xml_buffer, gml_id xml_buffer, msGeometry xml_geometry, BRANNSTASJ xml_buffer, KASERNERT xml_buffer, BRANNVESEN xml_buffer, ANLEGGID xml_buffer, AJOURDATO xml_buffer, INFORMASJ xml_buffer, OPPHAV xml_buffer, STASJONSTY xml_buffer, OBJTYPE xml_buffer, DATO xml_buffer, BRANNSTA_ xml_buffer
    -> brannstasjoner_utf8 (writer POSTGIS_1)
brannstasjoner_utf8 (writer POSTGIS_1)
    attributes: gml_parent_id text, gml_id text, msgeometry text, brannstasj text, kasernert text, brannvesen text, anleggid text, ajourdato text, informasj text, opphav text, stasjonsty text, objtype text, dato text, brannsta_ text
layer_562 (reader WFS_1)
    attributes: gml_parent_id xml_buffer, gml_id xml_buffer, msGeometry xml_geometry, POLY_ xml_buffer, POLY_ID xml_buffer, AREA xml_buffer, PERIMETER xml_buffer, OPPR xml_buffer, X xml_buffer, Y xml_buffer, KOORDH xml_buffer, SENTRAL xml_buffer, LOKALISERI xml_buffer, OPPHAV xml_buffer, MALEMETODE xml_buffer, NOYAKTIGHE xml_buffer, SYNBARHET xml_buffer, H_MALEMETO xml_buffer, H_NOYAKTIG xml_buffer, MAX_AVVIK xml_buffer, OBJTYPE xml_buffer, NAVN xml_buffer, DATO xml_buffer
    -> sentraldistrikter110 (writer POSTGIS_1)
sentraldistrikter110 (writer POSTGIS_1)
    attributes: gml_parent_id text, gml_id text, msgeometry text, poly_ text, poly_id text, area text, perimeter text, oppr text, x text, y text, koordh text, sentral text, lokaliseri text, opphav text, malemetode text, noyaktighe text, synbarhet text, h_malemeto text, h_noyaktig text, max_avvik text, objtype text, navn text, dato text
