FME workspace DSBsivilforsvaret_distriktskontorWFS.fmw

Parameters:
- READER_FORMAT = POSTGIS   # Input Format
- READER_DATASET = geonor01tst   # Reader Dataset
- GML_OUT_TARGET_NS_PREFIX_GML = app   # Target Namespace Prefix
- GML_OUT_TARGET_NS_URI_GML = http://skjema.geonorge.no/SOSI/produktspesifikasjon/   # Target Namespace URI
- SourceDataset_POSTGIS_3 = geonor01tst   # Database

Readers:
- XML_1: XML from $(FME_MF_DIR)useparameters.xml
- POSTGIS_1: POSTGIS from $(SourceDataset_POSTGIS_3)

Writers:
- GML2_1: GML2 to C:\Users\bpont\Downloads\return.gml
- GML_1: GML to C:\Users\bpont\Downloads\return.gml
- GML_2: GML to C:\Users\bpont\Downloads\return.gml
- TEXTLINE_1: TEXTLINE to return.xml

Note: WFS Service Template / To modify this workspace to serve your desired dataset, please follow the steps below: / 1. Open the Transformers in the Navigation Window. / 2. Click on the first transformer (_FeatureReader_Source) to navigate to it. / 3. Open the transformer Properties and modify the reader settings to read your desired source data. / 4. Modify the Private Parameters in the Navigation Window / Input Format: Choose the same format as you used in the FeatureReader / Reader Dataset: Copy the contents of the Dataset field in the FeatureReader / Target Namespace Prefix: Default of 'mywfs' will work, but you can specify your own namespace ('fme' is reserved and will cause the workspace to fail). / Target Namespace URI: Your namespace schema, if you change from the default. / 5. Right-click on Workspace Resources in the Navigator and choose Add a Reader as a Resource. / Add a reader with the same settings you used in the Feature Reader. / This resource will provide the output schema information for the results. / 6. Open the Properties of the three GML feature types in the lower right section of the workspace. / Check the Dynamic Properties box. / Modify the Schema Sources to point only to the reader you added as a resource. / Leave Schema Definition set to Default / 7. Publish workspace to FME Server Data Streaming Service. Check the service properties to ensure that / The Output Datasets include the Textline and all three GML writers / The Source Dataset to Override is set to useParameters[XML]
Note: Route Features
AttributeFilter_6
    ATTR_VALUES = <EMPTY>,<MISSING>,<NULL>,<UNFILTERED>,GetCapabilities,DescribeFeatureType,GetFeature
    ATTR_NAME = REQUEST
    <UNFILTERED> -> FeatureReader_Schema_1
    GetCapabilities -> FeatureReader_Schema_1
    DescribeFeatureType -> FeatureReader_Schema_2
    GetFeature -> StringReplacer_2
    <NULL> -> FeatureReader_Schema_1
    <MISSING> -> FeatureReader_Schema_1
    <EMPTY> -> FeatureReader_Schema_1
text_line (writer TEXTLINE_1)
    attributes: text_line_data buffer

Bookmark: Read POST if sent, otherwise create feature to use GET parameters
GetCapabilities (reader XML_1)
    attributes: xml_fragment xml_xml, xml_id xml_char(21), xml_matched_element xml_char(16), xml_parent_child_pos xml_char(1), xml_parent_id xml_char(1)
    -> AttributeCreator
DescribeFeatureType (reader XML_1)
    attributes: xml_fragment xml_xml, xml_id xml_char(25), xml_matched_element xml_char(20), xml_parent_child_pos xml_char(1), xml_parent_id xml_char(1)
    -> AttributeCreator
GetFeature (reader XML_1)
    attributes: xml_fragment xml_xml, xml_id xml_char(16), xml_matched_element xml_char(11), xml_parent_child_pos xml_char(1), xml_parent_id xml_char(1)
    -> AttributeCreator
Note: Copy Feature Type to attribute
AttributeCreator
    ATTR_LIST = _id,0
    -> FeatureTypeExtractor_2
    -> AttributeCreator_Output
AttributeCreator_Output: Logger
    MAXCOORDS = 20
    MESSAGE = Feature is:
    MAXFEATS = 20
FeatureTypeExtractor_2
    DEST_ATTR = REQUEST
    -> DuplicateRemover
Note: Create feature after all / input features read
Creator
    NUM = 1
    GEOMTYPE = Geometry Object
    CREATED -> DuplicateRemover
Note: Block GET feature if POST is read
DuplicateRemover
    KEYATTR = _id
    UNIQUE -> AttributeRenamer_5
AttributeRenamer_5
    ATTR_LIST = xml_fragment,xml_request,
    -> AttributeFilter
Note: Route Features
AttributeFilter
    ATTR_VALUES = <EMPTY>,<MISSING>,<NULL>,<UNFILTERED>,GetCapabilities,DescribeFeatureType,GetFeature
    ATTR_NAME = REQUEST
    GetCapabilities -> XMLFlattener_2
    DescribeFeatureType -> XMLFlattener
    <MISSING> -> ParameterFetcher_2
    GetFeature -> XMLFlattener_3

Bookmark: Process GET Request
Note: Get URI of workspace / Map null for testing in desktop
ParameterFetcher_2
    ATTR_LIST = _FME_SERVER_REQUEST_URI {$(FME_SERVER_REQUEST_URI)}
    -> NullAttributeMapper_2
NullAttributeMapper_2
    NEW_VALUE = " "
    ATTRCHOICE = Selected Attributes
    ATTRLIST = _FME_SERVER_REQUEST_URI
    SOURCE_ATTR_VAL = Empty "Missing (Selected Attributes Only)" Null
    NULL_TREATMENT = New Value
    -> TextDecoder
Note: Decode URL string
TextDecoder
    DEST_ATTR = _FME_SERVER_REQUEST_URI
    ENCODING_TYPE = URL (Percent Encoding)
    STRING_TO_DECODE = @Value(_FME_SERVER_REQUEST_URI)
    -> FMEServerURLSplitter
Note: Split calling URI to get parameters
Note: FMEServerURLSplitter [FMEServerURLSplitter] / [Embedded] / Request URI: @Value(_FME_SERVER_REQUEST_URI) / URL Parameter Name Case: UPPERCASE / Decode URL Parameters: Decode
FMEServerURLSplitter
    DECODE_URL_TEXT = Decode
    _FME_SERVER_REQUEST_URI = @Value(_FME_SERVER_REQUEST_URI)
    URL_PARAM_NAME_CASE = UPPERCASE
    -> AttributeExposer_4
Note: Expose parameter attributes
AttributeExposer_4
    ATTR_LIST = SERVICE,REQUEST,VERSION,TYPENAME,TYPENAMES,FILTER,BBOX,ACCEPTVERSIONS,SRSNAME,COUNT,MAXFEATURES
    -> AttributeFilter_6

Bookmark: GetCapabilities POST Request
Note: Flatten POST XML
XMLFlattener_2
    ATTRIBUTE_XML = xml_request
    XML_SOURCE_TYPE = Attribute with XML document
    EMBEDDED_EXPRESSIONS = GetCapabilities
    FLATTEN_OPTIONS = <structure separator="." map-empty-elements="yes" matched-prefix="attributes" matched-attributes="yes" cardinality="+{?}" structure-prefix="" child-position-attribute="" except-expression="" ui-mode="basic" matched-ancestor-attributes=""/>
    NEW_ATTRIBUTES = GetCapabilities.version TypeName TypeNames
    -> AttributeRenamer_2
Note: Copy Version
AttributeRenamer_2
    ATTR_LIST = GetCapabilities.version,VERSION,
    -> AttributeFilter_6

Bookmark: DescribeFeatureType POST request
Note: Flatten POST XML
XMLFlattener
    ATTRIBUTE_XML = xml_request
    XML_SOURCE_TYPE = Attribute with XML document
    EMBEDDED_EXPRESSIONS = DescribeFeatureType
    FLATTEN_OPTIONS = <structure separator="." map-empty-elements="yes" matched-prefix="attributes" matched-attributes="yes" cardinality="+{?}" structure-prefix="" child-position-attribute="" except-expression="" ui-mode="basic" matched-ancestor-attributes=""/>
    NEW_ATTRIBUTES = DescribeFeatureType.version TypeName TypeNames TypeName{} TypeNames{}
    -> ListConcatenator
Note: Create Type lists
ListConcatenator
    LIST_ATTR = TypeName{}
    VAL_ATTR = _typename
    DROP_EMPTY_PARTS = Yes
    SEP = ,
    -> ListConcatenator_2
ListConcatenator_2
    LIST_ATTR = TypeNames{}
    VAL_ATTR = _typenames
    DROP_EMPTY_PARTS = Yes
    SEP = ,
    -> AttributeCreator_6
Note: Copy Version and Type Names
AttributeCreator_6
    ATTR_LIST = TYPENAME,"FME_CONDITIONAL:DEFAULT_VALUE'@Value(_typename)'BOOL_OP;OR;COMPOSITE_TEST;<Unused>;TEST _typename ATTRIBUTE_VALUE_NULL _FME_BLANK_STRING_;TEST _typename ATTRIBUTE_IS_EMPTY _FME_BLANK_STRING_;TEST _typename ATTRIBUTE_IS_MISSING _FME_BLANK_STRING_'@Value(TypeName)'FME_NUM_CONDITIONS2___",TYPENAMES,"FME_CONDITIONAL:DEFAULT_VALUE'@Value(_typenames)'BOOL_OP;OR;COMPOSITE_TEST;<Unused>;TEST _typenames ATTRIBUTE_VALUE_NULL _FME_BLANK_STRING_;TEST _typenames ATTRIBUTE_IS_EMPTY _FME_BLANK_STRING_;TEST _typenames ATTRIBUTE_IS_MISSING _FME_BLANK_STRING_'@Value(TypeNames)'FME_NUM_CONDITIONS2___",VERSION,@Value(DescribeFeatureType.version)
    -> AttributeFilter_6

Bookmark: GetFeature POST
Note: Flatten POST XML
XMLFlattener_3
    ATTRIBUTE_XML = xml_request
    XML_SOURCE_TYPE = Attribute with XML document
    EMBEDDED_EXPRESSIONS = GetFeature
    FLATTEN_OPTIONS:
      <structure
      separator="."
      open-list-brace="{"
      close-list-brace="}"
      map-empty-elements="yes"
      matched-prefix="attributes"
      matched-attributes="yes"
      matched-ancestor-attributes=""
      cardinality="+{?}"
      except=""
      structure-prefix=""
      child-position-attribute=""
      attribute-identifier=""/>

      <!--
      The options here allows customization of the attributes and attribute lists of the matched XML subtree
      that will be added to FME Features.

      Here are the following options that can be specified:

      1. separator
      This value of this option is used as the separator in the naming of the attributes of the children of the matched elements.

      Default value: .
      Possible values: any string

      2. open-list-brace
      Specifies the open list index delimiter brace for the flattened attributes.

      Default value: {
      Possible values: any string

      3. close-list-brace
      Specifies the close list index delimiter brace for the flattened attributes.

      Default value: }
      Possible values: any string

      4. map-empty-elements
      If set to yes, then any empty elements will be added as attributes with empty values onto the features.
      Otherwise, the attributes will not be added onto the features.

      Default value if not specified: yes
      Possible values: yes|no

      Default value:
      Possible values: any string

      5. matched-prefix
      This option controls whether FME feature attributes produced will be prefixed with matched element's name.
      If the value is 'yes', then both the matched element's attributes and all its children are prefixed
      If the value is 'no', then none of the feature attributes are prefixed with matched element's name
      If the value is 'children', then only the children of the matched element are prefixed
      If the value is 'attributes', then only the attributes of the matched element are prefixed

      Default value if not specified: yes
      Possible values: yes|no|children|attributes

      6. matched-attributes
      If this option is set to 'yes' then the attributes of the matched element are mapped as FME feature attributes.
      Otherwise, the attributes of the matched element are ignored.

      matched-prefix option can also be set to 'attributes' or 'yes' to allow the attributes to be prefixed with
      the name of the matched element.

      Default value if not specified: yes
      Possible values: yes|no

      7. matched-ancestor-attributes
      The option controls whether XML attributes from ancestor of the matched element should be included as FME feature attributes.

      The valid values for this option are:
      - 'parent' or '1'         : XML attributes of the parent of the matched element are added
      - 'grandparent' or '2'    : XML attributes of the grandparent of the matched element are added
      - 'root' or '-1'          : XML attributes of the root of the document are added
      - any non-negative number : XML attributes of the ancestor by going up x levels from the matched element are added.
                                  0 is the matched element.

      To include more than one ancestor, multiple values can be separated by a space.
      For example: To get the attributes from root, parent and grand parent, we can specify
      matched-ancestor-attributes="parent grandparent root"

      Default value:
      Possible values: parent|grandparent|root

      8. cardinality
      This option can be specified as a space separated list of cardinality directives.

      Default value: +{?} (Treat child elements as a list if there are more than one with the same name)
      Possible values: Refer to the documentation of XFMap section in XML Reader documentation

      9. structure-prefix
      This option can be set to non-empty string that serves as a prefix to every attribute that is generated for a matched element.

      Default value:
      Possible values: any string

      10. except
      The except attribute accepts the same types of expressions as the match or except attribute of a mapping rule.
      For example, the expression except=”parent/child{2}” could be used to exclude the second <child> element
      contained in a <parent> element from the output of the structure subrule.

      Default value:
      Possible values: any path expression

      11. child-position-attribute
      When this option is set to non-empty string, each child element will generate an additional feature attribute
      whose value will be the position of the child element witihin its parent.

      Default value:
      Possible values: any string

      12. attribute-identifier (Any string)
      XML attributes can be differentiated from leaf elements. By setting this option to non-empty string, XML reader
      will append a prefix to the attributes in the leaf elements.

      All the options have more elaborated examples and descriptions in the XML reader documentation.
      -->
    NEW_ATTRIBUTES = GetFeature.version Query.typeName Query.typeNames Query{}.typeName Query{}.typeNames Query{}.srsName Query{}.COUNT Query.COUNT Query.MAXFEATURES Query{}.MAXFEATURES
    -> XMLFragmenter
    -> FeatureMerger [input 1]
Note: Extract Filter XML
XMLFragmenter
    MERGE_ATTRS = Yes
    ATTRIBUTE_XML = xml_request
    XML_SOURCE_TYPE = Attribute with XML document
    EMBEDDED_EXPRESSIONS = Filter
    FRAGMENTS -> FeatureMerger [input 2]
Note: Merge Filter onto request
FeatureMerger
    ATTR_CONFLICT_RES = Use Supplier
    SUPPLIERS_FIRST = No
    PROCESS_DUPS = No
    MERGE_TYPE = Attributes Only
    JOIN_KEYS = 1 1 AUTO
    ATTR_ACCUM_MODE = Merge Supplier
    IGNORE_NULLS = No
    MERGED -> ListExploder_4
    NOT_MERGED -> ListExploder_4
Note: Explode query list
ListExploder_4
    LIST_ATTR = Query{}
    INDEX_ATTR = _element_index
    ATTR_ACCUM_MODE = Merge Incoming List
    ATTR_CONFLICT_RES = Use Original
    NOT_FOUND -> AttributeRenamer_4
    LIST_FOUND -> AttributeRenamer_3
Note: Copy Version and Type Names
AttributeRenamer_3
    ATTR_LIST = GetFeature.version,VERSION,,typeName,TYPENAME,,typeNames,TYPENAMES,,xml_fragment,FILTER,,srsName,SRSNAME,,COUNT,Teller,,MAXFEATURES,Teller,
    -> AttributeFilter_6
Note: Copy Version and Type Names
AttributeRenamer_4
    ATTR_LIST = GetFeature.version,VERSION,,Query.typeName,TYPENAME,,Query.typeNames,TYPENAMES,,xml_fragment,FILTER,,Query.srsName,SRSNAME,,COUNT,Teller,,MAXFEATURES,Teller,
    -> AttributeFilter_6

Bookmark: GetCapabilities
Note: Read Source data schema
FeatureReader_Schema_1
    FEATURETYPES = schema
    ATTR_CONFLICT_RES = Use Result
    FORMAT = SCHEMA
    FEATURETYPES_RADIO = FEATURETYPES
    SCHEMA_SCHEMA_READER = yes
    SCHEMA_REAL_FORMAT = $(READER_FORMAT)
    DATASET = $(READER_DATASET)
    ATTR_ACCUM_MODE = Merge Initiator and Result
    SUPPORTED_SPATIAL_INTERACTIONS = ENVELOPE_INTERSECT%INTERSECTS%CONTAINS%CROSSES%DISJOINT%EQUALS%OVERLAPS%TOUCHES%WITHIN
    COMBINE_GEOM = Use Result
    <OTHER> -> AttributeExposer
    INITIATOR -> AttributeSplitter
AttributeSplitter
    ATTR_NAME = _FME_SERVER_REQUEST_URI
    DELIMITER = ?
    TRIM_OPTION = Both
    DROP_EMPTY_PARTS = No
    LIST_NAME = _uri
    -> AttributeCopier_3
AttributeCopier_3
    ATTR_LIST = _uri{0},_FME_SERVER_REQUEST_URI,
    -> AttributeFilter_2
Note: Separate versions
AttributeFilter_2
    ATTR_VALUES = <EMPTY>,<MISSING>,<NULL>,<UNFILTERED>,1.0.0,1.1.0,2.0.0
    ATTR_NAME = VERSION
    1.0.0 -> XMLTemplater_5 [input 1]
    1.1.0 -> XMLTemplater_2 [input 1]
    2.0.0 -> XMLTemplater_4 [input 1]
    <UNFILTERED> -> XMLTemplater_4 [input 1]
    <NULL> -> XMLTemplater_4 [input 1]
    <MISSING> -> XMLTemplater_4 [input 1]
    <EMPTY> -> XMLTemplater_4 [input 1]
AttributeExposer
    ATTR_LIST = fme_feature_type_name
    -> DuplicateRemover_3
DuplicateRemover_3
    KEYATTR = fme_feature_type_name
    UNIQUE -> AttributeFilter_3
AttributeFilter_3
    ATTR_VALUES = <EMPTY>,<MISSING>,<NULL>,<UNFILTERED>,1.0.0,1.1.0,2.0.0
    ATTR_NAME = VERSION
    1.0.0 -> XMLTemplater_5 [input 2]
    1.1.0 -> XMLTemplater_2 [input 2]
    2.0.0 -> XMLTemplater_4 [input 2]
    <UNFILTERED> -> XMLTemplater_4 [input 2]
    <NULL> -> XMLTemplater_4 [input 2]
    <MISSING> -> XMLTemplater_4 [input 2]
    <EMPTY> -> XMLTemplater_4 [input 2]
Note: Create GetCapabilities 1.0.0
XMLTemplater_5
    VISIBLE_QUERY_VALIDATE = Yes
    ROOT_QUERY_EXPR:
      <?xml version="1.0" encoding="UTF-8"?>
      <WFS_Capabilities xmlns:xsi="http://www.w3.org/2001/XMLSchema-instance" xmlns:ogc="http://www.opengis.net/ogc" xmlns:gml2="http://www.safe.com/gml2" xmlns="http://www.opengis.net/wfs" version="1.0.0">
      	<!--Service Identification Section-->
      	<Service>
      		<Name>FME Server WFS Service</Name>
      		<Title>WFS Service Compliant with OGC WFS Specification Version 1.0.0</Title>
      		<Abstract>An OGC WFS Service created by Safe Software's FME Server</Abstract>
      		<OnlineResource>"{fme:get-attribute("_FME_SERVER_REQUEST_URI")}"</OnlineResource>
      		<Fees>None</Fees>
      		<AccessConstraints>None</AccessConstraints>
      	</Service>
      	<!--Operations Metadata Section-->
      	<Capability>
      		<Request>
      			<GetCapabilities>
      				<DCPType>
      					<HTTP>
      						<Get onlineResource="{fme:get-attribute("_FME_SERVER_REQUEST_URI")}"></Get>
      						<Post onlineResource="{fme:get-attribute("_FME_SERVER_REQUEST_URI")}"></Post>
      					</HTTP>
      				</DCPType>
      			</GetCapabilities>
      			<GetFeature>
      				<ResultFormat>
      					<GML2></GML2>
      				</ResultFormat>
      				<DCPType>
      					<HTTP>
      						<Get onlineResource="{fme:get-attribute("_FME_SERVER_REQUEST_URI")}"></Get>
      						<Post onlineResource="{fme:get-attribute("_FME_SERVER_REQUEST_URI")}"></Post>
      					</HTTP>
      				</DCPType>
      			</GetFeature>
      			<DescribeFeatureType>
      				<SchemaDescriptionLanguage>
      					<XMLSCHEMA></XMLSCHEMA>
      				</SchemaDescriptionLanguage>
      				<DCPType>
      					<HTTP>
      						<Get onlineResource="{fme:get-attribute("_FME_SERVER_REQUEST_URI")}"></Get>
      						<Post onlineResource="{fme:get-attribute("_FME_SERVER_REQUEST_URI")}"></Post>
      					</HTTP>
      				</DCPType>
      			</DescribeFeatureType>
      		</Request>
      	</Capability>
      	<!--Feature Type List Section-->
      	<FeatureTypeList>
      		<Operations>
      			<Query></Query>
      		</Operations>

      {fme:process-features("FEATURE")}

      	</FeatureTypeList>
      	<!--Filter Capabilities Section-->
      	<ogc:Filter_Capabilities>
      		<ogc:Spatial_Capabilities>
      			<ogc:Spatial_Operators>
      				<ogc:BBOX></ogc:BBOX>
      			</ogc:Spatial_Operators>
      		</ogc:Spatial_Capabilities>
      		<ogc:Scalar_Capabilities>
      			<ogc:Logical_Operators></ogc:Logical_Operators>
      		</ogc:Scalar_Capabilities>
      	</ogc:Filter_Capabilities>
      </WFS_Capabilities>
    FEATURE_QUERY_EXPR:
      		<FeatureType xmlns="http://www.opengis.net/wfs">
      			<Name>{fme:get-attribute("fme_feature_type_name")}</Name>
      			<Title>{fme:get-attribute("fme_feature_type_name")}</Title>
      			<Abstract></Abstract>
      			<SRS>EPSG:4258</SRS>
      			<SRS>EPSG:4326</SRS>
      			<SRS>EPSG:25830</SRS>
      			<SRS>EPSG:25831</SRS>
      			<SRS>EPSG:25832</SRS>
      			<SRS>EPSG:25833</SRS>
      			<SRS>EPSG:25834</SRS>
      			<SRS>EPSG:25835</SRS>
      			<SRS>EPSG:25836</SRS>
      			<SRS>EPSG:3044</SRS>
      			<SRS>EPSG:3045</SRS>
      			<LatLongBoundingBox maxx="180" maxy="90" minx="-180" miny="-90"></LatLongBoundingBox>
      		</FeatureType>
    OUTPUT_XML_HEADER = Yes
    RESULT_ATTRIBUTE = _result
    -> XMLFormatter
Note: Create GetCapabilities 1.1.0
Note: Need to update GetCapabilities with allowable filters
XMLTemplater_2
    VISIBLE_QUERY_VALIDATE = Yes
    ROOT_QUERY_EXPR:
      <?xml version="1.0" encoding="UTF-8"?>
      <wfs:WFS_Capabilities xmlns:xlink="http://www.w3.org/1999/xlink" xmlns:wfs="http://www.opengis.net/wfs" xmlns:ows="http://www.opengis.net/ows" xmlns:xsi="http://www.w3.org/2001/XMLSchema-instance" xmlns:ogc="http://www.opengis.net/ogc" xmlns:gml="http://www.opengis.net/gml" updateSequence="0" version="1.1.0" xsi:schemaLocation="http://www.opengis.net/wfs ../wfs/1.1.0/WFS.xsd">
      	<!--Service Identification Section-->
      	<ows:ServiceIdentification>
      		<ows:Title>WFS Service Compliant with OGC WFS Specification Version 1.1.0</ows:Title>
      		<ows:Abstract>An OGC WFS Service created by Safe Software's FME Server</ows:Abstract>
      		<ows:ServiceType>WFS</ows:ServiceType>
      		<ows:ServiceTypeVersion>1.1.0</ows:ServiceTypeVersion>
      		<ows:Fees>None</ows:Fees>
      		<ows:AccessConstraints>None</ows:AccessConstraints>
      	</ows:ServiceIdentification>
      	<!--Service Provider Section-->
      	<ows:ServiceProvider>
      		<ows:ProviderName>GeoNorge</ows:ProviderName>
      		<ows:ProviderSite xlink:href="www.safe.com"></ows:ProviderSite>
      		<ows:ServiceContact>
      			<ows:IndividualName>Norge Digitalt</ows:IndividualName>
      			<ows:PositionName></ows:PositionName>
      			<ows:ContactInfo>
      				<ows:Phone>
      					<ows:Voice></ows:Voice>
      					<ows:Facsimile></ows:Facsimile>
      				</ows:Phone>
      				<ows:Address>
      					<ows:City>Hønefoss</ows:City>
      					<ows:PostalCode></ows:PostalCode>
      					<ows:Country>Norway</ows:Country>
      					<ows:ElectronicMailAddress>post@norgedigitalt.no</ows:ElectronicMailAddress>
      				</ows:Address>
      				<ows:OnlineResource xlink:href="http://www.geonorge.no"></ows:OnlineResource>
      				<ows:HoursOfService></ows:HoursOfService>
      				<ows:ContactInstructions></ows:ContactInstructions>
      			</ows:ContactInfo>
      			<ows:Role></ows:Role>
      		</ows:ServiceContact>
      	</ows:ServiceProvider>
      	<!--Operations Metadata Section-->
      	<ows:OperationsMetadata>
      		<ows:Operation name="GetCapabilities">
      			<ows:DCP>
      				<ows:HTTP>
      					<ows:Get xlink:href="{fme:get-attribute("_FME_SERVER_REQUEST_URI")}"></ows:Get>
      					<ows:Post xlink:href="{fme:get-attribute("_FME_SERVER_REQUEST_URI")}"></ows:Post>
      				</ows:HTTP>
      			</ows:DCP>
      			<ows:Parameter name="AcceptVersions">
      				<ows:Value>1.1.0</ows:Value>
      				<ows:Value>1.0.0</ows:Value>
      			</ows:Parameter>
      			<ows:Parameter name="AcceptFormats">
      				<ows:Value>text/xml</ows:Value>
      			</ows:Parameter>
      			<ows:Parameter name="Sections">
      				<ows:Value>ServiceIdentification</ows:Value>
      				<ows:Value>ServiceProvider</ows:Value>
      				<ows:Value>OperationsMetadata</ows:Value>
      				<ows:Value>FeatureTypeList</ows:Value>
      				<ows:Value>ServesGMLObjectTypeList</ows:Value>
      				<ows:Value>SupportsGMLObjectTypeList</ows:Value>
      			</ows:Parameter>
      		</ows:Operation>
      		<ows:Operation name="GetFeature">
      			<ows:DCP>
      				<ows:HTTP>
      					<ows:Get xlink:href="{fme:get-attribute("_FME_SERVER_REQUEST_URI")}"></ows:Get>
      					<ows:Post xlink:href="{fme:get-attribute("_FME_SERVER_REQUEST_URI")}"></ows:Post>
      				</ows:HTTP>
      			</ows:DCP>
      			<ows:Parameter name="resultType">
      				<ows:Value>results</ows:Value>
      			</ows:Parameter>
      			<ows:Parameter name="outputFormat">
      				<ows:Value>text/xml; subtype=gml/3.1.1</ows:Value>
      			</ows:Parameter>
      		</ows:Operation>
      		<ows:Operation name="DescribeFeatureType">
      			<ows:DCP>
      				<ows:HTTP>
      					<ows:Get xlink:href="{fme:get-attribute("_FME_SERVER_REQUEST_URI")}"></ows:Get>
      					<ows:Post xlink:href="{fme:get-attribute("_FME_SERVER_REQUEST_URI")}"></ows:Post>
      				</ows:HTTP>
      			</ows:DCP>
      			<ows:Parameter name="outputFormat">
      				<ows:Value>text/xml; subtype=gml/3.1.1</ows:Value>
      			</ows:Parameter>
      		</ows:Operation>
      	</ows:OperationsMetadata>
      	<!--Feature Type List Section-->
      	<wfs:FeatureTypeList>

      {fme:process-features("FEATURE")}

      	</wfs:FeatureTypeList>
      	<!--Supports GML Object Type List Section-->
      	<wfs:SupportsGMLObjectTypeList>
      		<wfs:GMLObjectType>
      			<wfs:Name>gml:AbstractGMLFeatureType</wfs:Name>
      			<wfs:OutputFormats>
      				<wfs:Format>text/xml; subtype=gml3.1.1</wfs:Format>
      			</wfs:OutputFormats>
      		</wfs:GMLObjectType>
      	</wfs:SupportsGMLObjectTypeList>
      	<!--Filter Capabilities Section-->
      	<ogc:Filter_Capabilities>
      		<ogc:Spatial_Capabilities>
      			<ogc:GeometryOperands>
      				<ogc:GeometryOperand>gml:Envelope</ogc:GeometryOperand>
      			</ogc:GeometryOperands>
      			<ogc:SpatialOperators>
      				<ogc:SpatialOperator name="BBOX"></ogc:SpatialOperator>
      			</ogc:SpatialOperators>
      		</ogc:Spatial_Capabilities>
              <ogc:Scalar_Capabilities>
                   <ogc:LogicalOperators/>
                   <ogc:ComparisonOperators>
                       <ogc:ComparisonOperator>LessThan</ogc:ComparisonOperator>
                       <ogc:ComparisonOperator>GreaterThan</ogc:ComparisonOperator>
                       <ogc:ComparisonOperator>LessThanEqualTo</ogc:ComparisonOperator>
                       <ogc:ComparisonOperator>GreaterThanEqualTo</ogc:ComparisonOperator>
                       <ogc:ComparisonOperator>EqualTo</ogc:ComparisonOperator>
                       <ogc:ComparisonOperator>NotEqualTo</ogc:ComparisonOperator>
                       <ogc:ComparisonOperator>Like</ogc:ComparisonOperator>
                       <ogc:ComparisonOperator>Between</ogc:ComparisonOperator>
                       <ogc:ComparisonOperator>NullCheck</ogc:ComparisonOperator>
                   </ogc:ComparisonOperators>
              </ogc:Scalar_Capabilities>
       		<ogc:Id_Capabilities>
      			<ogc:EID></ogc:EID>
      			<ogc:FID></ogc:FID>
      		</ogc:Id_Capabilities>
      	</ogc:Filter_Capabilities>
      </wfs:WFS_Capabilities>
    FEATURE_QUERY_EXPR:
              <wfs:FeatureType xmlns:ows="http://www.opengis.net/ows" xmlns:wfs="http://www.opengis.net/wfs" xmlns:$(GML_OUT_TARGET_NS_PREFIX_GML)="$(GML_OUT_TARGET_NS_URI_GML)">
                  <wfs:Name>$(GML_OUT_TARGET_NS_PREFIX_GML):{fme:get-attribute("fme_feature_type_name")}</wfs:Name>
                  <wfs:Title>{fme:get-attribute("fme_feature_type_name")}</wfs:Title>
                  <wfs:Abstract></wfs:Abstract>
                  <wfs:DefaultSRS>urn:ogc:def:crs:EPSG::4258</wfs:DefaultSRS>
                  <wfs:OtherSRS>urn:ogc:def:crs:EPSG::4326</wfs:OtherSRS>
                  <wfs:OtherSRS>urn:ogc:def:crs:EPSG::25830</wfs:OtherSRS>
                  <wfs:OtherSRS>urn:ogc:def:crs:EPSG::25831</wfs:OtherSRS>
                  <wfs:OtherSRS>urn:ogc:def:crs:EPSG::25832</wfs:OtherSRS>
                  <wfs:OtherSRS>urn:ogc:def:crs:EPSG::25833</wfs:OtherSRS>
                  <wfs:OtherSRS>urn:ogc:def:crs:EPSG::25834</wfs:OtherSRS>
                  <wfs:OtherSRS>urn:ogc:def:crs:EPSG::25835</wfs:OtherSRS>
                  <wfs:OtherSRS>urn:ogc:def:crs:EPSG::25836</wfs:OtherSRS>
                  <wfs:OtherSRS>urn:ogc:def:crs:EPSG::3044</wfs:OtherSRS>
                  <wfs:OtherSRS>urn:ogc:def:crs:EPSG::3045</wfs:OtherSRS>
                  <wfs:OutputFormats>
                      <wfs:Format>text/xml; subtype=gml/3.1.1</wfs:Format>
                  </wfs:OutputFormats>
                  <ows:WGS84BoundingBox>
                      <ows:LowerCorner>-180 -90</ows:LowerCorner>
                      <ows:UpperCorner>180 90</ows:UpperCorner>
                  </ows:WGS84BoundingBox>
              </wfs:FeatureType>
    OUTPUT_XML_HEADER = Yes
    RESULT_ATTRIBUTE = _result
    -> XMLFormatter
Note: Create GetCapabilities 2.0.0
XMLTemplater_4
    VISIBLE_QUERY_VALIDATE = Yes
    ROOT_QUERY_EXPR:
      <?xml version="1.0" encoding="UTF-8"?>
      <wfs:WFS_Capabilities xmlns:xsi="http://www.w3.org/2001/XMLSchema-instance" xmlns="http://www.opengis.net/wfs/2.0" xmlns:wfs="http://www.opengis.net/wfs/2.0" xmlns:ows="http://www.opengis.net/ows/1.1" xmlns:gml="http://www.opengis.net/gml/3.2" xmlns:fes="http://www.opengis.net/fes/2.0" xmlns:xlink="http://www.w3.org/1999/xlink" xmlns:xs="http://www.w3.org/2001/XMLSchema" version="2.0.0" xsi:schemaLocation="http://www.opengis.net/wfs/2.0 http://schemas.opengis.net/wfs/2.0/wfs.xsd" updateSequence="71579">	<!--Service Identification Section-->
      	<ows:ServiceIdentification>
      		<ows:Title>WFS Service Compliant with OGC WFS Specification Version 2.0.0</ows:Title>
      		<ows:Abstract>An OGC WFS Service created by GeoNorge FME Server</ows:Abstract>
      		<ows:ServiceType>WFS</ows:ServiceType>
      		<ows:ServiceTypeVersion>2.0.0</ows:ServiceTypeVersion>
      		<ows:ServiceTypeVersion>1.1.0</ows:ServiceTypeVersion>
      		<ows:ServiceTypeVersion>1.0.0</ows:ServiceTypeVersion>
      		<ows:Fees>None</ows:Fees>
      		<ows:AccessConstraints>None</ows:AccessConstraints>
      	</ows:ServiceIdentification>
      	<!--Service Provider Section-->
      	<ows:ServiceProvider>
      		<ows:ProviderName>GeoNorge</ows:ProviderName>
      		<ows:ProviderSite xlink:href="www.safe.com"></ows:ProviderSite>
      		<ows:ServiceContact>
      			<ows:IndividualName>Norge Digitalt</ows:IndividualName>
      			<ows:PositionName></ows:PositionName>
      			<ows:ContactInfo>
      				<ows:Phone>
      					<ows:Voice></ows:Voice>
      					<ows:Facsimile></ows:Facsimile>
      				</ows:Phone>
      				<ows:Address>
      					<ows:City>Hønefoss</ows:City>
      					<ows:PostalCode></ows:PostalCode>
      					<ows:Country>Norway</ows:Country>
      					<ows:ElectronicMailAddress>post@norgedigitalt.no</ows:ElectronicMailAddress>
      				</ows:Address>
      				<ows:OnlineResource xlink:href="http://www.geonorge.no"></ows:OnlineResource>
      				<ows:HoursOfService></ows:HoursOfService>
      				<ows:ContactInstructions></ows:ContactInstructions>
      			</ows:ContactInfo>
      			<ows:Role></ows:Role>
      		</ows:ServiceContact>
      	</ows:ServiceProvider>
      	<!--Operations Metadata Section-->
      	<ows:OperationsMetadata>
      		<ows:Operation name="GetCapabilities">
      			<ows:DCP>
      				<ows:HTTP>
      					<ows:Get xlink:href="{fme:get-attribute("_FME_SERVER_REQUEST_URI")}"></ows:Get>
      					<ows:Post xlink:href="{fme:get-attribute("_FME_SERVER_REQUEST_URI")}"></ows:Post>
      				</ows:HTTP>
      			</ows:DCP>
      			<ows:Parameter name="AcceptVersions">
                      <ows:AllowedValues>
                          <ows:Value>2.0.0</ows:Value>
                          <ows:Value>1.1.0</ows:Value>
                          <ows:Value>1.0.0</ows:Value>
                      </ows:AllowedValues>
      			</ows:Parameter>
      			<ows:Parameter name="AcceptFormats">
                      <ows:AllowedValues>
                          <ows:Value>text/xml</ows:Value>
                      </ows:AllowedValues>
      			</ows:Parameter>
      		</ows:Operation>
      		<ows:Operation name="DescribeFeatureType">
      			<ows:DCP>
      				<ows:HTTP>
      					<ows:Get xlink:href="{fme:get-attribute("_FME_SERVER_REQUEST_URI")}"></ows:Get>
      					<ows:Post xlink:href="{fme:get-attribute("_FME_SERVER_REQUEST_URI")}"></ows:Post>
      				</ows:HTTP>
      			</ows:DCP>
                  <ows:Parameter name="outputFormat">
                      <ows:AllowedValues>
                          <ows:Value>text/xml; subtype=gml/3.2</ows:Value>
                      </ows:AllowedValues>
                  </ows:Parameter>
      		</ows:Operation>
      		<ows:Operation name="GetFeature">
      			<ows:DCP>
      				<ows:HTTP>
      					<ows:Get xlink:href="{fme:get-attribute("_FME_SERVER_REQUEST_URI")}"></ows:Get>
      					<ows:Post xlink:href="{fme:get-attribute("_FME_SERVER_REQUEST_URI")}"></ows:Post>
      				</ows:HTTP>
      			</ows:DCP>
      		</ows:Operation>
                <!-- ***************************************************** -->
                <!-- *   CONFORMANCE DECLARATION                         * -->
                <!-- ***************************************************** -->
                <ows:Constraint name="ImplementsBasicWFS">
                   <ows:NoValues/>
                   <ows:DefaultValue>TRUE</ows:DefaultValue>
                </ows:Constraint>
                <ows:Constraint name="ImplementsTransactionalWFS">
                   <ows:NoValues/>
                   <ows:DefaultValue>FALSE</ows:DefaultValue>
                </ows:Constraint>
                <ows:Constraint name="ImplementsLockingWFS">
                   <ows:NoValues/>
                   <ows:DefaultValue>FALSE</ows:DefaultValue>
                </ows:Constraint>
                <ows:Constraint name="KVPEncoding">
                   <ows:NoValues/>
                   <ows:DefaultValue>FALSE</ows:DefaultValue>
                </ows:Constraint>
                <ows:Constraint name="XMLEncoding">
                   <ows:NoValues/>
                   <ows:DefaultValue>FALSE</ows:DefaultValue>
                </ows:Constraint>
                <ows:Constraint name="SOAPEncoding">
                   <ows:NoValues/>
                   <ows:DefaultValue>FALSE</ows:DefaultValue>
                </ows:Constraint>
                <ows:Constraint name="ImplementsInheritance">
                   <ows:NoValues/>
                   <ows:DefaultValue>FALSE</ows:DefaultValue>
                </ows:Constraint>
                <ows:Constraint name="ImplementsRemoteResolve">
                   <ows:NoValues/>
                   <ows:DefaultValue>FALSE</ows:DefaultValue>
                </ows:Constraint>
                <ows:Constraint name="ImplementsResultPaging">
                   <ows:NoValues/>
                   <ows:DefaultValue>FALSE</ows:DefaultValue>
                </ows:Constraint>
                <ows:Constraint name="ImplementsStandardJoins">
                   <ows:NoValues/>
                   <ows:DefaultValue>FALSE</ows:DefaultValue>
                </ows:Constraint>
                <ows:Constraint name="ImplementsSpatialJoins">
                   <ows:NoValues/>
                   <ows:DefaultValue>FALSE</ows:DefaultValue>
                </ows:Constraint>
                <ows:Constraint name="ImplementsTemporalJoins">
                   <ows:NoValues/>
                   <ows:DefaultValue>FALSE</ows:DefaultValue>
                </ows:Constraint>
                <ows:Constraint name="ImplementsFeatureVersioning">
                   <ows:NoValues/>
                   <ows:DefaultValue>FALSE</ows:DefaultValue>
                </ows:Constraint>
                <ows:Constraint name="ManageStoredQueries">
                   <ows:NoValues/>
                   <ows:DefaultValue>FALSE</ows:DefaultValue>
                </ows:Constraint>
      	</ows:OperationsMetadata>
      	<!--Feature Type List Section-->
      	<wfs:FeatureTypeList>

      {fme:process-features("FEATURE")}

      	</wfs:FeatureTypeList>
      	<!--Supports GML Object Type List Section-->
      	<wfs:SupportsGMLObjectTypeList>
      		<wfs:GMLObjectType>
      			<wfs:Name>gml:AbstractGMLFeatureType</wfs:Name>
      			<wfs:OutputFormats>
      				<wfs:Format>text/xml; subtype=gml3.2.1</wfs:Format>
      			</wfs:OutputFormats>
      		</wfs:GMLObjectType>
      	</wfs:SupportsGMLObjectTypeList>
      	<!--Filter Capabilities Section-->
         <fes:Filter_Capabilities>
            <fes:Conformance>
               <fes:Constraint name="ImplementsQuery">
                  <ows:NoValues/>
                  <ows:DefaultValue>TRUE</ows:DefaultValue>
               </fes:Constraint>
               <fes:Constraint name="ImplementsAdHocQuery">
                  <ows:NoValues/>
                  <ows:DefaultValue>FALSE</ows:DefaultValue>
               </fes:Constraint>
               <fes:Constraint name="ImplementsFunctions">
                  <ows:NoValues/>
                  <ows:DefaultValue>FALSE</ows:DefaultValue>
               </fes:Constraint>
               <fes:Constraint name="ImplementsMinStandardFilter">
                  <ows:NoValues/>
                  <ows:DefaultValue>FALSE</ows:DefaultValue>
               </fes:Constraint>
               <fes:Constraint name="ImplementsStandardFilter">
                  <ows:NoValues/>
                  <ows:DefaultValue>FALSE</ows:DefaultValue>
               </fes:Constraint>
               <fes:Constraint name="ImplementsMinSpatialFilter">
                  <ows:NoValues/>
                  <ows:DefaultValue>FALSE</ows:DefaultValue>
               </fes:Constraint>
               <fes:Constraint name="ImplementsSpatialFilter">
                  <ows:NoValues/>
                  <ows:DefaultValue>TRUE</ows:DefaultValue>
               </fes:Constraint>
               <fes:Constraint name="ImplementsMinTemporalFilter">
                  <ows:NoValues/>
                  <ows:DefaultValue>FALSE</ows:DefaultValue>
               </fes:Constraint>
               <fes:Constraint name="ImplementsTemporalFilter">
                  <ows:NoValues/>
                  <ows:DefaultValue>FALSE</ows:DefaultValue>
               </fes:Constraint>
               <fes:Constraint name="ImplementsVersionNav">
                  <ows:NoValues/>
                  <ows:DefaultValue>FALSE</ows:DefaultValue>
               </fes:Constraint>
               <fes:Constraint name="ImplementsSorting">
                  <ows:NoValues/>
                  <ows:DefaultValue>FALSE</ows:DefaultValue>
               </fes:Constraint>
               <fes:Constraint name="ImplementsExtendedOperators">
                  <ows:NoValues/>
                  <ows:DefaultValue>FALSE</ows:DefaultValue>
               </fes:Constraint>
           </fes:Conformance>
           <fes:Scalar_Capabilities>
               <fes:LogicalOperators/>
               <fes:ComparisonOperators>
                   <fes:ComparisonOperator name="PropertyIsBetween"/>
                   <fes:ComparisonOperator name="PropertyIsEqualTo"/>
                   <fes:ComparisonOperator name="PropertyIsGreaterThan"/>
                   <fes:ComparisonOperator name="PropertyIsGreaterThanOrEqualTo"/>
                   <fes:ComparisonOperator name="PropertyIsLessThan"/>
                   <fes:ComparisonOperator name="PropertyIsLessThanOrEqualTo"/>
                   <fes:ComparisonOperator name="PropertyIsLike"/>
                   <fes:ComparisonOperator name="PropertyIsNotEqualTo"/>
                   <fes:ComparisonOperator name="PropertyIsNull"/>
               </fes:ComparisonOperators>
           </fes:Scalar_Capabilities>
         </fes:Filter_Capabilities>
      </wfs:WFS_Capabilities>
    FEATURE_QUERY_EXPR:
              <FeatureType xmlns:ows="http://www.opengis.net/ows/1.1" xmlns:wfs="http://www.opengis.net/wfs/2.0" xmlns="http://www.opengis.net/wfs/2.0" xmlns:$(GML_OUT_TARGET_NS_PREFIX_GML)="$(GML_OUT_TARGET_NS_URI_GML)">
                  <Name>$(GML_OUT_TARGET_NS_PREFIX_GML):{fme:get-attribute("fme_feature_type_name")}</Name>
                  <Title>{fme:get-attribute("fme_feature_type_name")}</Title>
                  <Abstract></Abstract>
                  <DefaultCRS>urn:ogc:def:crs:EPSG:4258</DefaultCRS>
                  <OtherCRS>urn:ogc:def:crs:EPSG::4326</OtherCRS>
                  <OtherCRS>urn:ogc:def:crs:EPSG::25830</OtherCRS>
                  <OtherCRS>urn:ogc:def:crs:EPSG::25831</OtherCRS>
                  <OtherCRS>urn:ogc:def:crs:EPSG::25832</OtherCRS>
                  <OtherCRS>urn:ogc:def:crs:EPSG::25833</OtherCRS>
                  <OtherCRS>urn:ogc:def:crs:EPSG::25834</OtherCRS>
                  <OtherCRS>urn:ogc:def:crs:EPSG::25835</OtherCRS>
                  <OtherCRS>urn:ogc:def:crs:EPSG::25836</OtherCRS>
                  <OtherCRS>urn:ogc:def:crs:EPSG::3044</OtherCRS>
                  <OtherCRS>urn:ogc:def:crs:EPSG::3045</OtherCRS>
                  <OutputFormats>
                      <Format>text/xml; subtype=gml/3.2.1</Format>
                  </OutputFormats>
                  <ows:WGS84BoundingBox>
                      <ows:LowerCorner>-180 -90</ows:LowerCorner>
                      <ows:UpperCorner>180 90</ows:UpperCorner>
                  </ows:WGS84BoundingBox>
              </FeatureType>
    OUTPUT_XML_HEADER = Yes
    RESULT_ATTRIBUTE = _result
    -> XMLFormatter
Note: Pretty-Print the XML output
XMLFormatter
    SCHEMALOC_CLEANUP = No
    LIST_NAME = _xml_error
    XML_ATTR_TEXT = _result
    XML_OUTPUT_ATTR = text_line_data
    OUTPUT_ENCODING = utf-8
    WHITESPACE_HANDLING = Preserve all whitespace
    XML_INPUT_TYPE = Attribute Specifying XML Text
    REMOVE_EMPTY_ELEMENT = No
    COLLAPSE_EMPTY_ELEMENT = No
    NAMESPACE_CLEANUP = No
    REMOVE_ALL_COMMENT = No
    FORMATTING_CHOICE = Pretty-Print XML
    XML_OUTPUT_TYPE = Attribute
    PASSED -> text_line (writer TEXTLINE_1)

Bookmark: DescribeFeatureType
Note: Read Source data schema
FeatureReader_Schema_2
    FEATURETYPES = schema
    ATTR_CONFLICT_RES = Use Result
    FORMAT = SCHEMA
    FEATURETYPES_RADIO = FEATURETYPES
    SCHEMA_SCHEMA_READER = yes
    SCHEMA_REAL_FORMAT = $(READER_FORMAT)
    DATASET = $(READER_DATASET)
    ATTR_ACCUM_MODE = Merge Initiator and Result
    SUPPORTED_SPATIAL_INTERACTIONS = ENVELOPE_INTERSECT%INTERSECTS%CONTAINS%CROSSES%DISJOINT%EQUALS%OVERLAPS%TOUCHES%WITHIN
    COMBINE_GEOM = Use Result
    <OTHER> -> AttributeExposer_2
AttributeExposer_2
    ATTR_LIST = fme_feature_type_name,attribute{}.name,attribute{}.fme_data_type,attribute{}.fme_type
    -> DuplicateRemover_2
DuplicateRemover_2
    KEYATTR = fme_feature_type_name
    UNIQUE -> AttributeFilter_5
AttributeFilter_5
    ATTR_VALUES = <EMPTY>,<MISSING>,<NULL>,<UNFILTERED>,1.0.0,1.1.0,2.0.0
    ATTR_NAME = VERSION
    1.0.0 -> Tester
    1.1.0 -> Tester_2
    2.0.0 -> Tester_3
Note: Create feature type areas
Note: Pretty-Print the XML output
XMLFormatter_2
    SCHEMALOC_CLEANUP = No
    LIST_NAME = _xml_error
    XML_ATTR_TEXT = DescFeatType
    XML_OUTPUT_ATTR = text_line_data
    OUTPUT_ENCODING = utf-8
    WHITESPACE_HANDLING = Preserve all whitespace
    XML_INPUT_TYPE = Attribute Specifying XML Text
    REMOVE_EMPTY_ELEMENT = No
    COLLAPSE_EMPTY_ELEMENT = No
    NAMESPACE_CLEANUP = No
    REMOVE_ALL_COMMENT = No
    FORMATTING_CHOICE = Pretty-Print XML
    XML_OUTPUT_TYPE = Attribute
    PASSED -> text_line (writer TEXTLINE_1)

Bookmark: WFS 1.0.0
Note: Keep only requested features
Tester
    BOOL_OP = OR
    TEST_CLAUSE:
      TEST @Value(fme_feature_type_name) IN @Value(TYPENAME)
      TEST @Value(fme_feature_type_name) IN @Value(TYPENAMES)
    TEST_MODE = Automatic
    TEST_DESCRIPTION = ""
    PASSED -> ListExploder
    PASSED -> AttributeFilter_8
AttributeFilter_8
    ATTR_VALUES = <EMPTY>,<MISSING>,<NULL>,<UNFILTERED>,dsb.sivilforsvaret_distriktskontor
    ATTR_NAME = fme_feature_type_name
    dsb.sivilforsvaret_distriktskontor -> XMLTemplater_11 [input 1]
Note: Explode list of attributes
ListExploder
    MODE = List Elements and Original Attributes
    LIST_ATTR = attribute{}
    LIST_FOUND -> StringSearcher_2
Note: Decimal, String / and other attribtes
StringSearcher_2
    MATCHED_RESULT_ATTR = _matched_characters
    STRING_TO_SEARCH = @Value(fme_data_type)
    REGEXP = [(]([0-9]*),([0-9]*)[)]
    MATCHED_PARTS_ATTR = _matched_parts
    CASE = no
    NOT_MATCHED -> StringSearcher
    MATCHED -> XMLTemplater [input 2]
    MATCHED -> XMLTemplater_10 [input 2]
    MATCHED -> XMLTemplater_11 [input 2]
StringSearcher
    MATCHED_RESULT_ATTR = _matched_characters
    STRING_TO_SEARCH = @Value(fme_data_type)
    REGEXP = [(]([0-9]*)[)]
    MATCHED_PARTS_ATTR = _matched_parts
    CASE = no
    NOT_MATCHED -> AttributeValueMapper
    MATCHED -> XMLTemplater [input 3]
    MATCHED -> XMLTemplater_10 [input 3]
    MATCHED -> XMLTemplater_11 [input 3]
AttributeValueMapper
    VAL_ATTR = wfs_data_type
    LUT = fme_buffer,string,fme_char,string,fme_int64,long,fme_uint64,unsignedLong,fme_int32,int,fme_uint32,unsignedInt,fme_int16,short,fme_uint16,unsignedShort,fme_uint8,unsignedByte,fme_real32,float,fme_real64,double,fme_boolean,boolean,fme_datetime,string,fme_date,string,fme_time,string
    SRC = fme_data_type
    DIRECTION = Forward (Source To Destination)
    -> XMLTemplater_11 [input 4]
    -> XMLTemplater_10 [input 4]
    -> XMLTemplater [input 4]
XMLTemplater
    VISIBLE_QUERY_VALIDATE = Yes
    COMPLEX_QUERY_EXPR:
      					<element xmlns="http://www.w3.org/2001/XMLSchema" minOccurs="0" name="{fme:get-attribute("name")}">
      						<simpleType>
      							<restriction base="string">
      								<maxLength value="{fme:get-attribute("_matched_parts{0}")}"></maxLength>
      							</restriction>
      						</simpleType>
      					</element>
    SIMPLE_QUERY_EXPR = <element xmlns="http://www.w3.org/2001/XMLSchema" minOccurs="0" name="{fme:get-attribute("name")}" type="{fme:get-attribute("wfs_data_type")}"></element>
    ROOT_QUERY_EXPR:
      	<complexType xmlns="http://www.w3.org/2001/XMLSchema" name="{fme:get-attribute("fme_feature_type_name")}Type">
      		<complexContent>
      			<extension base="gml:AbstractFeatureType">
      				<sequence>

                          {fme:process-features("DECIMAL")}
                          {fme:process-features("COMPLEX")}
                          {fme:process-features("SIMPLE")}

       <!--                   <element name="lineStringProperty" type="gml:GeometryPropertyType"></element>
                          <element name="multiLineStringProperty" type="gml:GeometryPropertyType"></element>
                          <element name="polygonProperty" type="gml:GeometryPropertyType"></element>
                          <element name="multiPolygonProperty" type="gml:GeometryPropertyType"></element>
                          <element name="multiPointProperty" type="gml:GeometryPropertyType"></element>-->
      					<choice>
      						<element ref="gml:lineStringProperty" type="gml:GeometryPropertyType"></element>
      						<element ref="gml:multiLineStringProperty" type="gml:GeometryPropertyType"></element>
      						<element ref="gml:polygonProperty" type="gml:GeometryPropertyType"></element>
      						<element ref="gml:multiPolygonProperty" type="gml:GeometryPropertyType"></element>
      						<element ref="gml:pointProperty" type="gml:GeometryPropertyType"></element>
      						<element ref="gml:multiPointProperty" type="gml:GeometryPropertyType"></element>
      					</choice>
                          <element name="polygonProperty" type="gml:GeometryPropertyType"></element>
                      </sequence>
      			</extension>
      		</complexContent>
      	</complexType>
    CONSECUTIVE_GROUPS = No
    GROUP_BY = fme_feature_type_name
    OUTPUT_XML_HEADER = Yes
    RESULT_ATTRIBUTE = _result
    DECIMAL_QUERY_EXPR:
      					<element xmlns="http://www.w3.org/2001/XMLSchema" minOccurs="0" name="{fme:get-attribute("name")}">
      						<simpleType>
      							<restriction base="decimal">
      								<totalDigits value="{fme:get-attribute("_matched_parts{0}")}"></totalDigits>
      								<fractionDigits value="{fme:get-attribute("_matched_parts{1}")}"></fractionDigits>
      							</restriction>
      						</simpleType>
      					</element>
    -> Sampler
    -> XMLTemplater_3 [input 2]
Note: Create feature type lines
XMLTemplater_10
    VISIBLE_QUERY_VALIDATE = Yes
    COMPLEX_QUERY_EXPR:
      					<element xmlns="http://www.w3.org/2001/XMLSchema" minOccurs="0" name="{fme:get-attribute("name")}">
      						<simpleType>
      							<restriction base="string">
      								<maxLength value="{fme:get-attribute("_matched_parts{0}")}"></maxLength>
      							</restriction>
      						</simpleType>
      					</element>
    SIMPLE_QUERY_EXPR = <element xmlns="http://www.w3.org/2001/XMLSchema" minOccurs="0" name="{fme:get-attribute("name")}" type="{fme:get-attribute("wfs_data_type")}"></element>
    ROOT_QUERY_EXPR:
      	<complexType xmlns="http://www.w3.org/2001/XMLSchema" name="{fme:get-attribute("fme_feature_type_name")}Type">
      		<complexContent>
      			<extension base="gml:AbstractFeatureType">
      				<sequence>

                          {fme:process-features("DECIMAL")}
                          {fme:process-features("COMPLEX")}
                          {fme:process-features("SIMPLE")}

       <!--                   <element name="lineStringProperty" type="gml:GeometryPropertyType"></element>
                          <element name="multiLineStringProperty" type="gml:GeometryPropertyType"></element>
                          <element name="polygonProperty" type="gml:GeometryPropertyType"></element>
                          <element name="multiPolygonProperty" type="gml:GeometryPropertyType"></element>
                          <element name="multiPointProperty" type="gml:GeometryPropertyType"></element>-->
      					<choice>
      						<element ref="gml:lineStringProperty" type="gml:GeometryPropertyType"></element>
      						<element ref="gml:multiLineStringProperty" type="gml:GeometryPropertyType"></element>
      						<element ref="gml:polygonProperty" type="gml:GeometryPropertyType"></element>
      						<element ref="gml:multiPolygonProperty" type="gml:GeometryPropertyType"></element>
      						<element ref="gml:pointProperty" type="gml:GeometryPropertyType"></element>
      						<element ref="gml:multiPointProperty" type="gml:GeometryPropertyType"></element>
      					</choice>
                          <element name="lineStringProperty" type="gml:GeometryPropertyType"></element>
                      </sequence>
      			</extension>
      		</complexContent>
      	</complexType>
    CONSECUTIVE_GROUPS = No
    GROUP_BY = fme_feature_type_name
    OUTPUT_XML_HEADER = Yes
    RESULT_ATTRIBUTE = _result
    DECIMAL_QUERY_EXPR:
      					<element xmlns="http://www.w3.org/2001/XMLSchema" minOccurs="0" name="{fme:get-attribute("name")}">
      						<simpleType>
      							<restriction base="decimal">
      								<totalDigits value="{fme:get-attribute("_matched_parts{0}")}"></totalDigits>
      								<fractionDigits value="{fme:get-attribute("_matched_parts{1}")}"></fractionDigits>
      							</restriction>
      						</simpleType>
      					</element>
    -> Sampler
    -> XMLTemplater_3 [input 2]
Note: Create feature type points
XMLTemplater_11
    VISIBLE_QUERY_VALIDATE = Yes
    COMPLEX_QUERY_EXPR:
      					<element xmlns="http://www.w3.org/2001/XMLSchema" minOccurs="0" name="{fme:get-attribute("name")}">
      						<simpleType>
      							<restriction base="string">
      								<maxLength value="{fme:get-attribute("_matched_parts{0}")}"></maxLength>
      							</restriction>
      						</simpleType>
      					</element>
    SIMPLE_QUERY_EXPR = <element xmlns="http://www.w3.org/2001/XMLSchema" minOccurs="0" name="{fme:get-attribute("name")}" type="{fme:get-attribute("wfs_data_type")}"></element>
    ROOT_QUERY_EXPR:
      	<complexType xmlns="http://www.w3.org/2001/XMLSchema" name="{fme:get-attribute("fme_feature_type_name")}Type">
      		<complexContent>
      			<extension base="gml:AbstractFeatureType">
      				<sequence>

                          {fme:process-features("DECIMAL")}
                          {fme:process-features("COMPLEX")}
                          {fme:process-features("SIMPLE")}

       <!--                   <element name="lineStringProperty" type="gml:GeometryPropertyType"></element>
                          <element name="multiLineStringProperty" type="gml:GeometryPropertyType"></element>
                          <element name="polygonProperty" type="gml:GeometryPropertyType"></element>
                          <element name="multiPolygonProperty" type="gml:GeometryPropertyType"></element>
                          <element name="multiPointProperty" type="gml:GeometryPropertyType"></element>-->
      					<choice>
      						<element ref="gml:lineStringProperty" type="gml:GeometryPropertyType"></element>
      						<element ref="gml:multiLineStringProperty" type="gml:GeometryPropertyType"></element>
      						<element ref="gml:polygonProperty" type="gml:GeometryPropertyType"></element>
      						<element ref="gml:multiPolygonProperty" type="gml:GeometryPropertyType"></element>
      						<element ref="gml:pointProperty" type="gml:GeometryPropertyType"></element>
      						<element ref="gml:multiPointProperty" type="gml:GeometryPropertyType"></element>
      					</choice>
                          <element name="pointProperty" type="gml:GeometryPropertyType"></element>
                      </sequence>
      			</extension>
      		</complexContent>
      	</complexType>
    CONSECUTIVE_GROUPS = No
    GROUP_BY = fme_feature_type_name
    OUTPUT_XML_HEADER = Yes
    RESULT_ATTRIBUTE = _result
    DECIMAL_QUERY_EXPR:
      					<element xmlns="http://www.w3.org/2001/XMLSchema" minOccurs="0" name="{fme:get-attribute("name")}">
      						<simpleType>
      							<restriction base="decimal">
      								<totalDigits value="{fme:get-attribute("_matched_parts{0}")}"></totalDigits>
      								<fractionDigits value="{fme:get-attribute("_matched_parts{1}")}"></fractionDigits>
      							</restriction>
      						</simpleType>
      					</element>
    -> Sampler
    -> XMLTemplater_3 [input 2]
Sampler
    SAMPLE_TYPE_LONG = First N Features
    RATE = 1
    SAMPLED -> XMLTemplater_3 [input 1]
Note: Create DescribeFeatures
XMLTemplater_3
    VISIBLE_QUERY_VALIDATE = Yes
    ROOT_QUERY_EXPR:
      <?xml version="1.0" encoding="UTF-8"?>
      <schema xmlns:xlink="http://www.w3.org/1999/xlink" xmlns:$(GML_OUT_TARGET_NS_PREFIX_GML)="$(GML_OUT_TARGET_NS_URI_GML)" xmlns:gml="http://www.opengis.net/gml" xmlns="http://www.w3.org/2001/XMLSchema" elementFormDefault="qualified" targetNamespace="$(GML_OUT_TARGET_NS_URI_GML)">
      	<import namespace="http://www.opengis.net/gml" schemaLocation="http://schemas.opengis.net/gml/2.1.2/feature.xsd"></import>

          {fme:process-features("ELEMENTS")}

      </schema>
    OUTPUT_XML_HEADER = Yes
    ELEMENTS_QUERY_EXPR:
      	<element xmlns="http://www.w3.org/2001/XMLSchema" name="{fme:get-attribute("fme_feature_type_name")}" substitutionGroup="gml:_Feature" type="$(GML_OUT_TARGET_NS_PREFIX_GML):{fme:get-attribute("fme_feature_type_name")}Type"></element>
          ,{fme:get-xml-attribute("_result")}
    RESULT_ATTRIBUTE = DescFeatType
    -> XMLFormatter_2

Bookmark: WFS 1.1.0
Note: Keep only requested features
Tester_2
    BOOL_OP = OR
    TEST_CLAUSE:
      TEST $(GML_OUT_TARGET_NS_PREFIX_GML):@Value(fme_feature_type_name) IN @Value(TYPENAME)
      TEST $(GML_OUT_TARGET_NS_PREFIX_GML):@Value(fme_feature_type_name) IN @Value(TYPENAMES)
    TEST_MODE = Automatic
    TEST_DESCRIPTION = ""
    PASSED -> ListExploder_2
    PASSED -> XMLTemplater_6 [input 1]
Note: Explode list of attributes
ListExploder_2
    MODE = List Elements and Original Attributes
    LIST_ATTR = attribute{}
    LIST_FOUND -> StringSearcher_4
Note: Decimal, String / and other attribtes
StringSearcher_4
    MATCHED_RESULT_ATTR = _matched_characters
    STRING_TO_SEARCH = @Value(fme_data_type)
    REGEXP = [(]([0-9]*),([0-9]*)[)]
    MATCHED_PARTS_ATTR = _matched_parts
    CASE = no
    NOT_MATCHED -> StringSearcher_3
    MATCHED -> XMLTemplater_6 [input 2]
StringSearcher_3
    MATCHED_RESULT_ATTR = _matched_characters
    STRING_TO_SEARCH = @Value(fme_data_type)
    REGEXP = [(]([0-9]*)[)]
    MATCHED_PARTS_ATTR = _matched_parts
    CASE = no
    NOT_MATCHED -> AttributeValueMapper_2
    MATCHED -> XMLTemplater_6 [input 3]
AttributeValueMapper_2
    VAL_ATTR = wfs_data_type
    LUT = fme_buffer,string,fme_char,string,fme_int64,long,fme_uint64,unsignedLong,fme_int32,int,fme_uint32,unsignedInt,fme_int16,short,fme_uint16,unsignedShort,fme_uint8,unsignedByte,fme_real32,float,fme_real64,double,fme_boolean,boolean,fme_datetime,string,fme_date,string,fme_time,string
    SRC = fme_data_type
    DIRECTION = Forward (Source To Destination)
    -> XMLTemplater_6 [input 4]
Note: Create feature type
XMLTemplater_6
    VISIBLE_QUERY_VALIDATE = Yes
    COMPLEX_QUERY_EXPR:
      					<element minOccurs="0" name="{fme:get-attribute("name")}">
      						<simpleType>
      							<restriction base="string">
      								<maxLength value="{fme:get-attribute("_matched_parts{0}")}"></maxLength>
      							</restriction>
      						</simpleType>
      					</element>
    SIMPLE_QUERY_EXPR = <element minOccurs="0" name="{fme:get-attribute("name")}" type="{fme:get-attribute("wfs_data_type")}"></element>
    ROOT_QUERY_EXPR:
      	<complexType name="{fme:get-attribute("fme_feature_type_name")}Type">
      		<complexContent>
      			<extension base="gml:AbstractFeatureType">
      				<sequence>

                          {fme:process-features("DECIMAL")}
                          {fme:process-features("COMPLEX")}
                          {fme:process-features("SIMPLE")}

      					<element minOccurs="0" ref="gml:curveProperty"></element>
      					<element minOccurs="0" ref="gml:multiCurveProperty"></element>
      					<element minOccurs="0" ref="gml:surfaceProperty"></element>
      					<element minOccurs="0" ref="gml:multiSurfaceProperty"></element>
      					<element minOccurs="0" ref="gml:pointProperty"></element>
      					<element minOccurs="0" ref="gml:multiPointProperty"></element>
      				</sequence>
      			</extension>
      		</complexContent>
      	</complexType>
    CONSECUTIVE_GROUPS = No
    GROUP_BY = fme_feature_type_name
    OUTPUT_XML_HEADER = Yes
    RESULT_ATTRIBUTE = _result
    DECIMAL_QUERY_EXPR:
      					<element minOccurs="0" name="{fme:get-attribute("name")}">
      						<simpleType>
      							<restriction base="decimal">
      								<totalDigits value="{fme:get-attribute("_matched_parts{0}")}"></totalDigits>
      								<fractionDigits value="{fme:get-attribute("_matched_parts{1}")}"></fractionDigits>
      							</restriction>
      						</simpleType>
      					</element>
    -> XMLTemplater_7 [input 2]
    -> Sampler_2
Sampler_2
    SAMPLE_TYPE_LONG = First N Features
    RATE = 1
    SAMPLED -> XMLTemplater_7 [input 1]
Note: Create DescribeFeatures
XMLTemplater_7
    VISIBLE_QUERY_VALIDATE = Yes
    ROOT_QUERY_EXPR:
      <schema xmlns:xlink="http://www.w3.org/1999/xlink" xmlns:gml="http://www.opengis.net/gml" xmlns="http://www.w3.org/2001/XMLSchema" xmlns:$(GML_OUT_TARGET_NS_PREFIX_GML)="$(GML_OUT_TARGET_NS_URI_GML)" elementFormDefault="qualified" targetNamespace="$(GML_OUT_TARGET_NS_URI_GML)">
      	<import namespace="http://www.opengis.net/gml" schemaLocation="http://schemas.opengis.net/gml/3.1.1/base/gml.xsd"></import>

          {fme:process-features("ELEMENTS")}

      </schema>
    OUTPUT_XML_HEADER = Yes
    ELEMENTS_QUERY_EXPR:
      	<element name="{fme:get-attribute("fme_feature_type_name")}" substitutionGroup="gml:_Feature" type="$(GML_OUT_TARGET_NS_PREFIX_GML):{fme:get-attribute("fme_feature_type_name")}Type"></element>
          ,{fme:get-xml-attribute("_result")}
    RESULT_ATTRIBUTE = DescFeatType
    -> XMLFormatter_2

Bookmark: WFS 2.0.0
Note: Keep only requested features
Tester_3
    BOOL_OP = OR
    TEST_CLAUSE:
      TEST $(GML_OUT_TARGET_NS_PREFIX_GML):@Value(fme_feature_type_name) IN @Value(TYPENAME)
      TEST $(GML_OUT_TARGET_NS_PREFIX_GML):@Value(fme_feature_type_name) IN @Value(TYPENAMES)
    TEST_MODE = Automatic
    TEST_DESCRIPTION = ""
    PASSED -> ListExploder_3
    PASSED -> XMLTemplater_8 [input 1]
Note: Explode list of attributes
ListExploder_3
    MODE = List Elements and Original Attributes
    LIST_ATTR = attribute{}
    LIST_FOUND -> StringSearcher_6
Note: Decimal, String / and other attribtes
StringSearcher_6
    MATCHED_RESULT_ATTR = _matched_characters
    STRING_TO_SEARCH = @Value(fme_data_type)
    REGEXP = [(]([0-9]*),([0-9]*)[)]
    MATCHED_PARTS_ATTR = _matched_parts
    CASE = no
    NOT_MATCHED -> StringSearcher_5
    MATCHED -> XMLTemplater_8 [input 2]
StringSearcher_5
    MATCHED_RESULT_ATTR = _matched_characters
    STRING_TO_SEARCH = @Value(fme_data_type)
    REGEXP = [(]([0-9]*)[)]
    MATCHED_PARTS_ATTR = _matched_parts
    CASE = no
    NOT_MATCHED -> AttributeValueMapper_3
    MATCHED -> XMLTemplater_8 [input 3]
AttributeValueMapper_3
    VAL_ATTR = wfs_data_type
    LUT = fme_buffer,string,fme_char,string,fme_int64,long,fme_uint64,unsignedLong,fme_int32,int,fme_uint32,unsignedInt,fme_int16,short,fme_uint16,unsignedShort,fme_uint8,unsignedByte,fme_real32,float,fme_real64,double,fme_boolean,boolean,fme_datetime,string,fme_date,string,fme_time,string
    SRC = fme_data_type
    DIRECTION = Forward (Source To Destination)
    -> XMLTemplater_8 [input 4]
Note: Create feature type
XMLTemplater_8
    VISIBLE_QUERY_VALIDATE = Yes
    COMPLEX_QUERY_EXPR:
      					<element minOccurs="0" name="{fme:get-attribute("name")}">
      						<simpleType>
      							<restriction base="string">
      								<maxLength value="{fme:get-attribute("_matched_parts{0}")}"></maxLength>
      							</restriction>
      						</simpleType>
      					</element>
    SIMPLE_QUERY_EXPR = <element minOccurs="0" name="{fme:get-attribute("name")}" type="{fme:get-attribute("wfs_data_type")}"></element>
    ROOT_QUERY_EXPR:
      	<complexType name="{fme:get-attribute("fme_feature_type_name")}Type">
      		<complexContent>
      			<extension base="gml:AbstractFeatureType">
      				<sequence>

                          {fme:process-features("DECIMAL")}
                          {fme:process-features("COMPLEX")}
                          {fme:process-features("SIMPLE")}

      					<element minOccurs="0" ref="gml:curveProperty"></element>
      					<element minOccurs="0" ref="gml:multiCurveProperty"></element>
      					<element minOccurs="0" ref="gml:surfaceProperty"></element>
      					<element minOccurs="0" ref="gml:multiSurfaceProperty"></element>
      					<element minOccurs="0" ref="gml:pointProperty"></element>
      					<element minOccurs="0" ref="gml:multiPointProperty"></element>
      				</sequence>
      			</extension>
      		</complexContent>
      	</complexType>
    CONSECUTIVE_GROUPS = No
    GROUP_BY = fme_feature_type_name
    OUTPUT_XML_HEADER = Yes
    RESULT_ATTRIBUTE = _result
    DECIMAL_QUERY_EXPR:
      					<element minOccurs="0" name="{fme:get-attribute("name")}">
      						<simpleType>
      							<restriction base="decimal">
      								<totalDigits value="{fme:get-attribute("_matched_parts{0}")}"></totalDigits>
      								<fractionDigits value="{fme:get-attribute("_matched_parts{1}")}"></fractionDigits>
      							</restriction>
      						</simpleType>
      					</element>
    -> XMLTemplater_9 [input 2]
    -> Sampler_3
Sampler_3
    SAMPLE_TYPE_LONG = First N Features
    RATE = 1
    SAMPLED -> XMLTemplater_9 [input 1]
Note: Create DescribeFeatures
XMLTemplater_9
    VISIBLE_QUERY_VALIDATE = Yes
    ROOT_QUERY_EXPR:
      <schema xmlns:gml="http://www.opengis.net/gml/3.2" xmlns:xlink="http://www.w3.org/1999/xlink" xmlns:$(GML_OUT_TARGET_NS_PREFIX_GML)="$(GML_OUT_TARGET_NS_URI_GML)"  xmlns="http://www.w3.org/2001/XMLSchema" targetNamespace="$(GML_OUT_TARGET_NS_URI_GML)" elementFormDefault="qualified">
      	<import namespace="http://www.opengis.net/gml/3.2" schemaLocation="http://schemas.opengis.net/gml/3.2.1/gml.xsd"></import>

          {fme:process-features("ELEMENTS")}

      </schema>
    OUTPUT_XML_HEADER = Yes
    ELEMENTS_QUERY_EXPR:
      	<element name="{fme:get-attribute("fme_feature_type_name")}" substitutionGroup="gml:AbstractFeature" type="$(GML_OUT_TARGET_NS_PREFIX_GML):{fme:get-attribute("fme_feature_type_name")}Type"></element>
          ,{fme:get-xml-attribute("_result")}
    RESULT_ATTRIBUTE = DescFeatType
    -> XMLFormatter_2

Bookmark: GetFeatures
Note: Fjerner Namespace / fra Type names
StringReplacer_2
    FIND_TEXT = $(GML_OUT_TARGET_NS_PREFIX_GML):
    REGEXP = no
    NO_MATCH = _FME_NO_OP_
    SRC_ATTRS = TYPENAME,TYPENAMES
    CASE = no
    -> StringReplacer
StringReplacer
    FIND_TEXT = ,
    REGEXP = no
    REPLACE_TEXT = " "
    NO_MATCH = _FME_NO_OP_
    SRC_ATTRS = TYPENAME,TYPENAMES
    CASE = no
    -> Tester_4
Note: Different WFS versions have / different type name attributes
Tester_4
    BOOL_OP = OR
    TEST_CLAUSE = TEST @Value(VERSION) = 2.0.0
    TEST_MODE = Automatic
    TEST_DESCRIPTION = ""
    PASSED -> AttributeCopier
    FAILED -> AttributeCopier_2
Note: WFS 2.0.0
AttributeCopier
    ATTR_LIST = TYPENAMES,_types,"",COUNT,Teller,""
    -> Tester_5
AttributeCopier_2
    ATTR_LIST = TYPENAME,_types,"",MAXFEATURES,Teller,""
    -> Tester_5
Note: Finnes BBOX?
Tester_5
    BOOL_OP = OR
    TEST_CLAUSE:
      TEST BBOX ATTRIBUTE_IS_EMPTY ""
      TEST BBOX ATTRIBUTE_IS_MISSING ""
      TEST BBOX ATTRIBUTE_VALUE_NULL ""
    TEST_MODE = Automatic
    TEST_DESCRIPTION = ""
    FAILED -> AttributeSplitter_2
    PASSED -> Tester_11
Note: WFS 2.0 BBOX?
Tester_11
    BOOL_OP = OR
    TEST_CLAUSE = TEST @Value(FILTER) CONTAINS fes:BBOX
    TEST_MODE = Automatic
    TEST_DESCRIPTION = ""
    FAILED -> 2DBoxReplacer
    PASSED -> WFS2.0BBOXCreator
WFS2.0BBOXCreator
    FILTER = @Value(FILTER)
    Reprojector_4_Reprojected -> BulkAttributeRemover
Note: Ingen BBOX - bruker veldig stor BBOX
2DBoxReplacer
    MINXVALATTR = -1000000000000
    MINYVALATTR = -1000000000000
    MAXYVALATTR = 1000000000000
    MAXXVALATTR = 1000000000000
    BOX -> BulkAttributeRemover
Note: Get BBOX coords from parameter
AttributeSplitter_2
    ATTR_NAME = BBOX
    DELIMITER = ,
    TRIM_OPTION = Both
    DROP_EMPTY_PARTS = No
    LIST_NAME = _bbox
    -> 2DBoxReplacer_2
Note: Create boundary from BBOX
2DBoxReplacer_2
    MINXVALATTR = @Value(_bbox{0})
    MINYVALATTR = @Value(_bbox{1})
    MAXYVALATTR = @Value(_bbox{3})
    MAXXVALATTR = @Value(_bbox{2})
    BOX -> Tester_10
Note: Is SRSNAME provided?
Tester_10
    BOOL_OP = OR
    TEST_CLAUSE = TEST SRSNAME ATTRIBUTE_IS_EMPTY ""
    TEST_MODE = Automatic
    TEST_DESCRIPTION = ""
    FAILED -> AttributeValueMapper_6
    PASSED -> BulkAttributeRemover
Note: If urn-notation is provided, map to standard EPSG
AttributeValueMapper_6
    VAL_ATTR = SRSNAME
    LUT = urn:ogc:def:crs:EPSG::4258,EPSG:4258,urn:ogc:def:crs:EPSG::4326,EPSG:4326,urn:ogc:def:crs:EPSG::25830,EPSG:25830,urn:ogc:def:crs:EPSG::25831,EPSG:25831,urn:ogc:def:crs:EPSG::25832,EPSG:25832,urn:ogc:def:crs:EPSG::25833,EPSG:25833,urn:ogc:def:crs:EPSG::25834,EPSG:25834,urn:ogc:def:crs:EPSG::25835,EPSG:25835,urn:ogc:def:crs:EPSG::25836,EPSG:25836,urn:ogc:def:crs:EPSG::3044,EPSG:3044,urn:ogc:def:crs:EPSG::3045,EPSG:3045
    DEFAULT_VALUE = @Value(SRSNAME)
    SRC = SRSNAME
    DIRECTION = Forward (Source To Destination)
    -> Reprojector_5
Note: Reprojects to default coordinate system
Reprojector_5
    RASTER_CELL_SIZE = Preserve Cells
    DEST = EPSG:4258
    SOURCE = @Value(SRSNAME)
    INTERPOLATION_TYPE_NAME = Nearest Neighbor
    REPROJECTED -> BulkAttributeRemover
FeatureMerger_2
    ATTR_CONFLICT_RES = Use Requestor
    SUPPLIERS_FIRST = No
    PROCESS_DUPS = No
    MERGE_TYPE = Attributes Only
    JOIN_KEYS = 1 1 AUTO
    ATTR_ACCUM_MODE = Merge Supplier
    IGNORE_NULLS = No
    MERGED -> _FeatureReader_Source
    NOT_MERGED -> _FeatureReader_Source
Note: Leser objekter fra databasen, bruker eventuell avgrensningsboks.
_FeatureReader_Source: FeatureReader
    ATTR_NAME = _types
    COMBINE_GEOM = Use Result
    POSTGIS_USE_TRUE_POSTGIS_TYPES = yes
    POSTGIS_USER_NAME = geonortst
    POSTGIS_HOST = Nnridb504
    FEATURETYPES_RADIO = ATTR_NAME
    POSTGIS_SCHEMALIST = dsb
    ATTR_ACCUM_MODE = Merge Initiator and Result
    WHERE = @Value(_where)
    DATASET = geonor01tst
    POSTGIS_QUERY_FEATURE_TYPES_FOR_MERGE_FILTERS = Yes
    POSTGIS_PASSWORD =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
    INTERACT = Intersects
    POSTGIS_CLIP_TO_ENVELOPE = NO
    POSTGIS_USE_SEARCH_ENVELOPE = NO
    ATTR_CONFLICT_RES = Use Result
    FORMAT = POSTGIS
    POSTGIS_PORT = 5432
    POSTGIS_DISABLE_COLLECTION_SPLITTING = yes
    <OTHER> -> Tester_9
Note: Is SRSNAME provided?
Tester_7
    BOOL_OP = OR
    TEST_CLAUSE = TEST SRSNAME ATTRIBUTE_IS_EMPTY ""
    TEST_MODE = Automatic
    TEST_DESCRIPTION = ""
    PASSED -> Reprojector_3
    FAILED -> AttributeValueMapper_5
Note: Reprojects to default coordinate system
Reprojector_3
    RASTER_CELL_SIZE = Preserve Cells
    DEST = EPSG:4258
    SOURCE = EPSG:4258
    INTERPOLATION_TYPE_NAME = Nearest Neighbor
    REPROJECTED -> AttributeFilter_4
Note: If urn-notation is provided, map to standard EPSG
AttributeValueMapper_5
    VAL_ATTR = SRSNAME
    LUT = urn:ogc:def:crs:EPSG::4258,EPSG:4258,urn:ogc:def:crs:EPSG::4326,EPSG:4326,urn:ogc:def:crs:EPSG::25830,EPSG:25830,urn:ogc:def:crs:EPSG::25831,EPSG:25831,urn:ogc:def:crs:EPSG::25832,EPSG:25832,urn:ogc:def:crs:EPSG::25833,EPSG:25833,urn:ogc:def:crs:EPSG::25834,EPSG:25834,urn:ogc:def:crs:EPSG::25835,EPSG:25835,urn:ogc:def:crs:EPSG::25836,EPSG:25836,urn:ogc:def:crs:EPSG::3044,EPSG:3044,urn:ogc:def:crs:EPSG::3045,EPSG:3045
    DEFAULT_VALUE = @Value(SRSNAME)
    SRC = SRSNAME
    DIRECTION = Forward (Source To Destination)
    -> Reprojector_2
Note: Reprojects to destination coordinate system
Reprojector_2
    RASTER_CELL_SIZE = Preserve Cells
    DEST = @Value(SRSNAME)
    SOURCE = EPSG:4258
    INTERPOLATION_TYPE_NAME = Nearest Neighbor
    REPROJECTED -> AttributeFilter_4
Note: Ulike GML-writere for ulike WFS-versjoner
AttributeFilter_4
    ATTR_VALUES = <EMPTY>,<MISSING>,<NULL>,<UNFILTERED>,1.0.0,1.1.0,2.0.0
    ATTR_NAME = VERSION
    1.1.0 -> GML3.1 (writer GML_1)
    2.0.0 -> GML3.2 (writer GML_2)
    1.0.0 -> CoordinateConcatenator
CoordinateConcatenator
    COORD_ATTR = attr_Geometry
    ELEMENT_DELIM = " "
    COORDINATES_TO_INCLUDE_DIS = X Y
    -> GML2 (writer GML2_1)
Note: WFS 1.0.0
GML2 (writer GML2_1)
Note: WFS 1.1.0
GML3.1 (writer GML_1)
Note: WFS 2.0.0
GML3.2 (writer GML_2)

Bookmark: Implement Filter as SQL for SQL enabled datasets
Note: "Renser" XML-attributter
BulkAttributeRemover
    ATTR_EXP = xml_
    -> Tester_6
    -> FeatureMerger_2 [input 1]
Note: Sjekker om filter er satt
Tester_6
    BOOL_OP = OR
    TEST_CLAUSE:
      TEST FILTER ATTRIBUTE_VALUE_NULL ""
      TEST FILTER ATTRIBUTE_IS_EMPTY ""
      TEST FILTER ATTRIBUTE_IS_MISSING ""
    TEST_MODE = Automatic
    TEST_DESCRIPTION = ""
    PASSED -> AttributeCreator_5
    FAILED -> XMLFragmenter_2
Note: Trekker ut filterspørringe
XMLFragmenter_2
    MERGE_ATTRS = Yes
    ATTRIBUTE_XML = FILTER
    XML_SOURCE_TYPE = Attribute with XML document
    EMBEDDED_EXPRESSIONS = Filter/*
    FLATTEN_OPTIONS = <structure separator="." map-empty-elements="yes" matched-prefix="attributes" matched-attributes="yes" cardinality="+{?}" structure-prefix="" child-position-attribute="" except-expression="" ui-mode="basic" matched-ancestor-attributes=""/>
    NEW_ATTRIBUTES = PropertyName Literal LowerBoundary.Literal UpperBoundary.Literal
    FRAGMENTS -> AttributeFilter_7
AttributeFilter_7
    ATTR_VALUES = <EMPTY>,<MISSING>,<NULL>,<UNFILTERED>,PropertyIsEqualTo,PropertyIsNotEqualTo,PropertyIsLessThan,PropertyIsLessThanOrEqualTo,PropertyIsGreaterThan,PropertyIsGreaterThanOrEqualTo,PropertyIsLike,PropertyIsNull,PropertyIsBetween
    ATTR_NAME = xml_matched_element
    PropertyIsEqualTo -> AttributeValueMapper_4
    PropertyIsNull -> AttributeCreator_3
    PropertyIsBetween -> AttributeCreator_4
    PropertyIsNotEqualTo -> AttributeValueMapper_4
    PropertyIsLessThan -> AttributeValueMapper_4
    PropertyIsLessThanOrEqualTo -> AttributeValueMapper_4
    PropertyIsGreaterThan -> AttributeValueMapper_4
    PropertyIsGreaterThanOrEqualTo -> AttributeValueMapper_4
    PropertyIsLike -> AttributeValueMapper_4
    <UNFILTERED> -> AttributeCreator_5
    <NULL> -> AttributeCreator_5
    <MISSING> -> AttributeCreator_5
    <EMPTY> -> AttributeCreator_5
Note: Lager "dummy" where-clause
AttributeCreator_5
    ATTR_LIST = _where,1=1
    -> FeatureMerger_2 [input 2]
Note: Mapper operatorer til SQL
AttributeValueMapper_4
    VAL_ATTR = _operator
    LUT = PropertyIsEqualTo,=,PropertyIsNotEqualTo,<>,PropertyIsLessThan,<,PropertyIsLessThanOrEqualTo,<=,PropertyIsGreaterThan,>,PropertyIsGreaterThanOrEqualTo,>=,PropertyIsLike,LIKE
    SRC = xml_matched_element
    DIRECTION = Forward (Source To Destination)
    -> AttributeCreator_2
Note: Lager where-clause
AttributeCreator_2
    ATTR_LIST = _where,@Value(PropertyName) @Value(_operator) @Value(Literal)
    -> FeatureMerger_2 [input 2]
Note: Lager where-clause
AttributeCreator_3
    ATTR_LIST = _where,@Value(PropertyName) IS NULL
    -> FeatureMerger_2 [input 2]
Note: Lager where-clause
AttributeCreator_4
    ATTR_LIST = _where,@Value(PropertyName) BETWEEN @Value(LowerBoundary.Literal) AND @Value(UpperBoundary.Literal)
    -> FeatureMerger_2 [input 2]

Bookmark: Limit number of features if count or maxfeatures is set
Tester_9
    BOOL_OP = OR
    TEST_CLAUSE:
      TEST Teller ATTRIBUTE_IS_EMPTY ""
      TEST Teller ATTRIBUTE_IS_MISSING ""
      TEST Teller ATTRIBUTE_VALUE_NULL ""
    TEST_MODE = Automatic
    TEST_DESCRIPTION = ""
    FAILED -> Counter
    PASSED -> Tester_7
Counter
    DOMAIN = counter
    SCOPE = Global
    START = 0
    CNT_ATTR = _count
    -> Tester_8
Tester_8
    BOOL_OP = OR
    TEST_CLAUSE = TEST @Value(_count) < @Value(Teller)
    TEST_MODE = Automatic
    TEST_DESCRIPTION = ""
    PASSED -> Tester_7

FME custom transformer WFS2.0BBOXCreator

Parameters:
- FILTER = @Value(FILTER)

StringReplacer_3_Input (input)
    -> StringReplacer_3
StringReplacer_3
    FIND_TEXT = +
    REGEXP = no
    REPLACE_TEXT = " "
    NO_MATCH = _FME_NO_OP_
    SRC_ATTRS = FILTER
    CASE = no
    -> XMLFragmenter_4
Note: Extracts filter with BBOX
XMLFragmenter_4
    MERGE_ATTRS = Yes
    ATTRIBUTE_XML = FILTER
    XML_SOURCE_TYPE = Attribute with XML document
    EMBEDDED_EXPRESSIONS = fes:BBOX/*
    FLATTEN_OPTIONS = <structure separator="." map-empty-elements="yes" matched-prefix="attributes" matched-attributes="yes" cardinality="+{?}" structure-prefix="" child-position-attribute="" except-expression="" ui-mode="basic" matched-ancestor-attributes=""/>
    NEW_ATTRIBUTES = lowerCorner upperCorner Envelope.srsName
    FRAGMENTS -> AttributeCreator_7
AttributeCreator_7
    ATTR_LIST = gml_bbox,@Value(lowerCorner) @Value(upperCorner)
    -> AttributeSplitter_3
AttributeSplitter_3
    ATTR_NAME = gml_bbox
    DELIMITER = " "
    TRIM_OPTION = Both
    DROP_EMPTY_PARTS = No
    LIST_NAME = gml_bboxlist
    -> Tester_2
Tester_2
    BOOL_OP = OR
    TEST_CLAUSE:
      TEST @Value(Envelope.srsName) = urn:ogc:def:crs:EPSG::4258
      TEST @Value(Envelope.srsName) = EPSG:4258
      TEST @Value(Envelope.srsName) = urn:ogc:def:crs:EPSG::4326
      TEST @Value(Envelope.srsName) = EPSG:4326
      TEST @Value(Envelope.srsName) = urn:ogc:def:crs:EPSG::3044
      TEST @Value(Envelope.srsName) = urn:ogc:def:crs:EPSG::3045
      TEST @Value(Envelope.srsName) = EPSG:3044
      TEST @Value(Envelope.srsName) = EPSG:3045
    TEST_MODE = Automatic
    TEST_DESCRIPTION = ""
    PASSED -> 2DBoxReplacer_3
    FAILED -> 2DBoxReplacer_2
Note: Create boundary from BBOX
2DBoxReplacer_3
    MINXVALATTR = @Value(gml_bboxlist{1})
    MINYVALATTR = @Value(gml_bboxlist{0})
    MAXYVALATTR = @Value(gml_bboxlist{2})
    MAXXVALATTR = @Value(gml_bboxlist{3})
    BOX -> AttributeValueMapper_7
Note: Create boundary from BBOX
2DBoxReplacer_2
    MINXVALATTR = @Value(gml_bboxlist{0})
    MINYVALATTR = @Value(gml_bboxlist{1})
    MAXYVALATTR = @Value(gml_bboxlist{3})
    MAXXVALATTR = @Value(gml_bboxlist{2})
    BOX -> AttributeValueMapper_7
Note: If urn-notation is provided, map to standard EPSG
AttributeValueMapper_7
    VAL_ATTR = Envelope.srsName
    LUT = urn:ogc:def:crs:EPSG::4258,EPSG:4258,urn:ogc:def:crs:EPSG::4326,EPSG:4326,urn:ogc:def:crs:EPSG::25830,EPSG:25830,urn:ogc:def:crs:EPSG::25831,EPSG:25831,urn:ogc:def:crs:EPSG::25832,EPSG:25832,urn:ogc:def:crs:EPSG::25833,EPSG:25833,urn:ogc:def:crs:EPSG::25834,EPSG:25834,urn:ogc:def:crs:EPSG::25835,EPSG:25835,urn:ogc:def:crs:EPSG::25836,EPSG:25836,urn:ogc:def:crs:EPSG::3044,EPSG:3044,urn:ogc:def:crs:EPSG::3045,EPSG:3045
    DEFAULT_VALUE = @Value(Envelope.srsName)
    SRC = Envelope.srsName
    DIRECTION = Forward (Source To Destination)
    -> Reprojector_4
Note: Reprojects to default coordinate system
Reprojector_4
    RASTER_CELL_SIZE = Preserve Cells
    DEST = EPSG:4258
    SOURCE = @Value(Envelope.srsName)
    INTERPOLATION_TYPE_NAME = Nearest Neighbor
    REPROJECTED -> Reprojector_4_Reprojected (output)
Reprojector_4_Reprojected (output)

FME custom transformer FMEServerURLSplitter
This transformer is useful for breaking up the full URI request that is sent to FME Server. The transformer actually takes any URL and breaks it up into pieces, so it could be applied elsewhere.
With FME 2014 Server the entire request URL is now held in the FME_SERVER_REQUEST_URI parameter so that it can be used within the workspace. This is useful in cases where extra parameters are tacked onto a URL or the URL path doesn't end with .fmw.
This capability makes it possible for FME Server to be used to satisfy new types of requests where the full request cannot be known until runtime.
Input:
Request URI: the full URI request made to FME Server, in string or attribute form
Output
base_url - This is the entire URL up to the starts of URL parameters. 
fme_server_base_url - The FME Server base url. Is the same as above if the base_url ends at .fmw. This is only present if the url has .fmw in it. 
fme_server_extra_url_path - the additional components of the path if it is from FME Server. This is present if the base_url is different from the fme_server_base_url.
fme_server_extra_url{} list - fme_server_extra_url_path broken up into a list for convenience
url_raw_parameters - These are all the url parameters as one string.
num_parms - The number of URL parameters after they have been parsed out. 
decoded parameters - The parameters themselves are also parsed out and turned into FME attributes. 
Example
Given the url 
http://dondemo/fmejobsubmitter/webdump/PublishParameterDump.fmw/another/value?DestDataset_TEXTLINE=output.txt&opt_showresult=false&opt_servicemode=sync&anotherparm=here
base_url has value `http://dondemo/fmejobsubmitter/webdump/PublishParameterDump.fmw/another/value'
fme_server_base_url has value `http://dondemo/fmejobsubmitter/webdump/PublishParameterDump.fmw/'
fme_server_extra_url_path' has value `another/value'
fme_server_extra_url{0}' has value 'another'
fme_server_extra_url{1}' has value 'value'
url_raw_parameters' has value 'DestDataset_TEXTLINE=output.txt&opt_showresult=false&opt_servicemode=sync&anotherparm=here'
num_parms' has value '4'
DestDataset_TEXTLINE has value 'output.txt'
anotherparm has value 'here'
opt_servicemode has value 'sync'
opt_showresult has value 'false'
Copyright (c) 2014 Safe Software Inc.
Permission is granted to anyone, free of charge, to use, modify and distribute the object code form of this transformer for any purpose, subject to the following restrictions:
1) The origin of this transformer and associated FME(R) software must not be misrepresented.
2) This transformer may only be used in conjunction with a validly licensed copy of FME software.
THIS SOFTWARE IS PROVIDED BY SAFE SOFTWARE INC. "AS IS" AND ANY EXPRESS OR IMPLIED WARRANTIES, INCLUDING, BUT NOT LIMITED TO, THE IMPLIED WARRANTIES OF MERCHANTABILITY, NONINFRINGEMENT AND FITNESS FOR A PARTICULAR PURPOSE ARE DISCLAIMED. IN NO EVENT SHALL SAFE SOFTWARE INC. BE LIABLE FOR ANY DIRECT, INDIRECT, INCIDENTAL, SPECIAL, EXEMPLARY, OR CONSEQUENTIAL DAMAGES (INCLUDING, BUT NOT LIMITED TO, PROCUREMENT OF SUBSTITUTE GOODS OR SERVICES; LOSS OF USE, DATA, OR PROFITS; OR BUSINESS INTERRUPTION) HOWEVER CAUSED AND ON ANY THEORY OF LIABILITY, WHETHER IN CONTRACT, STRICT LIABILITY, OR TORT (INCLUDING NEGLIGENCE OR OTHERWISE) ARISING IN ANY WAY OUT OF THE USE OF THIS SOFTWARE, EVEN IF ADVISED OF THE POSSIBILITY OF SUCH DAMAGE.

Parameters:
- _FME_SERVER_REQUEST_URI =   # Request URI
- URL_PARAM_NAME_CASE = Untouched   # case"%"Full Title Case"%Untouched URL Parameter Name Case
- DECODE_URL_TEXT = Don't Decode   # Decode" Decode URL Parameters

AttributeSplitter_Input (input)
    -> AttributeSplitter
Output (output)

Bookmark: First split url up into two peices ("base url" and "parm string")
AttributeSplitter
    ATTR_NAME = _FME_SERVER_REQUEST_URI
    DELIMITER = ?
    TRIM_OPTION = Both
    DROP_EMPTY_PARTS = No
    LIST_NAME = _list
    -> AttributeRenamer
AttributeRenamer
    ATTR_LIST = _list{0},base_url,"",_list{1},url_raw_parameters,""
    -> AttributeSplitter_2

Bookmark: Check if Parms and build list
Note: Now we split the parm string into a list.
AttributeSplitter_2
    ATTR_NAME = url_raw_parameters
    DELIMITER = &
    TRIM_OPTION = Both
    DROP_EMPTY_PARTS = No
    LIST_NAME = _paramList
    -> TestFilter
TestFilter
    TEST_LIST = BOOL_OP,OR,COMPOSITE_TEST,<Unused>,TEST_CLAUSE,"TEST _paramList{0} NOT_ATTRIBUTE_IS_EMPTY """"",Parameters
    DEFAULT_VALUE = NoParameters
    Parameters -> ListElementCounter
    NoParameters -> Remove_Empty_Argument
Note: No Parms so remove attribute
Remove_Empty_Argument: AttributeRemover
    REMOVE_ATTRS = url_raw_parameters
    -> StringSearcher

Bookmark: Loop Initialization
ListElementCounter
    CNT_ATTR = num_parms
    LIST_NAME = _paramList{}
    -> InitializeCounter
InitializeCounter: Counter
    DOMAIN = AttributeCount
    SCOPE = Global
    START = 0
    CNT_ATTR = currentListPos
    -> AttributeCreator_2

Bookmark: Iterate over all the parameters that were set
AttributeLooper (input)
    -> AttributeCreator_2

Bookmark: Extract a value and build attribute
AttributeCreator_2
    ATTR_LIST = curListEntry,@Value(_paramList{@Value(currentListPos)})
    -> Tester
Tester
    BOOL_OP = OR
    TEST_CLAUSE = TEST @Value(curListEntry) CONTAINS FES:FILTER
    TEST_MODE = Automatic
    TEST_DESCRIPTION = ""
    FAILED -> AttributeSplitter_3
    PASSED -> SubstringExtractor
SubstringExtractor
    END = 5
    SRC_STRING = @Value(curListEntry)
    RESULT_ATTR = paramEntry{0}
    START = 0
    -> SubstringExtractor_2
SubstringExtractor_2
    END = -1
    SRC_STRING = @Value(curListEntry)
    RESULT_ATTR = paramEntry{1}
    START = 7
    -> AreWeChangingCase
AttributeSplitter_3
    ATTR_NAME = curListEntry
    DELIMITER = =
    TRIM_OPTION = Both
    DROP_EMPTY_PARTS = No
    LIST_NAME = paramEntry
    -> AreWeChangingCase
AreWeDecodingURLText: TestFilter
    TEST_LIST = BOOL_OP,OR,COMPOSITE_TEST,<Unused>,TEST_CLAUSE,"TEST $(DECODE_URL_TEXT) = Decode",Decode
    DEFAULT_VALUE = Don't Decode
    Don't Decode -> AttributeCreator
    Decode -> DecodeParamName
DecodeParamName: TextDecoder
    DEST_ATTR = paramEntry{0}
    ENCODING_TYPE = URL (Percent Encoding)
    STRING_TO_DECODE = @Value(paramEntry{0})
    -> DecodeParamValue
DecodeParamValue: TextDecoder
    DEST_ATTR = paramEntry{1}
    ENCODING_TYPE = URL (Percent Encoding)
    STRING_TO_DECODE = @Value(paramEntry{1})
    -> AttributeCreator
AttributeCreator
    ATTR_LIST = @Value(paramEntry{0}),@Value(paramEntry{1})
    -> IncrementCounter
IncrementCounter: Counter
    DOMAIN = AttributeCount
    SCOPE = Global
    START = 0
    CNT_ATTR = currentListPos
    -> TestForMoreParms

Bookmark: Change Case
AreWeChangingCase: TestFilter
    TEST_LIST = BOOL_OP,OR,COMPOSITE_TEST,<Unused>,TEST_CLAUSE,"TEST $(URL_PARAM_NAME_CASE) = Untouched",No case change
    DEFAULT_VALUE = change case
    change case -> StringCaseChanger
    No case change -> AreWeDecodingURLText
StringCaseChanger
    CHANGE_TYPE = $(URL_PARAM_NAME_CASE)
    ATTRCHOICE = Selected Attributes
    ATTRLIST = paramEntry{0}
    -> AreWeDecodingURLText

Bookmark: Another Iteration?
TestForMoreParms: TestFilter
    TEST_LIST = BOOL_OP,OR,COMPOSITE_TEST,<Unused>,TEST_CLAUSE,"TEST @Value(currentListPos) < @Value(num_parms)",More Params
    DEFAULT_VALUE = All Done
    More Params -> AttributeLooper (output)
    All Done -> StringSearcher
AttributeLooper (output)

Bookmark: Extract URL Path after the *.fmw.
StringSearcher
    MATCHED_RESULT_ATTR = _matched_characters
    STRING_TO_SEARCH = @Value(base_url)
    REGEXP = ^(.*[.]fmw/)(.*)$
    MATCHED_PARTS_ATTR = _matched_parts
    CASE = no
    MATCHED -> AttributeRenamer_2
    NOT_MATCHED -> AttributeRemover
AttributeRenamer_2
    ATTR_LIST = _matched_parts{0},fme_server_base_url,"",_matched_parts{1},fme_server_extra_url_path,""
    -> AttributeSplitter_4
AttributeSplitter_4
    ATTR_NAME = fme_server_extra_url_path
    DELIMITER = /
    TRIM_OPTION = Both
    DROP_EMPTY_PARTS = No
    LIST_NAME = fme_server_extra_url
    -> AttributeRemover
AttributeRemover
    LIST_ATTRS = _paramList{} _matched_parts{} paramEntry{} _list{}
    REMOVE_ATTRS = currentListPos,curListEntry,_matched_characters
    -> Output (output)
