FME workspace DSBSentraldistrikterPostGIS2GML.fmw

Parameters:
- SourceDataset_POSTGIS = geonortst@Nnridb504:5432/geonor01tst   # Connection
- DestDataset_GML = $(FME_MF_DIR)PostGIS2GML_return.gml   # Destination Geography Markup Language (GML) File

Readers:
- POSTGIS_1: POSTGIS from $(SourceDataset_POSTGIS)

Writers:
- GML_1: GML to $(DestDataset_GML)

dsb.sentraldistrikter110grense (reader POSTGIS_1)
    attributes: objtype varchar(32), objid int4, avgrensningfk int4, avgrensningfk2 int4
    -> FeatureMerger [input 1]
dsb.sentraldistrikter110 (reader POSTGIS_1)
    attributes: lokalid uuid, navnerom text, versjonid varchar(2), msgeometry text, poly_ text, poly_id text, area text, perimeter text, oppr text, x float8, y float8, koordh text, sentral text, lokalisering text, opphav text, omradeid int8, originaldatavert text, kopidato timestamp, malemetode text, noyaktighet int8, synbarhet text, h_malemetode text, h_noyaktig text, max_avvik text, objtype text, navn text, datafangstdato date, objid int4
    -> FeatureMerger_2 [input 2]
    -> dsb.sentraldistrikter110 (writer GML_1)
    -> FeatureMerger [input 2]
FeatureMerger
    SUPPLIERS_FIRST = No
    PROCESS_DUPS = No
    JOIN_KEYS = @Value(avgrensningfk) @Value(objid) AUTO
    SUPPLIER_PREFIX = pref_
    ATTR_ACCUM_MODE = Prefix Supplier
    IGNORE_NULLS = No
    MERGE_TYPE = Attributes Only
    NOT_MERGED -> FeatureMerger_2 [input 1]
    MERGED -> AttributeCreator
AttributeCreator
    ATTR_LIST = sentraldisktrikt.xlink_href{0},@Value(pref_objid)
    -> FeatureMerger_2 [input 1]
FeatureMerger_2
    SUPPLIERS_FIRST = No
    GEOM_TYPE = Build Polygons
    PROCESS_DUPS = Yes
    JOIN_KEYS = @Value(avgrensningfk2) @Value(objid) AUTO
    SUPPLIER_PREFIX = pref2
    ATTR_ACCUM_MODE = Prefix Supplier
    IGNORE_NULLS = No
    MERGE_TYPE = Attributes Only
    MERGED -> AttributeCreator_2
    NOT_MERGED -> dsb.sentraldistrikter110grense (writer GML_1)
AttributeCreator_2
    ATTR_LIST = sentraldisktrikt.xlink_href{1},@Value(pref2objid)
    -> dsb.sentraldistrikter110grense (writer GML_1)
dsb.sentraldistrikter110grense (writer GML_1)
    attributes: objtype xml_char(32), avgrensningfk xml_int32, avgrensningfk2 xml_int32, sentraldistrikt.xlink_href{} xml_buffer
dsb.sentraldistrikter110 (writer GML_1)
    attributes: lokalid xml_buffer, navnerom xml_buffer, versjonid xml_char(2), msgeometry xml_buffer, poly_ xml_buffer, poly_id xml_buffer, area xml_buffer, perimeter xml_buffer, oppr xml_buffer, x xml_real64, y xml_real64, koordh xml_buffer, sentral xml_buffer, lokalisering xml_buffer, opphav xml_buffer, omradeid xml_int64, originaldatavert xml_buffer, kopidato xml_char(20), malemetode xml_buffer, noyaktighet xml_int64, synbarhet xml_buffer, h_malemetode xml_buffer, h_noyaktig xml_buffer, max_avvik xml_buffer, objtype xml_buffer, navn xml_buffer, datafangstdato xml_char(8), objid xml_int32
