FME workspace DSBAtomFeed.fmw
Title: SOSI ATOM Data Download Feed
Description: Pakka data for SOSI tilbys.
Requirements: FME 2015.0+
History: 23/02/2015,N Wlock,Created

Parameters:
- FMEServerRoot = http://nnrite507   # Base URL for the FME Server host
- Title = DSB ATOM Feed: DSB Data
- Description = DSB data for brannstasjoner, sentraldistrikter og Sivilforsvaret
- Author = Karen Lie   # Author of ATOM service
- Repository_Name = DSB   # Server Repository name which contains workspace(s)
- LastUpdate = 2015-08-19T16:15Z   # Date the workspace was last updated
- FMEVersion = 2015.0   # Version of FME being used
- ROTKATALOG_WEB = http://testnedlasting.geonorge.no/geonorge/DSB/SOSI/   # Sti til rotkatalog for SOSI-filene
- SourceDataset_POSTGRES = geonor01tst   # Database

Readers:
- POSTGRES_1: POSTGRES from $(SourceDataset_POSTGRES)

Writers:
- GEORSS_1: GEORSS to $(FME_MF_DIR)ATOM\DSBAtomFeed.xml

Entry (writer GEORSS_1)

Bookmark: Kommuner
admingrense.kommuner (reader POSTGRES_1)
    attributes: kommuneid int2,PRIKEY, navn varchar(80)
    -> AttributeRangeMapper_2
AttributeRangeMapper_2
    OUT_ATTR = koordsys
    LUT = 1,1799,25832,1800,1999,25833,2000,2099,25835,,,
    IN_ATTR = kommuneid
    -> TestFilter_2
    -> AttributeRangeMapper_2_Output
TestFilter_2
    DEFAULT_VALUE = <UNFILTERED>
    TEST_LIST = BOOL_OP,OR,COMPOSITE_TEST,<Unused>,TEST_CLAUSE,"TEST @Value(kommuneid) <= 1799",25832,BOOL_OP,OR,COMPOSITE_TEST,<Unused>,TEST_CLAUSE,"TEST @Value(kommuneid) >= 2000",25835
    <UNFILTERED> -> AttributeCreator_12
    25835 -> AttributeCreator_12
    25832 -> AttributeCreator_12
    25835 -> AttributeCreator_6
    25832 -> AttributeCreator_6
AttributeCreator_12
    ATTR_LIST = koordsys,25833
    -> AttributeCreator_6
Note: Lager nedlastingsURL
AttributeCreator_6
    ATTR_LIST = DownloadUrl,$(ROTKATALOG_WEB)/DSB_@PadLeft(@Value(kommuneid),4,0)_@Value(navn)_@Value(koordsys).zip,name,DSB,value,DSB SOSI Data @Value(navn)
    -> AttributeCreator_7
AttributeCreator_7
    ATTR_LIST = Title,@Value(value),Content,Trykk på linken for å laste ned data for kommune @PadLeft(@Value(kommuneid),4,0), @Value(navn) i koordinatsystemet EPSG:@Value(koordsys). <br />  <a href="@Value(DownloadUrl)">@Value(value)<\a>,Description,Data for Sivilforsvaret og Brannvesenet. Trykk på linken for nedlasting: @Value(value),ContentType,html,LastUpdate,$(LastUpdate),Id,@Value(DownloadUrl),Category{0}.Category,EPSG:@Value(koordsys),Category{0}.Domain,http://www.opengis.net/def/crs/,Category{0}.Label,EPSG/0/@Value(koordsys),Author,Karen Lie,Copyright,DSB - Sivilforsvaret og brannvesenet.,LinkURI,@Value(DownloadUrl),Category{1}.Category,Kommune,Category{1}.Label,@Value(navn)
    -> Entry (writer GEORSS_1)
AttributeRangeMapper_2_Output: Inspector

Bookmark: Feed
Creator_2
    GEOMTYPE = Geometry Object
    NUM = 1
    CREATED -> AttributeCreator
AttributeCreator
    ATTR_LIST = Title,$(Title),Description,$(Description),LinkURI,$(FMEServerRoot)/$(Repository_Name),Id,$(FMEServerRoot)/$(Repository_Name),LastUpdate,$(LastUpdate),LinkRelation,self,LinkType,application/atom+xml,Copyright,DSB,Description,$(Description),GeneratorURI,$(FMEServerRoot),GeneratorVersion,$(FMEVersion)
    -> Feed (writer GEORSS_1)
Feed (writer GEORSS_1)

Bookmark: Hele landet
Creator_3
    GEOMTYPE = Geometry Object
    NUM = 1
    CREATED -> AttributeCreator_5

Bookmark: Set Up Entry Content with Download Link
Note: Lager nedlastingsURL for hele landet
AttributeCreator_5
    ATTR_LIST = DownloadUrl,$(ROTKATALOG_WEB)DSB_25833.zip,name,DSB,value,DSB SOSI Data hele Norge
    -> AttributeCreator_2
AttributeCreator_2
    ATTR_LIST = Title,@Value(value),Content,Trykk på linken for å laste ned landsdekkende data i koordinatsystemet EPSG:25833. <br />  <a href="@Value(DownloadUrl)">@Value(value)<\a>,Description,Data for Sivilforsvaret og Brannvesenet. Trykk på linken for nedlasting: @Value(value),ContentType,html,LastUpdate,$(LastUpdate),Id,@Value(DownloadUrl),Category{0}.Category,EPSG:25833,Category{0}.Domain,http://www.opengis.net/def/crs/,Category{0}.Label,EPSG/0/25833,Author,Karen Lie,Copyright,DSB - Sivilforsvaret og brannvesenet.,LinkURI,@Value(DownloadUrl)
    -> Entry (writer GEORSS_1)

Bookmark: Fylker
admingrense.fylker (reader POSTGRES_1)
    attributes: fylkeid int2,PRIKEY, navn varchar(80)
    -> AttributeRangeMapper
AttributeRangeMapper
    OUT_ATTR = koordsys
    LUT = 1,17,25832,18,19,25833,20,20,25835,,,25833
    IN_ATTR = fylkeid
    -> TestFilter
TestFilter
    DEFAULT_VALUE = <UNFILTERED>
    TEST_LIST = BOOL_OP,OR,COMPOSITE_TEST,<Unused>,TEST_CLAUSE,"TEST @Value(fylkeid) <= 17",25832,BOOL_OP,OR,COMPOSITE_TEST,<Unused>,TEST_CLAUSE,"TEST @Value(fylkeid) = 20",25835
    <UNFILTERED> -> AttributeCreator_14
    25835 -> AttributeCreator_14
    25832 -> AttributeCreator_14
    25835 -> AttributeCreator_3
    25832 -> AttributeCreator_3
AttributeCreator_14
    ATTR_LIST = koordsys,25833
    -> AttributeCreator_3
Note: Lager nedlastingsURL
AttributeCreator_3
    ATTR_LIST = DownloadUrl,$(ROTKATALOG_WEB)DSB_@PadLeft(@Value(fylkeid),2,0)_@Value(navn)_25833.zip,name,DSB,value,DSB SOSI Data @Value(navn)
    -> AttributeCreator_4
AttributeCreator_4
    ATTR_LIST = Title,@Value(value),Content,Trykk på linken for å laste ned data for fylke @Value(fylkeid), @Value(navn) i koordinatsystemet EPSG:@Value(koordsys). <br />  <a href="@Value(DownloadUrl)">@Value(value)<\a>,Description,Data for Sivilforsvaret og Brannvesenet. Trykk på linken for nedlasting: @Value(value),ContentType,html,LastUpdate,$(LastUpdate),Id,@Value(DownloadUrl),Category{0}.Category,EPSG:@Value(koordsys),Category{0}.Domain,http://www.opengis.net/def/crs/,Category{0}.Label,EPSG/0/@Value(koordsys),Author,Karen Lie,Copyright,DSB - Sivilforsvaret og brannvesenet.,LinkURI,@Value(DownloadUrl),Category{1}.Category,Fylke,Category{1}.Label,@Value(navn)
    -> Entry (writer GEORSS_1)
