FME workspace DSBsivilforsvarsdistrikterWFS10_test.fmw

Parameters:
- DestDataset_GML2 = $(FME_MF_DIR)return.gml   # Destination Geography Markup Language (GML) v2.1.2 File
- SourceDataset_POSTGIS = geonor01tst   # Database
- FEATURE_TYPES_2 = akvakultur.akvakulturpunkt akvakultur.akvakulturgrense akvakultur.akvakulturflate

Readers:
- POSTGIS_1: POSTGIS from $(SourceDataset_POSTGIS)

Writers:
- GML2_1: GML2 to $(DestDataset_GML2)

akvakultur.akvakulturpunkt (reader POSTGIS_1)
    attributes: objid int4,PRIKEY, objtype varchar(32), akva_enhet varchar(80), akva_kapasitet float4, av_class varchar(80), plassering varchar(80), vannmiljo varchar(80), kopidato date, areal_m2 int4, navn varchar(80), id int4, avgrensningfk int4,BTREE
    -> NewFeatureType (writer GML2_1)
NewFeatureType (writer GML2_1)
