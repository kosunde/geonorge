FME workspace DSBwfs2postgisKartverket.fmw
Title: DSB WFS til DSB PostGIS etter SOSI standard

Parameters:
- CONFIG_FILE:   # Python Script
      #-------------------------------------------------------------------------------
      # Name:        GetConfigFile
      # Purpose:
      #
      # Author:      xsunknu
      #
      # Created:     21.08.2015
      # Copyright:   (c) xsunknu 2015
      # Licence:     <your licence>
      #-------------------------------------------------------------------------------
      
      import os, fme
      fmwdir = fme.macroValues['FME_MF_DIR']
      fmwfile = fme.macroValues['FME_MF_NAME']
      fmwfile = os.path.join(fmwdir, fmwfile)
      configfile = os.path.splitext(fmwfile)[0] + '_config.xml'
      print configfile
      return configfile
- WFS_IN:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      #Read XML config file
      configtree = ET.parse(fme.macroValues['CONFIG_FILE'])
      configdoc = configtree.getroot()
      value = configdoc.find('wfsin').text
      return value

Readers:
- WFS_1: WFS from $(WFS_IN) in EPSG:32633

Writers:
- POSTGIS_1: POSTGIS to geonor01tst in EPSG:4258

Bookmark: 110-Sentraler
layer_562 (reader WFS_1)
    attributes: gml_parent_id xml_buffer, gml_id xml_buffer, msGeometry xml_geometry, POLY_ xml_buffer, POLY_ID xml_buffer, AREA xml_buffer, PERIMETER xml_buffer, OPPR xml_buffer, X xml_buffer, Y xml_buffer, KOORDH xml_buffer, SENTRAL xml_buffer, LOKALISERI xml_buffer, OPPHAV xml_buffer, MALEMETODE xml_buffer, NOYAKTIGHE xml_buffer, SYNBARHET xml_buffer, H_MALEMETO xml_buffer, H_NOYAKTIG xml_buffer, MAX_AVVIK xml_buffer, OBJTYPE xml_buffer, NAVN xml_buffer, DATO xml_buffer
    -> DateFormatter
Note: Formaterer datofelter
DateFormatter
    INVALID_DATE_VALUE = FME_NULL_VALUE
    DATE_ATTR = DATO
    SRCFMT = %Y%m%d
    FMT = ISO Date (%Y-%m-%d)
    -> TimeStamper
Note: Lager kopidato
TimeStamper
    TIME_ATTR = kopidato
    FMT = FME Date/Time (^Y^m^d^H^M^S)
    -> Reprojector
Note: Reprojiserer til EPSG4258
Reprojector
    INTERPOLATION_TYPE_NAME = Nearest Neighbor
    RASTER_CELL_SIZE = Preserve Cells
    SOURCE = Read from feature
    DEST = EPSG:4258
    REPROJECTED -> AttributeCreator_3
Note: Setter områdeID = 3
AttributeCreator_3
    ATTR_LIST = omradeid,3
    -> TopologyBuilder [input 3]
Note: Lager avgrensningslinjer for flatene
TopologyBuilder
    MAX = 0
    ALLOW_CYCLES = No
    ALL_EDGES = Yes
    OVERLAPPING_MODE = No
    CLEAN_DATA = No
    PROP_ATTRS = No
    LINE -> AttributeCreator_5
    AREA -> AttributeCreator_6
AttributeCreator_5
    ATTR_LIST = objtype,110distriktGrense,avgrensningfk,@Value(_left_polygon),avgrensningfk2,@Value(_right_polygon),malemetode,64,noyaktighet,50000
    -> dsb.sentraldistrikter110grense (writer POSTGIS_1)
dsb.sentraldistrikter110grense (writer POSTGIS_1)
    attributes: objtype varchar(32), objid int4, avgrensningfk int4, avgrensningfk2 int4, malemetode int4, noyaktighet int8
AttributeCreator_6
    ATTR_LIST = objid,@Value(_polygon_id),originaldatavert,DSB
    -> dsb.sentraldistrikter110 (writer POSTGIS_1)
dsb.sentraldistrikter110 (writer POSTGIS_1)
    attributes: lokalid uuid, navnerom text, versjonid varchar(2), msgeometry text, poly_ text, poly_id text, area text, perimeter text, oppr text, x float8, y float8, koordh text, sentral text, lokalisering text, opphav text, omradeid int8, originaldatavert text, kopidato timestamp, malemetode text, noyaktighet int8, synbarhet text, h_malemetode text, h_noyaktig text, max_avvik text, objtype text, navn text, datafangstdato date, objid int4

Bookmark: Sivilforsvarsdistrikter
layer_307 (reader WFS_1)
    attributes: gml_parent_id xml_buffer, gml_id xml_buffer, msGeometry xml_geometry, SIVDISTRIK xml_buffer, URL xml_buffer, NAVN xml_buffer
    -> AttributeCreator
AttributeCreator
    ATTR_LIST = originaldatavert,DSB,objtype,Sivilforsvardistrikt,omradeid,3
    -> TimeStamper_2
TimeStamper_2
    TIME_ATTR = kopidato
    FMT = FME Date/Time (^Y^m^d^H^M^S)
    -> Reprojector_2
Reprojector_2
    INTERPOLATION_TYPE_NAME = Nearest Neighbor
    RASTER_CELL_SIZE = Preserve Cells
    SOURCE = Read from feature
    DEST = EPSG:4258
    REPROJECTED -> dsb.sivilforsvarsdistrikter (writer POSTGIS_1)
    REPROJECTED -> TopologyBuilder_2 [input 3]
dsb.sivilforsvarsdistrikter (writer POSTGIS_1)
    attributes: lokalid uuid, navnerom text, versjonid varchar(2), msgeometry text, sivdistrik text, url text, navn text, kopidato timestamp, originaldatavert text, omradeid int4, objtype text
TopologyBuilder_2
    MAX = 0
    ALLOW_CYCLES = No
    ALL_EDGES = Yes
    OVERLAPPING_MODE = No
    CLEAN_DATA = No
    PROP_ATTRS = No
    LINE -> AttributeCreator_7
AttributeCreator_7
    ATTR_LIST = objtype,SivilforsvarDistriktsgrense
    -> dsb.sivilforsvarsdistriktergrense (writer POSTGIS_1)
dsb.sivilforsvarsdistriktergrense (writer POSTGIS_1)
    attributes: objtype text

Bookmark: Distriktskontor
layer_309 (reader WFS_1)
    attributes: gml_parent_id xml_buffer, gml_id xml_buffer, msGeometry xml_geometry, TYPE xml_buffer, KOMMUNE xml_buffer, URL xml_buffer, NAVN xml_buffer, DATO xml_buffer
    -> DateFormatter_5
DateFormatter_5
    INVALID_DATE_VALUE = FME_NULL_VALUE
    DATE_ATTR = DATO
    SRCFMT = %Y%m%d
    FMT = ISO Date (%Y-%m-%d)
    -> AttributeCreator_2
AttributeCreator_2
    ATTR_LIST = originaldatavert,DSB,objtype,Distriktskontor,omradeid,3
    -> TimeStamper_3
TimeStamper_3
    TIME_ATTR = kopidato
    FMT = FME Date/Time (^Y^m^d^H^M^S)
    -> Reprojector_3
Reprojector_3
    INTERPOLATION_TYPE_NAME = Nearest Neighbor
    RASTER_CELL_SIZE = Preserve Cells
    SOURCE = Read from feature
    DEST = EPSG:4258
    REPROJECTED -> dsb.sivilforsvaret_distriktskontor (writer POSTGIS_1)
dsb.sivilforsvaret_distriktskontor (writer POSTGIS_1)
    attributes: lokalid uuid, navnerom text, versjonid varchar(2), msgeometry text, type text, kommune text, url text, navn text, dato date, omradeid int8, originaldatavert text, kopidato timestamp, objtype text

Bookmark: Brannstasjoner
layer_511 (reader WFS_1)
    attributes: gml_parent_id xml_buffer, gml_id xml_buffer, msGeometry xml_geometry, BRANNSTASJ xml_buffer, KASERNERT xml_buffer, BRANNVESEN xml_buffer, ANLEGGID xml_buffer, AJOURDATO xml_buffer, INFORMASJ xml_buffer, OPPHAV xml_buffer, STASJONSTY xml_buffer, OBJTYPE xml_buffer, DATO xml_buffer, BRANNSTA_ xml_buffer
    -> DateFormatter_4
DateFormatter_4
    INVALID_DATE_VALUE = FME_NULL_VALUE
    DATE_ATTR = AJOURDATO,DATO
    SRCFMT = %Y%m%d
    FMT = FME Date (%Y%m%d)
    -> TimeStamper_6
TimeStamper_6
    TIME_ATTR = kopidato
    FMT = FME Date/Time (^Y^m^d^H^M^S)
    -> Reprojector_5
Reprojector_5
    INTERPOLATION_TYPE_NAME = Nearest Neighbor
    RASTER_CELL_SIZE = Preserve Cells
    SOURCE = Read from feature
    DEST = EPSG:4258
    REPROJECTED -> AttributeCreator_4
AttributeCreator_4
    ATTR_LIST = omradeid,3
    -> dsb.brannstasjoner (writer POSTGIS_1)
dsb.brannstasjoner (writer POSTGIS_1)
    attributes: lokalid uuid, navnerom text, versjonid varchar(2), msgeometry text, brannstasjon text, kasernert text, brannvesen text, anleggid text, ajourdato date, informasjon text, opphav text, stasjonstype text, objtype text, dato date, brannsta_ text, omradeid int8, originaldatavert text, kopidato timestamp
