FME workspace DSB_Postgis2sosi.fmw
# Copyright: (c) xgrimor 2015
# Licence: <your licence>
Title: DSB data fra PostGIS til SOSI

Parameters:
- KNR =   # Kommune(r)
- FNR =   # Fylke(r)
- CLIPPERCOORDS =   # Klippekoordinater
- CLIPPER_EPSG_CODE = 4258   # EPSGkode (kun tall)
- CLIPPER_FILE =   # "" Clipper file (any format)
- OUTPUT_EPSG_CODE =   # Output EPSG code
- FANOUT =   # Fanout områder
- CONFIG_FILE:   # Python Script
      #-------------------------------------------------------------------------------
      # Name:        GetConfigFile
      # Purpose:
      #
      # Author:      xsunknu
      #
      # Created:     21.08.2015
      # Copyright:   (c) xsunknu 2015
      # Licence:     <your licence>
      #-------------------------------------------------------------------------------
      
      import os, fme
      
      fmwdir = fme.macroValues['FME_MF_DIR']
      fmwfile = fme.macroValues['FME_MF_NAME']
      
      fmwfile = os.path.join(fmwdir, fmwfile)
      configfile = os.path.splitext(fmwfile)[0] + '_config.xml'
      
      return configfile
- PG_PWD:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgpwd').text
      
      return value
- PG_USER:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pguser').text
      
      return value
- PG_HOST:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pghost').text
      
      return value
- FIXEDCLIPPERCOORDS:   # Python Script
      #-------------------------------------------------------------------------------
      # Name:        FixClipperCoords
      # Purpose:
      #
      # Author:      xsunknu
      #
      # Created:     21.08.2015
      # Copyright:   (c) xsunknu 2015
      # Licence:     <your licence>
      #-------------------------------------------------------------------------------
      
      import fme
      clippercoords = fme.macroValues['CLIPPERCOORDS']
      
      if clippercoords == '':
          clippercoords = '1 1'
      
      return clippercoords
- DESTCOORDSYS:   # Python Script
      #-------------------------------------------------------------------------------
      # Name:        SetCoordinateSystem
      # Purpose:
      #
      # Author:      xsunknu
      #
      # Created:     21.08.2015
      # Copyright:   (c) xsunknu 2015
      # Licence:     <your licence>
      #-------------------------------------------------------------------------------
      
      import os, fme
      
      EPSGvalue = fme.macroValues['OUTPUT_EPSG_CODE']
      EPSGcode  = 'EPSG:' + EPSGvalue
      
      return EPSGcode
- CLIPPERCOORDSYS:   # Python Script
      #-------------------------------------------------------------------------------
      # Name:        SetCoordinateSystem
      # Purpose:
      #
      # Author:      xsunknu
      #
      # Created:     21.08.2015
      # Copyright:   (c) xsunknu 2015
      # Licence:     <your licence>
      #-------------------------------------------------------------------------------
      
      import os, fme
      
      EPSGvalue = fme.macroValues['CLIPPER_EPSG_CODE']
      EPSGcode  = 'EPSG:' + EPSGvalue
      
      return EPSGcode
- SOSI_FILE = DSB   # SOSI file
- SourceDataset_POSTGIS_1 = geonor01tst   # Database
- FANOUT_FOLDER:   # Python Script
      #-------------------------------------------------------------------------------
      # Name:        GetConfigFile
      # Purpose:
      #
      # Author:      xsunknu
      #
      # Created:     21.08.2015
      # Copyright:   (c) xsunknu 2015
      # Licence:     <your licence>
      #-------------------------------------------------------------------------------
      
      import os, fme
      from xml.etree import ElementTree as ET
      
      if 'FME_SERVER_DEST_DIR' in fme.macroValues:
          value = fme.macroValues['FME_SERVER_DEST_DIR']
      else:
          #Read XML config file
          configtree = ET.parse(fme.macroValues['CONFIG_FILE'])
          configdoc = configtree.getroot()
          value = configdoc.find('destdir').text
      
      return value

Readers:
- POSTGIS_1: POSTGIS from $(SourceDataset_POSTGIS_1) in EPSG:4258
- POSTGIS_2: POSTGIS from geonor01tst

Writers:
- SOSI_1: SOSI to $(FME_MF_DIR)dsb.sos in $(DESTCOORDSYS)

CreateClipper
    CLIPPERCOORDS = $(FIXEDCLIPPERCOORDS)
    DESTCOORDSYS = $(DESTCOORDSYS)
    CLIPPERCOORDSYS = $(CLIPPERCOORDSYS)
    reprojectBboxESRI_REPROJECTED_2 -> Clipper [input 1]
AttributeCreator_2
    ATTR_LIST = _KNR,$(KNR),_FNR,$(FNR),_CLIPPERCOORDS,$(CLIPPERCOORDS),_CLIPPER_FILE,$(CLIPPER_FILE)
    -> Tester_3
Note: Sjekker om det er sendt inn klippere
Tester_3
    TEST_CLAUSE:
      TEST _KNR ATTRIBUTE_IS_EMPTY ""
      TEST _FNR ATTRIBUTE_IS_EMPTY ""
      TEST _CLIPPER_FILE ATTRIBUTE_IS_EMPTY ""
      TEST _CLIPPERCOORDS ATTRIBUTE_IS_EMPTY ""
    TEST_DESCRIPTION = ""
    BOOL_OP = AND
    TEST_MODE = Automatic
    PASSED -> Reprojector
    FAILED -> Clipper [input 2]
Clipper
    CREATE_AGGREGATES = Yes
    CLIPPED_ATTR = _clipped
    ATTR_ACCUM_MODE = Merge Clipper
    CLIP_TYPE = Multiple Clippers
    BOUNDARY_CASES = Treat as Inside
    PRESERVE_CLIPPEE_EXTENTS = No
    ATTR_CONFLICT_RES = Use Clippee
    INSIDE -> Reprojector
Note: Reprojiserer til destcoordsys
Reprojector
    INTERPOLATION_TYPE_NAME = Nearest Neighbor
    RASTER_CELL_SIZE = Preserve Cells
    SOURCE = Read from feature
    DEST = $(DESTCOORDSYS)
    REPROJECTED -> AttributeCreator
AttributeCreator
    ATTR_LIST = sosifile,"FME_CONDITIONAL:DEFAULT_VALUE'$(SOSI_FILE)_$(OUTPUT_EPSG_CODE)'BOOL_OP;OR;COMPOSITE_TEST;<Unused>;TEST $(FANOUT) LIKE Kommuner'$(SOSI_FILE)_@PadLeft(@Value(kommuneid),4,0)_@Value(kommunenavn)_$(OUTPUT_EPSG_CODE)'BOOL_OP;OR;COMPOSITE_TEST;<Unused>;TEST $(FANOUT) LIKE Fylker'$(SOSI_FILE)_@PadLeft(@Value(fylkeid),2,0)_@Value(fylkesnavn)_$(OUTPUT_EPSG_CODE)'FME_NUM_CONDITIONS3___",dataeier,DSB,fylkesnr,@Value(fylkeid),komm,"FME_CONDITIONAL:DEFAULT_VALUE'@PadLeft(@Value(kommuneid),4,0)'BOOL_OP;OR;COMPOSITE_TEST;<Unused>;TEST kommuneid ATTRIBUTE_IS_MISSING _FME_BLANK_STRING_'FME_NULL_VALUE'FME_NUM_CONDITIONS2___"
    -> FeatureTypeFilter
FeatureTypeFilter
    ATTRIBUTES = <BLANK>,<UNFILTERED>,dsb.sivilforsvaret_distriktskontor,dsb.sentraldistrikter110,dsb.sivilforsvarsdistrikter,dsb.brannstasjoner,dsb.sentraldistrikter110grense,dsb.sivilforsvarsdistriktergrense
    dsb.sivilforsvarsdistrikter -> dsb.sivilforsvarsdistrikter (writer SOSI_1)
    dsb.sentraldistrikter110 -> dsb.sentraldistrikter110 (writer SOSI_1)
    dsb.sivilforsvaret_distriktskontor -> dsb.sivilforsvaret_distriktskontor (writer SOSI_1)
    dsb.sentraldistrikter110grense -> dsb.sentraldistrikter110grense (writer SOSI_1)
    dsb.brannstasjoner -> dsb.brannstasjoner (writer SOSI_1)
    dsb.sivilforsvarsdistriktergrense -> dsb.sivilforsvarsdistriktgrense (writer SOSI_1)
dsb.sivilforsvaret_distriktskontor (writer SOSI_1)
    attributes: _creation_instance SOSI_char, fylkeid SOSI_int32, fylkesnavn SOSI_char, kommuneid SOSI_int32, kommunenavn SOSI_char, lokalid SOSI_char, navnerom SOSI_char, versjonid SOSI_char, brannstasjon SOSI_char, kasernert SOSI_char, brannvesen SOSI_char, anleggid SOSI_char, ajourdato SOSI_char, informasjon SOSI_char, opphav SOSI_char, stasjonstype SOSI_char, objtype SOSI_char, dato SOSI_char, omradeid SOSI_char, kopidato SOSI_char, originaldatavert SOSI_char, msgeometry SOSI_char, poly_ SOSI_char, poly_id SOSI_char, area SOSI_char, perimeter SOSI_char, oppr SOSI_char, x SOSI_char, y SOSI_char, koordh SOSI_char,
      sentral SOSI_char, lokalisering SOSI_char, malemetode SOSI_char, noyaktighet SOSI_char, synbarhet SOSI_char, h_malemetode SOSI_char, h_noyaktig SOSI_char, max_avvik SOSI_char, navn SOSI_char, datafangstdato SOSI_char, type SOSI_char, kommune SOSI_char, url SOSI_char, sivdistrik SOSI_char, _KNR SOSI_char, _FNR SOSI_char, _CLIPPERCOORDS SOSI_char, _CLIPPER_FILE SOSI_char, _clipped SOSI_char, sosifile SOSI_char, dataeier SOSI_char, fylkesnr SOSI_char, komm SOSI_char
dsb.sentraldistrikter110 (writer SOSI_1)
    attributes: _creation_instance SOSI_char, fylkeid SOSI_int32, fylkesnavn SOSI_char, kommuneid SOSI_int32, kommunenavn SOSI_char, lokalid SOSI_char, navnerom SOSI_char, versjonid SOSI_char, brannstasjon SOSI_char, kasernert SOSI_char, brannvesen SOSI_char, anleggid SOSI_char, ajourdato SOSI_char, informasjon SOSI_char, opphav SOSI_char, stasjonstype SOSI_char, objtype SOSI_char, dato SOSI_char, omradeid SOSI_char, kopidato SOSI_char, originaldatavert SOSI_char, msgeometry SOSI_char, poly_ SOSI_char, poly_id SOSI_char, area SOSI_char, perimeter SOSI_char, oppr SOSI_char, x SOSI_char, y SOSI_char, koordh SOSI_char,
      sentral SOSI_char, lokalisering SOSI_char, malemetode SOSI_char, noyaktighet SOSI_char, synbarhet SOSI_char, h_malemetode SOSI_char, h_noyaktig SOSI_char, max_avvik SOSI_char, navn SOSI_char, datafangstdato SOSI_char, type SOSI_char, kommune SOSI_char, url SOSI_char, sivdistrik SOSI_char, _KNR SOSI_char, _FNR SOSI_char, _CLIPPERCOORDS SOSI_char, _CLIPPER_FILE SOSI_char, _clipped SOSI_char, sosifile SOSI_char, dataeier SOSI_char, fylkesnr SOSI_char, komm SOSI_char
dsb.sivilforsvarsdistrikter (writer SOSI_1)
    attributes: _creation_instance SOSI_char, fylkeid SOSI_int32, fylkesnavn SOSI_char, kommuneid SOSI_int32, kommunenavn SOSI_char, lokalid SOSI_char, navnerom SOSI_char, versjonid SOSI_char, brannstasjon SOSI_char, kasernert SOSI_char, brannvesen SOSI_char, anleggid SOSI_char, ajourdato SOSI_char, informasjon SOSI_char, opphav SOSI_char, stasjonstype SOSI_char, objtype SOSI_char, dato SOSI_char, omradeid SOSI_char, kopidato SOSI_char, originaldatavert SOSI_char, msgeometry SOSI_char, poly_ SOSI_char, poly_id SOSI_char, area SOSI_char, perimeter SOSI_char, oppr SOSI_char, x SOSI_char, y SOSI_char, koordh SOSI_char,
      sentral SOSI_char, lokalisering SOSI_char, malemetode SOSI_char, noyaktighet SOSI_char, synbarhet SOSI_char, h_malemetode SOSI_char, h_noyaktig SOSI_char, max_avvik SOSI_char, navn SOSI_char, datafangstdato SOSI_char, type SOSI_char, kommune SOSI_char, url SOSI_char, sivdistrik SOSI_char, _KNR SOSI_char, _FNR SOSI_char, _CLIPPERCOORDS SOSI_char, _CLIPPER_FILE SOSI_char, _clipped SOSI_char, sosifile SOSI_char, dataeier SOSI_char, fylkesnr SOSI_char, komm SOSI_char
dsb.brannstasjoner (writer SOSI_1)
    attributes: _creation_instance SOSI_char, fylkeid SOSI_int32, fylkesnavn SOSI_char, kommuneid SOSI_buffer, kommunenavn SOSI_char, lokalid SOSI_buffer, navnerom SOSI_buffer, versjonid SOSI_varchar(2), brannstasjon SOSI_buffer, kasernert SOSI_buffer, brannvesen SOSI_buffer, anleggid SOSI_buffer, ajourdato SOSI_date, informasjon SOSI_buffer, opphav SOSI_buffer, stasjonstype SOSI_buffer, objtype SOSI_buffer, dato SOSI_date, omradeid SOSI_int64, kopidato SOSI_datetime, originaldatavert SOSI_buffer, msgeometry SOSI_buffer, poly_ SOSI_buffer, poly_id SOSI_buffer, area SOSI_buffer, perimeter SOSI_buffer, oppr SOSI_buffer, x SOSI_real64, y SOSI_real64, koordh SOSI_buffer,
      sentral SOSI_buffer, lokalisering SOSI_buffer, malemetode SOSI_buffer, noyaktighet SOSI_int64, synbarhet SOSI_buffer, h_malemetode SOSI_buffer, h_noyaktig SOSI_buffer, max_avvik SOSI_buffer, navn SOSI_buffer, datafangstdato SOSI_date, type SOSI_buffer, kommune SOSI_buffer, url SOSI_buffer, sivdistrik SOSI_buffer, _KNR SOSI_char, _FNR SOSI_char, _CLIPPERCOORDS SOSI_char, _CLIPPER_FILE SOSI_char, _clipped SOSI_char, sosifile SOSI_char, dataeier SOSI_char, fylkesnr SOSI_char, komm SOSI_char
dsb.sentraldistrikter110grense (writer SOSI_1)
    attributes: OBJTYPE SOSI_char
dsb.sivilforsvarsdistriktgrense (writer SOSI_1)
    attributes: OBJTYPE SOSI_char

Bookmark: Fylke og/eller kommune clippers
admingrense.fylkeflate (reader POSTGIS_2)
    attributes: fylkeid int4, navn varchar(80)
    -> AttributeRenamer
AttributeRenamer
    ATTR_LIST = navn,fylkesnavn,
    -> Tester
Tester
    TEST_CLAUSE = TEST @Value(fylkeid) IN $(FNR)
    TEST_DESCRIPTION = ""
    BOOL_OP = OR
    TEST_MODE = Automatic
    PASSED -> Reprojector_2
admingrense.kommuneflate (reader POSTGIS_2)
    attributes: kommuneid int4, navn varchar(80)
    -> AttributeRenamer_2
AttributeRenamer_2
    ATTR_LIST = navn,kommunenavn,
    -> Tester_2
Tester_2
    TEST_CLAUSE = TEST @Value(kommuneid) IN $(KNR)
    TEST_DESCRIPTION = ""
    BOOL_OP = OR
    TEST_MODE = Automatic
    PASSED -> Reprojector_2
Reprojector_2
    INTERPOLATION_TYPE_NAME = Nearest Neighbor
    RASTER_CELL_SIZE = Preserve Cells
    SOURCE = Read from feature
    DEST = EPSG:4258
    REPROJECTED -> Clipper [input 1]

Bookmark: Clipper file (any format)
Creator
    NUM = 1
    GEOMTYPE = Geometry Object
    CREATED -> FeatureReader
FeatureReader
    ATTR_ACCUM_MODE = Only Use Result
    ATTRIBUTES = NewFeatureType,
    DATASET = $(CLIPPER_FILE)
    COMBINE_GEOM = Use Result
    FORMAT = GENERIC
    FEATURETYPES_RADIO = FEATURETYPES
    GENERIC_REAL_FORMAT = GUESS_FROM_EXTENSION
    OUTPUT_FEATURES_DISPLAY = Based on Connections
    INTERACT = <No Spatial Filter>
    <OTHER> -> Clipper [input 1]

Bookmark: PostGIS inn
dsb.sivilforsvaret_distriktskontor (reader POSTGIS_1)
    attributes: lokalid uuid, navnerom text, versjonid varchar(2), msgeometry text, type text, kommune text, url text, navn text, dato date, omradeid int8, kopidato timestamp, originaldatavert text, objtype text
    -> AttributeCreator_2
dsb.sivilforsvarsdistrikter (reader POSTGIS_1)
    attributes: lokalid uuid, navnerom text, versjonid varchar(2), msgeometry text, sivdistrik text, url text, navn text, kopidato timestamp, originaldatavert text, omradeid int4, objtype text
    -> AttributeCreator_2
dsb.brannstasjoner (reader POSTGIS_1)
    attributes: lokalid uuid, navnerom text, versjonid varchar(2), msgeometry text, brannstasjon text, kasernert text, brannvesen text, anleggid text, ajourdato date, informasjon text, opphav text, stasjonstype text, objtype text, dato date, brannsta_ text, omradeid int8, kopidato timestamp, originaldatavert text
    -> AttributeCreator_2
dsb.sentraldistrikter110 (reader POSTGIS_1)
    attributes: lokalid uuid, navnerom text, versjonid varchar(2), msgeometry text, poly_ text, poly_id text, area text, perimeter text, oppr text, x float8, y float8, koordh text, sentral text, lokalisering text, opphav text, omradeid int8, originaldatavert text, kopidato timestamp, malemetode text, noyaktighet int8, synbarhet text, h_malemetode text, h_noyaktig text, max_avvik text, objtype text, navn text, datafangstdato date
    -> AttributeCreator_2
dsb.sentraldistrikter110grense (reader POSTGIS_1)
    attributes: objtype varchar(32)
    -> AttributeCreator_2
dsb.sivilforsvarsdistriktergrense (reader POSTGIS_1)
    attributes: objtype text
    -> AttributeCreator_2

FME custom transformer CreateClipper

Parameters:
- CLIPPERCOORDS = 253577 6650999 253577 6651246 253763 6651246 253763 6650999 253577 6650999   # Clipper Coordinate List
- CLIPPERCOORDSYS = EPSG:25833   # Clipper Coordinate System
- DESTCOORDSYS = "ESRIWKT|ETRS_1989_UTM_Zone_35N|PROJCS["ETRS_1989_UTM_Zone_35N",GEOGCS["GCS_ETRS_1989",DATUM["D_ETRS_1989",SPHEROID["GRS_1980",6378137.0,298.257222101]],PRIMEM["Greenwich",0.0],UNIT["Degree",0.0174532925199433]],PROJECTION["Transverse_Mercator"],PARAMETER["False_Easting",500000.0],PARAMETER["False_Northing",0.0],PARAMETER["Central_Meridian",27.0],PARAMETER["Scale_Factor",0.9996],PARAMETER["Latitude_Of_Origin",0.0],UNIT["Meter",1.0]]"   # Destination Coordinate System

Note: Creating geometry from / the Clipper coords
Creator
    NUM = 1
    COORDS = $(CLIPPERCOORDS)
    GEOMTYPE = 2D Coordinate List
    COORDSYS = $(CLIPPERCOORDSYS)
    CREATED -> BoundingBoxAccumulator
Note: Calculating the bounding / box (envelope) from the geometry
BoundingBoxAccumulator
    TOPFER_INDEX = No
    BOUNDING_BOX -> SpatialFilter [input 1]
    ORIGINAL -> SpatialFilter [input 2]
Note: If the geometry is equal to its / own bounding box - it is a rectangle!
SpatialFilter
    MERGE_ATTRS = No
    USE_BOUNDING_BOX = No
    CURVE_BOUNDARY_RULE_PARAM = Default Rule
    PREDICATES = EQUALS
    BASE_TYPE = Single Base
    PREDATTR = _predicate
    PASS_CRITERIA = Pass Against One Base
    PASSED -> Reprojector
    FAILED -> Reprojector_2
Note: If rectangle, reproject the / geometry to the destination / coordinate system
Reprojector
    INTERPOLATION_TYPE_NAME = Nearest Neighbor
    RASTER_CELL_SIZE = Preserve Cells
    SOURCE = Read from feature
    DEST = $(DESTCOORDSYS)
    STROKE_ARCS = Yes
    REPROJECTED -> BoundingBoxAccumulator_2
Note: Then calculate the bounding / box from the projected geoemtry
BoundingBoxAccumulator_2
    TOPFER_INDEX = No
    BOUNDING_BOX -> Reprojector_3
Note: Reproject the geometry back to / the DB coordsys (LL/EUREF89)
Reprojector_3
    INTERPOLATION_TYPE_NAME = Nearest Neighbor
    RASTER_CELL_SIZE = Preserve Cells
    SOURCE = Read from feature
    DEST = EPSG:4258
    STROKE_ARCS = Yes
    REPROJECTED -> reprojectBboxESRI_REPROJECTED_2 (output)
Note: Reproject clipper to / the DB coordsys (LL/EUREF89)
Reprojector_2
    INTERPOLATION_TYPE_NAME = Nearest Neighbor
    RASTER_CELL_SIZE = Preserve Cells
    SOURCE = Read from feature
    DEST = EPSG:4258
    STROKE_ARCS = Yes
    REPROJECTED -> reprojectBboxESRI_REPROJECTED_2 (output)
reprojectBboxESRI_REPROJECTED_2 (output)
