FME workspace DSB_Postgis2sosisivilforsvarsdistrikter.fmw
# Copyright: (c) xgrimor 2015
# Licence: <your licence>
Title: DSB data fra PostGIS til SOSI
Shutdown Python:
      # -*- coding: utf-8 -*-
      #-------------------------------------------------------------------------------
      # Name:        zipfiles.py
      # Purpose:     Pakker filer i output folderen
      #
      # Author:      xsunknu
      #
      # Created:     18.09.2015
      # Copyright:   (c) xsunknu 2015
      # Licence:     <your licence>
      #-------------------------------------------------------------------------------

      import sys, os, zipfile, fme

      def zip(sosifile, zfile):
          from os.path import basename

          # Lager korresponderende zip-fil av SOSI-fil
          if os.path.isfile(zfile):
              os.remove(zfile)

          zf = zipfile.ZipFile(zfile, "w", zipfile.ZIP_DEFLATED)

          # Ønsker ikke full sti inn i ZIP-filen
          arcname = basename(sosifile)

          # ZIP-formatet støtter ikke non-ascii tegn
          # Erstatter AØÅæøå med ascii-tegn
          arcname = arcname.replace('\xc6', 'E')
          arcname = arcname.replace('\xd8', 'O')
          arcname = arcname.replace('\xc5', 'A')
          arcname = arcname.replace('\xe6', 'e')
          arcname = arcname.replace('\xf8', 'o')
          arcname = arcname.replace('\xe5', 'a')

          zf.write(sosifile, arcname)
          zf.close()
          os.remove(sosifile)

          return

      def main():

          # Kjøres ikke på FME Server, da FME Server selv sørger for pakkingen
          if not 'FME_SERVER_DEST_DIR' in fme.macroValues:
              if 'FANOUT_FOLDER' in fme.macroValues:
                  path = fme.macroValues['FANOUT_FOLDER']
                  for dirpath, dnames, fnames in os.walk(path):
                      for f in fnames:
                          if f.endswith(".sos"):
                              # Scanner gjennom alle SOSI-filer
                              sosifile = os.path.join(path, f)
                              zfile = os.path.splitext(sosifile)[0] + '.zip'
                              if os.path.isfile(zfile):

                                  # Korresponderende ZIP-fil finnes, sjekker timestamps
                                  sositstamp = os.stat(sosifile).st_mtime
                                  ziptstamp = os.stat(zfile).st_mtime

                                  if sositstamp > ziptstamp:
                                      # SOSI-fil er nyere enn ZIP-fila, ZIP-fila oppdateres
                                      # SOSI-fila slettes
                                      try:
                                          zip(sosifile, zfile)
                                      except:
                                          print 'Kunne ikke pakke: ' + sosifile
                                  else:
                                      # SOSI-fila er eldre enn ZIP-fila
                                      # SOSI-fila slettes
                                      try:
                                          os.remove(sosifile)
                                      except:
                                          print 'Kunne ikke slette: ' + sosifile
                              else:
                                  # ZIP-fila eksisterer ikke og lages
                                  # SOSI-fila slettes
                                  try:
                                      zip(sosifile, zfile)
                                  except:
                                      print 'Kunne ikke pakke: ' + sosifile


      if __name__ == '__main__':
          main()

Parameters:
- KNR =   # Kommune(r)
- FNR =   # Fylke(r)
- CLIPPERCOORDS =   # Klippekoordinater
- CLIPPER_EPSG_CODE = 4258   # EPSGkode (kun tall)
- CLIPPER_FILE =   # "" Clipper file (any format)
- OUTPUT_EPSG_CODE = 4258   # Output EPSG code
- FANOUT =   # Fanout områder
- CONFIG_FILE:   # Python Script
      #-------------------------------------------------------------------------------
      # Name:        GetConfigFile
      # Purpose:
      #
      # Author:      xsunknu
      #
      # Created:     21.08.2015
      # Copyright:   (c) xsunknu 2015
      # Licence:     <your licence>
      #-------------------------------------------------------------------------------
      
      import os, fme
      
      fmwdir = fme.macroValues['FME_MF_DIR']
      fmwfile = fme.macroValues['FME_MF_NAME']
      
      fmwfile = os.path.join(fmwdir, fmwfile)
      configfile = os.path.splitext(fmwfile)[0] + '_config.xml'
      
      return configfile
- PG_PWD:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgpwd').text
      
      return value
- PG_USER:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pguser').text
      
      return value
- PG_HOST:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pghost').text
      
      return value
- FIXEDCLIPPERCOORDS:   # Python Script
      #-------------------------------------------------------------------------------
      # Name:        FixClipperCoords
      # Purpose:
      #
      # Author:      xsunknu
      #
      # Created:     21.08.2015
      # Copyright:   (c) xsunknu 2015
      # Licence:     <your licence>
      #-------------------------------------------------------------------------------
      
      import fme
      clippercoords = fme.macroValues['CLIPPERCOORDS']
      
      if clippercoords == '':
          clippercoords = '1 1'
      
      return clippercoords
- DESTCOORDSYS:   # Python Script
      #-------------------------------------------------------------------------------
      # Name:        SetCoordinateSystem
      # Purpose:
      #
      # Author:      xsunknu
      #
      # Created:     21.08.2015
      # Copyright:   (c) xsunknu 2015
      # Licence:     <your licence>
      #-------------------------------------------------------------------------------
      
      import os, fme
      
      EPSGvalue = fme.macroValues['OUTPUT_EPSG_CODE']
      EPSGcode  = 'EPSG:' + EPSGvalue
      
      return EPSGcode
- CLIPPERCOORDSYS:   # Python Script
      #-------------------------------------------------------------------------------
      # Name:        SetCoordinateSystem
      # Purpose:
      #
      # Author:      xsunknu
      #
      # Created:     21.08.2015
      # Copyright:   (c) xsunknu 2015
      # Licence:     <your licence>
      #-------------------------------------------------------------------------------
      
      import os, fme
      
      EPSGvalue = fme.macroValues['CLIPPER_EPSG_CODE']
      EPSGcode  = 'EPSG:' + EPSGvalue
      
      return EPSGcode
- SOSI_FILE = Samfunnssikkerhet   # SOSI file
- FANOUT_FOLDER:   # Python Script
      #-------------------------------------------------------------------------------
      # Name:        GetConfigFile
      # Purpose:
      #
      # Author:      xsunknu
      #
      # Created:     21.08.2015
      # Copyright:   (c) xsunknu 2015
      # Licence:     <your licence>
      #-------------------------------------------------------------------------------
      
      import os, fme
      from xml.etree import ElementTree as ET
      
      if 'FME_SERVER_DEST_DIR' in fme.macroValues:
          value = fme.macroValues['FME_SERVER_DEST_DIR']
      else:
          #Read XML config file
          configtree = ET.parse(fme.macroValues['CONFIG_FILE'])
          configdoc = configtree.getroot()
          value = configdoc.find('destdir').text
      
      return value
- PG_DB:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgdb').text
      
      return value

Readers:
- POSTGIS_1: POSTGIS from $(PG_DB) in EPSG:4258
- POSTGIS_2: POSTGIS from $(PG_DB)

Writers:
- SOSI_1: SOSI to $(FME_MF_DIR)dsb.sos in $(DESTCOORDSYS)

CreateClipper
    CLIPPERCOORDS = $(FIXEDCLIPPERCOORDS)
    DESTCOORDSYS = $(DESTCOORDSYS)
    CLIPPERCOORDSYS = $(CLIPPERCOORDSYS)
    reprojectBboxESRI_REPROJECTED_2 -> Clipper [input 1]
AttributeCreator_2
    ATTR_LIST = _KNR,$(KNR),_FNR,$(FNR),_CLIPPERCOORDS,$(CLIPPERCOORDS),_CLIPPER_FILE,$(CLIPPER_FILE)
    -> Tester_3
Note: Sjekker om det er sendt inn klippere
Tester_3
    TEST_MODE = Automatic
    TEST_DESCRIPTION = ""
    TEST_CLAUSE:
      TEST _KNR ATTRIBUTE_IS_EMPTY ""
      TEST _FNR ATTRIBUTE_IS_EMPTY ""
      TEST _CLIPPER_FILE ATTRIBUTE_IS_EMPTY ""
      TEST _CLIPPERCOORDS ATTRIBUTE_IS_EMPTY ""
    BOOL_OP = AND
    PASSED -> Reprojector
    FAILED -> Clipper [input 2]
Clipper
    BOUNDARY_CASES = Treat as Inside
    CREATE_AGGREGATES = Yes
    CLIPPED_ATTR = _clipped
    PRESERVE_CLIPPEE_EXTENTS = No
    ATTR_ACCUM_MODE = Merge Clipper
    ATTR_CONFLICT_RES = Use Clippee
    CLIP_TYPE = Multiple Clippers
    INSIDE -> Reprojector
Note: Reprojiserer til destcoordsys
Reprojector
    SOURCE = Read from feature
    RASTER_CELL_SIZE = Preserve Cells
    INTERPOLATION_TYPE_NAME = Nearest Neighbor
    DEST = $(DESTCOORDSYS)
    REPROJECTED -> AttributeCreator
AttributeCreator
    ATTR_LIST = sosifile,"FME_CONDITIONAL:DEFAULT_VALUE'$(SOSI_FILE)_$(OUTPUT_EPSG_CODE)_Sivilforsvarsdistrikter_SOSI'BOOL_OP;OR;COMPOSITE_TEST;<Unused>;TEST $(FANOUT) LIKE Kommuner'$(SOSI_FILE)_@PadLeft(@Value(kommuneid),4,0)_@Value(kommunenavn)_$(OUTPUT_EPSG_CODE)_Sivilforsvarsdistrikter_SOSI'BOOL_OP;OR;COMPOSITE_TEST;<Unused>;TEST $(FANOUT) LIKE Fylker'$(SOSI_FILE)_@PadLeft(@Value(fylkeid),2,0)_@Value(fylkesnavn)_$(OUTPUT_EPSG_CODE)_Sivilforsvarsdistrikter_SOSI'FME_NUM_CONDITIONS3___",dataeier,DSB,fylkesnr,@Value(fylkeid),komm,"FME_CONDITIONAL:DEFAULT_VALUE'@PadLeft(@Value(kommuneid),4,0)'BOOL_OP;OR;COMPOSITE_TEST;<Unused>;TEST kommuneid ATTRIBUTE_IS_MISSING _FME_BLANK_STRING_'FME_NULL_VALUE'FME_NUM_CONDITIONS2___"
    -> StringReplacer
StringReplacer
    REGEXP = no
    SRC_ATTRS = sosifile
    CASE = no
    FIND_TEXT = " "
    NO_MATCH = _FME_NO_OP_
    REPLACE_TEXT = _
    -> FeatureTypeFilter
FeatureTypeFilter
    ATTRIBUTES = <BLANK>,<UNFILTERED>,dsb.sivilforsvaret_distriktskontor,dsb.sivilforsvarsdistrikter,dsb.sivilforsvarsdistriktergrense
    dsb.sivilforsvarsdistrikter -> dsb.sivilforsvarsdistrikter (writer SOSI_1)
    dsb.sivilforsvaret_distriktskontor -> dsb.sivilforsvaret_distriktskontor (writer SOSI_1)
    dsb.sivilforsvarsdistriktergrense -> dsb.sivilforsvarsdistriktgrense (writer SOSI_1)
dsb.sivilforsvaret_distriktskontor (writer SOSI_1)
    attributes: kommuneid SOSI_int32, kommunenavn SOSI_char, fylkeid SOSI_int32, fylkesnavn SOSI_char, _creation_instance SOSI_char, lokalid SOSI_char, navnerom SOSI_char, versjonid SOSI_char, msgeometry SOSI_char, sivdistrik SOSI_char, url SOSI_char, navn SOSI_char, kopidato SOSI_char, originaldatavert SOSI_char, omradeid SOSI_char, objtype SOSI_char, type SOSI_char, kommune SOSI_char, dato SOSI_char, _KNR SOSI_char, _FNR SOSI_char, _CLIPPERCOORDS SOSI_char, _CLIPPER_FILE SOSI_char, _clipped SOSI_char, sosifile SOSI_char, dataeier SOSI_char, fylkesnr SOSI_char, komm SOSI_char
dsb.sivilforsvarsdistrikter (writer SOSI_1)
    attributes: kommuneid SOSI_int32, kommunenavn SOSI_char, fylkeid SOSI_int32, fylkesnavn SOSI_char, _creation_instance SOSI_char, lokalid SOSI_char, navnerom SOSI_char, versjonid SOSI_char, msgeometry SOSI_char, sivdistrik SOSI_char, url SOSI_char, navn SOSI_char, kopidato SOSI_char, originaldatavert SOSI_char, omradeid SOSI_char, objtype SOSI_char, type SOSI_char, kommune SOSI_char, dato SOSI_char, _KNR SOSI_char, _FNR SOSI_char, _CLIPPERCOORDS SOSI_char, _CLIPPER_FILE SOSI_char, _clipped SOSI_char, sosifile SOSI_char, dataeier SOSI_char, fylkesnr SOSI_char, komm SOSI_char
dsb.sivilforsvarsdistriktgrense (writer SOSI_1)
    attributes: OBJTYPE SOSI_char

Bookmark: Fylke og/eller kommune clippers
admingrense.fylkeflate (reader POSTGIS_2)
    attributes: fylkeid int4, navn varchar(80)
    -> AttributeRenamer
AttributeRenamer
    ATTR_LIST = navn,fylkesnavn,
    -> Tester
Tester
    TEST_MODE = Automatic
    TEST_DESCRIPTION = ""
    TEST_CLAUSE = TEST @Value(fylkeid) IN $(FNR)
    BOOL_OP = OR
    PASSED -> Reprojector_2
admingrense.kommuneflate (reader POSTGIS_2)
    attributes: kommuneid int4, navn varchar(80)
    -> AttributeRenamer_2
AttributeRenamer_2
    ATTR_LIST = navn,kommunenavn,
    -> Tester_2
Tester_2
    TEST_MODE = Automatic
    TEST_DESCRIPTION = ""
    TEST_CLAUSE = TEST @Value(kommuneid) IN $(KNR)
    BOOL_OP = OR
    PASSED -> Reprojector_2
Reprojector_2
    SOURCE = Read from feature
    RASTER_CELL_SIZE = Preserve Cells
    INTERPOLATION_TYPE_NAME = Nearest Neighbor
    DEST = EPSG:4258
    REPROJECTED -> Clipper [input 1]

Bookmark: Clipper file (any format)
Creator
    NUM = 1
    GEOMTYPE = Geometry Object
    CREATED -> FeatureReader
FeatureReader
    FEATURETYPES_RADIO = FEATURETYPES
    GENERIC_REAL_FORMAT = GUESS_FROM_EXTENSION
    COMBINE_GEOM = Use Result
    ATTRIBUTES = NewFeatureType,
    FORMAT = GENERIC
    DATASET = $(CLIPPER_FILE)
    ATTR_ACCUM_MODE = Only Use Result
    INTERACT = <No Spatial Filter>
    OUTPUT_FEATURES_DISPLAY = Based on Connections
    <OTHER> -> Clipper [input 1]

Bookmark: PostGIS inn
dsb.sivilforsvaret_distriktskontor (reader POSTGIS_1)
    attributes: lokalid uuid, navnerom text, versjonid varchar(2), msgeometry text, type text, kommune text, url text, navn text, dato date, omradeid int8, kopidato timestamp, originaldatavert text, objtype text
    -> AttributeCreator_2
dsb.sivilforsvarsdistrikter (reader POSTGIS_1)
    attributes: lokalid uuid, navnerom text, versjonid varchar(2), msgeometry text, sivdistrik text, url text, navn text, kopidato timestamp, originaldatavert text, omradeid int4, objtype text
    -> AttributeCreator_2
dsb.sivilforsvarsdistriktergrense (reader POSTGIS_1)
    attributes: objtype text
    -> AttributeCreator_2

FME custom transformer CreateClipper

Parameters:
- CLIPPERCOORDS = 253577 6650999 253577 6651246 253763 6651246 253763 6650999 253577 6650999   # Clipper Coordinate List
- CLIPPERCOORDSYS = EPSG:25833   # Clipper Coordinate System
- DESTCOORDSYS = "ESRIWKT|ETRS_1989_UTM_Zone_35N|PROJCS["ETRS_1989_UTM_Zone_35N",GEOGCS["GCS_ETRS_1989",DATUM["D_ETRS_1989",SPHEROID["GRS_1980",6378137.0,298.257222101]],PRIMEM["Greenwich",0.0],UNIT["Degree",0.0174532925199433]],PROJECTION["Transverse_Mercator"],PARAMETER["False_Easting",500000.0],PARAMETER["False_Northing",0.0],PARAMETER["Central_Meridian",27.0],PARAMETER["Scale_Factor",0.9996],PARAMETER["Latitude_Of_Origin",0.0],UNIT["Meter",1.0]]"   # Destination Coordinate System

Note: Creating geometry from / the Clipper coords
Creator
    COORDS = $(CLIPPERCOORDS)
    COORDSYS = $(CLIPPERCOORDSYS)
    NUM = 1
    GEOMTYPE = 2D Coordinate List
    CREATED -> BoundingBoxAccumulator
Note: Calculating the bounding / box (envelope) from the geometry
BoundingBoxAccumulator
    TOPFER_INDEX = No
    BOUNDING_BOX -> SpatialFilter [input 1]
    ORIGINAL -> SpatialFilter [input 2]
Note: If the geometry is equal to its / own bounding box - it is a rectangle!
SpatialFilter
    MERGE_ATTRS = No
    USE_BOUNDING_BOX = No
    CURVE_BOUNDARY_RULE_PARAM = Default Rule
    PREDATTR = _predicate
    PREDICATES = EQUALS
    BASE_TYPE = Single Base
    PASS_CRITERIA = Pass Against One Base
    PASSED -> Reprojector
    FAILED -> Reprojector_2
Note: If rectangle, reproject the / geometry to the destination / coordinate system
Reprojector
    STROKE_ARCS = Yes
    SOURCE = Read from feature
    RASTER_CELL_SIZE = Preserve Cells
    INTERPOLATION_TYPE_NAME = Nearest Neighbor
    DEST = $(DESTCOORDSYS)
    REPROJECTED -> BoundingBoxAccumulator_2
Note: Then calculate the bounding / box from the projected geoemtry
BoundingBoxAccumulator_2
    TOPFER_INDEX = No
    BOUNDING_BOX -> Reprojector_3
Note: Reproject the geometry back to / the DB coordsys (LL/EUREF89)
Reprojector_3
    STROKE_ARCS = Yes
    SOURCE = Read from feature
    RASTER_CELL_SIZE = Preserve Cells
    INTERPOLATION_TYPE_NAME = Nearest Neighbor
    DEST = EPSG:4258
    REPROJECTED -> reprojectBboxESRI_REPROJECTED_2 (output)
Note: Reproject clipper to / the DB coordsys (LL/EUREF89)
Reprojector_2
    STROKE_ARCS = Yes
    SOURCE = Read from feature
    RASTER_CELL_SIZE = Preserve Cells
    INTERPOLATION_TYPE_NAME = Nearest Neighbor
    DEST = EPSG:4258
    REPROJECTED -> reprojectBboxESRI_REPROJECTED_2 (output)
reprojectBboxESRI_REPROJECTED_2 (output)
