FME workspace DSB_Postgis2gmlsivilforsvarsdistrikter.fmw
# Copyright: (c) xgrimor 2015
# Licence: <your licence>
Title: DSB data fra PostGIS til GML
Shutdown Python:
      # -*- coding: utf-8 -*-
      #-------------------------------------------------------------------------------
      # Name:        zipfiles.py
      # Purpose:     Pakker filer i output folderen
      #
      # Author:      xsunknu
      #
      # Created:     18.09.2015
      # Copyright:   (c) xsunknu 2015
      # Licence:     <your licence>
      #-------------------------------------------------------------------------------

      import sys, os, zipfile, fme

      def zip(gmlfile, zfile):
          from os.path import basename

          # Lager korresponderende zip-fil av SOSI-fil
          if os.path.isfile(zfile):
              os.remove(zfile)

          zf = zipfile.ZipFile(zfile, "w", zipfile.ZIP_DEFLATED)

          # Ønsker ikke full sti inn i ZIP-filen
          arcname = basename(gmlfile)

          # ZIP-formatet støtter ikke non-ascii tegn
          # Erstatter AØÅæøå med ascii-tegn
          arcname = arcname.replace('\xc6', 'E')
          arcname = arcname.replace('\xd8', 'O')
          arcname = arcname.replace('\xc5', 'A')
          arcname = arcname.replace('\xe6', 'e')
          arcname = arcname.replace('\xf8', 'o')
          arcname = arcname.replace('\xe5', 'a')

          zf.write(gmlfile, arcname)
          zf.close()
          os.remove(gmlfile)

          return

      def main():

          # Kjøres ikke på FME Server, da FME Server selv sørger for pakkingen
          if not 'FME_SERVER_DEST_DIR' in fme.macroValues:
              if 'FANOUT_FOLDER' in fme.macroValues:
                  path = fme.macroValues['FANOUT_FOLDER']
                  for dirpath, dnames, fnames in os.walk(path):
                      for f in fnames:
                          if f.endswith(".gml"):
                              # Scanner gjennom alle SOSI-filer
                              gmlfile = os.path.join(path, f)
                              zfile = os.path.splitext(gmlfile)[0] + '.zip'
                              if os.path.isfile(zfile):

                                  # Korresponderende ZIP-fil finnes, sjekker timestamps
                                  sositstamp = os.stat(gmlfile).st_mtime
                                  ziptstamp = os.stat(zfile).st_mtime

                                  if sositstamp > ziptstamp:
                                      # SOSI-fil er nyere enn ZIP-fila, ZIP-fila oppdateres
                                      # SOSI-fila slettes
                                      try:
                                          zip(gmlfile, zfile)
                                      except:
                                          print 'Kunne ikke pakke: ' + gmlfile
                                  else:
                                      # SOSI-fila er eldre enn ZIP-fila
                                      # SOSI-fila slettes
                                      try:
                                          os.remove(gmlfile)
                                      except:
                                          print 'Kunne ikke slette: ' + gmlfile
                              else:
                                  # ZIP-fila eksisterer ikke og lages
                                  # SOSI-fila slettes
                                  try:
                                      zip(gmlfile, zfile)
                                  except:
                                      print 'Kunne ikke pakke: ' + gmlfile


      if __name__ == '__main__':
          main()

Parameters:
- KNR =   # Kommune(r)
- FNR =   # Fylke(r)
- CLIPPERCOORDS =   # Klippekoordinater
- CLIPPER_EPSG_CODE = 4258   # EPSGkode (kun tall)
- CLIPPER_FILE =   # "" Clipper file (any format)
- OUTPUT_EPSG_CODE = 4258   # Output EPSG code
- FANOUT =   # Fanout områder
- DestDataset_GML = $(FME_MF_DIR)Sivilforsvarsdistrikter.gml   # Destination Geography Markup Language (GML) File
- CONFIG_FILE:   # Python Script
      #-------------------------------------------------------------------------------
      # Name:        GetConfigFile
      # Purpose:
      #
      # Author:      xsunknu
      #
      # Created:     21.08.2015
      # Copyright:   (c) xsunknu 2015
      # Licence:     <your licence>
      #-------------------------------------------------------------------------------
      
      import os, fme
      
      fmwdir = fme.macroValues['FME_MF_DIR']
      fmwfile = fme.macroValues['FME_MF_NAME']
      
      fmwfile = os.path.join(fmwdir, fmwfile)
      configfile = os.path.splitext(fmwfile)[0] + '_config.xml'
      
      return configfile
- PG_PWD:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgpwd').text
      
      return value
- PG_USER:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pguser').text
      
      return value
- PG_HOST:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pghost').text
      
      return value
- FIXEDCLIPPERCOORDS:   # Python Script
      #-------------------------------------------------------------------------------
      # Name:        FixClipperCoords
      # Purpose:
      #
      # Author:      xsunknu
      #
      # Created:     21.08.2015
      # Copyright:   (c) xsunknu 2015
      # Licence:     <your licence>
      #-------------------------------------------------------------------------------
      
      import fme
      clippercoords = fme.macroValues['CLIPPERCOORDS']
      
      if clippercoords == '':
          clippercoords = '1 1'
      
      return clippercoords
- DESTCOORDSYS:   # Python Script
      #-------------------------------------------------------------------------------
      # Name:        SetCoordinateSystem
      # Purpose:
      #
      # Author:      xsunknu
      #
      # Created:     21.08.2015
      # Copyright:   (c) xsunknu 2015
      # Licence:     <your licence>
      #-------------------------------------------------------------------------------
      
      import os, fme
      
      EPSGvalue = fme.macroValues['OUTPUT_EPSG_CODE']
      EPSGcode  = 'EPSG:' + EPSGvalue
      
      return EPSGcode
- CLIPPERCOORDSYS:   # Python Script
      #-------------------------------------------------------------------------------
      # Name:        SetCoordinateSystem
      # Purpose:
      #
      # Author:      xsunknu
      #
      # Created:     21.08.2015
      # Copyright:   (c) xsunknu 2015
      # Licence:     <your licence>
      #-------------------------------------------------------------------------------
      
      import os, fme
      
      EPSGvalue = fme.macroValues['CLIPPER_EPSG_CODE']
      EPSGcode  = 'EPSG:' + EPSGvalue
      
      return EPSGcode
- SOSI_FILE = Samfunnssikkerhet   # SOSI file
- FANOUT_FOLDER:   # Python Script
      #-------------------------------------------------------------------------------
      # Name:        GetConfigFile
      # Purpose:
      #
      # Author:      xsunknu
      #
      # Created:     21.08.2015
      # Copyright:   (c) xsunknu 2015
      # Licence:     <your licence>
      #-------------------------------------------------------------------------------
      
      import os, fme
      from xml.etree import ElementTree as ET
      
      if 'FME_SERVER_DEST_DIR' in fme.macroValues:
          value = fme.macroValues['FME_SERVER_DEST_DIR']
      else:
          #Read XML config file
          configtree = ET.parse(fme.macroValues['CONFIG_FILE'])
          configdoc = configtree.getroot()
          value = configdoc.find('destdir').text
      
      return value
- PG_DB:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgdb').text
      
      return value

Readers:
- POSTGIS_1: POSTGIS from $(PG_DB) in EPSG:4258
- POSTGIS_2: POSTGIS from $(PG_DB)

Writers:
- GML_1: GML to $(DestDataset_GML)

CreateClipper
    DESTCOORDSYS = $(DESTCOORDSYS)
    CLIPPERCOORDS = $(FIXEDCLIPPERCOORDS)
    CLIPPERCOORDSYS = $(CLIPPERCOORDSYS)
    reprojectBboxESRI_REPROJECTED_2 -> Clipper [input 1]
AttributeCreator_8
    ATTR_LIST = _KNR,$(KNR),_FNR,$(FNR),_CLIPPER_FILE,$(CLIPPER_FILE),_CLIPPERCOORDS,$(CLIPPERCOORDS)
    -> Tester_3
Note: Sjekker om det er sendt inn klippere
Tester_3
    TEST_CLAUSE:
      TEST _KNR ATTRIBUTE_IS_EMPTY ""
      TEST _FNR ATTRIBUTE_IS_EMPTY ""
      TEST _CLIPPER_FILE ATTRIBUTE_IS_EMPTY ""
      TEST _CLIPPERCOORDS ATTRIBUTE_IS_EMPTY ""
    BOOL_OP = AND
    TEST_MODE = Automatic
    TEST_DESCRIPTION = ""
    PASSED -> Reprojector
    FAILED -> Clipper [input 2]
Clipper
    ATTR_CONFLICT_RES = Use Clippee
    CLIPPED_ATTR = _clipped
    CLIP_TYPE = Multiple Clippers
    PRESERVE_CLIPPEE_EXTENTS = No
    CREATE_AGGREGATES = Yes
    ATTR_ACCUM_MODE = Merge Clipper
    BOUNDARY_CASES = Treat as Inside
    INSIDE -> Reprojector
FeatureTypeFilter
    ATTRIBUTES = <BLANK>,<UNFILTERED>,dsb.sivilforsvarsdistriktergrense,dsb.sivilforsvaret_distriktskontor,dsb.sivilforsvarsdistrikter
    dsb.sivilforsvarsdistriktergrense -> SpatialRelator [input 2]
    dsb.sivilforsvarsdistriktergrense -> SpatialRelator_2 [input 1]
    dsb.sivilforsvarsdistrikter -> SpatialRelator_2 [input 2]
    dsb.sivilforsvarsdistrikter -> TopologyBuilder [input 3]
    dsb.sivilforsvarsdistrikter -> SpatialRelator [input 1]
    dsb.sivilforsvarsdistrikter -> SpatialRelator_3 [input 2]
    dsb.sivilforsvaret_distriktskontor -> sivilforsvaret_distriktskontor (writer GML_1)
sivilforsvaret_distriktskontor (writer GML_1)
    attributes: Administrasjonssenter.Identifikasjon.lokalid xml_buffer, Administrasjonssenter.Identifikasjon.navnerom xml_buffer, Administrasjonssenter.Identifikasjon.versjonid xml_char(2), type xml_buffer, kommune xml_buffer, url xml_buffer, navn xml_buffer, dato xml_date, områdeid xml_int64, originaldatavert xml_buffer, kopidato xml_date, objtype xml_buffer

Bookmark: Fylke og/eller kommune clippers
admingrense.fylkeflate (reader POSTGIS_2)
    attributes: fylkeid int4, navn varchar(80)
    -> AttributeRenamer
AttributeRenamer
    ATTR_LIST = navn,fylkesnavn,
    -> Tester
Tester
    TEST_CLAUSE = TEST @Value(fylkeid) IN $(FNR)
    BOOL_OP = OR
    TEST_MODE = Automatic
    TEST_DESCRIPTION = ""
    PASSED -> Reprojector_2
admingrense.kommuneflate (reader POSTGIS_2)
    attributes: kommuneid int4, navn varchar(80)
    -> AttributeRenamer_2
AttributeRenamer_2
    ATTR_LIST = navn,kommunenavn,
    -> Tester_2
Tester_2
    TEST_CLAUSE = TEST @Value(kommuneid) IN $(KNR)
    BOOL_OP = OR
    TEST_MODE = Automatic
    TEST_DESCRIPTION = ""
    PASSED -> Reprojector_2
Reprojector_2
    SOURCE = Read from feature
    INTERPOLATION_TYPE_NAME = Nearest Neighbor
    RASTER_CELL_SIZE = Preserve Cells
    DEST = EPSG:4258
    REPROJECTED -> Clipper [input 1]

Bookmark: Clipper file (any format)
Creator
    NUM = 1
    GEOMTYPE = Geometry Object
    CREATED -> FeatureReader
FeatureReader
    OUTPUT_FEATURES_DISPLAY = Based on Connections
    ATTRIBUTES = NewFeatureType,
    FEATURETYPES_RADIO = FEATURETYPES
    ATTR_ACCUM_MODE = Only Use Result
    COMBINE_GEOM = Use Result
    FORMAT = GENERIC
    DATASET = $(CLIPPER_FILE)
    INTERACT = <No Spatial Filter>
    GENERIC_REAL_FORMAT = GUESS_FROM_EXTENSION
    <OTHER> -> Clipper [input 1]

Bookmark: PostGIS inn
dsb.sivilforsvarsdistrikter (reader POSTGIS_1)
    attributes: lokalid uuid, navnerom text, versjonid varchar(2), msgeometry text, sivdistrik text, url text, navn text, kopidato timestamp, originaldatavert text, omradeid int4, objtype text
    -> AttributeCreator_8
dsb.sivilforsvaret_distriktskontor (reader POSTGIS_1)
    attributes: lokalid uuid, navnerom text, versjonid varchar(2), msgeometry text, type text, kommune text, url text, navn text, dato date, omradeid int8, originaldatavert text, kopidato timestamp, objtype text
    -> AttributeCreator_8
dsb.sivilforsvarsdistriktergrense (reader POSTGIS_1)
    attributes: objtype text
    -> AttributeCreator_8

Bookmark: ID-generering og andre fellesoperasjoner
Note: Reprojiserer til destcoordsys
Reprojector
    SOURCE = Read from feature
    INTERPOLATION_TYPE_NAME = Nearest Neighbor
    RASTER_CELL_SIZE = Preserve Cells
    DEST = $(DESTCOORDSYS)
    REPROJECTED -> AttributeCreator
AttributeCreator
    ATTR_LIST = sosifile,"FME_CONDITIONAL:DEFAULT_VALUE'$(SOSI_FILE)_$(OUTPUT_EPSG_CODE)_Sivilforsvarsdistrikter_GML'BOOL_OP;OR;COMPOSITE_TEST;<Unused>;TEST $(FANOUT) LIKE Kommuner'$(SOSI_FILE)_@PadLeft(@Value(kommuneid),4,0)_@Value(kommunenavn)_$(OUTPUT_EPSG_CODE)_Sivilforsvarsdistrikter_GML'BOOL_OP;OR;COMPOSITE_TEST;<Unused>;TEST $(FANOUT) LIKE Fylker'$(SOSI_FILE)_@PadLeft(@Value(fylkeid),2,0)_@Value(fylkesnavn)_$(OUTPUT_EPSG_CODE)_Sivilforsvarsdistrikter_GML'BOOL_OP;OR;COMPOSITE_TEST;<Unused>;TEST $(FANOUT) = Norge'$(SOSI_FILE)_0000_Norge_$(OUTPUT_EPSG_CODE)_Sivilforsvarsdistrikter_GML'FME_NUM_CONDITIONS4___",dataeier,DSB,fylkesnr,@Value(fylkeid),komm,"FME_CONDITIONAL:DEFAULT_VALUE'@PadLeft(@Value(kommuneid),4,0)'BOOL_OP;OR;COMPOSITE_TEST;<Unused>;TEST kommuneid ATTRIBUTE_IS_MISSING _FME_BLANK_STRING_'FME_NULL_VALUE'FME_NUM_CONDITIONS2___"
    -> DateFormatter
DateFormatter
    DATE_ATTR = dato,kopidato
    SRCFMT = Unknown - Automatic Detection
    INVALID_DATE_VALUE = _FME_NO_OP_
    FMT = ISO DateTime (%Y-%m-%dT%H:%M:%S)
    -> Deaggregator
Deaggregator
    ID_SELECTION = ID and Parent ID
    LIST_ATTR_MODE_LOOKUP = LEAN
    COPY_ATTR = Every Node
    EXPLODE_INSTANCES = No
    PARENT_ID_ATTR = _hierarchy_parent_id
    SPLIT_COMPOSITES = No
    CHILD_ID_ATTR = _hierarchy_child_id_list
    PART_NUMBER_FIELD = _part_number
    ID_ATTR = _hierarchy_id
    MODE = Flatten One Level
    GEOM_NAME_FIELD = _geometry_name
    DEAGGREGATED -> UUIDGenerator
UUIDGenerator
    UUID_ATTR = gml_id
    -> AttributeCreator_2
AttributeCreator_2
    ATTR_LIST = _KNR,$(KNR),_FNR,$(FNR),_CLIPPERCOORDS,$(CLIPPERCOORDS),_CLIPPER_FILE,$(CLIPPER_FILE),gml_id,DSB_@Value(gml_id)
    -> AttributeRenamer_3
AttributeRenamer_3
    ATTR_LIST = lokalid,Administrasjonssenter.Identifikasjon.lokalid,,navnerom,Administrasjonssenter.Identifikasjon.navnerom,,versjonid,Administrasjonssenter.Identifikasjon.versjonid,,omradeid,områdeid,
    -> DateFormatter_2
DateFormatter_2
    DATE_ATTR = dato,kopidato
    SRCFMT = Unknown - Automatic Detection
    INVALID_DATE_VALUE = _FME_NO_OP_
    FMT = ISO Date (%Y-%m-%d)
    -> FeatureTypeFilter

Bookmark: Grenselinjer
SpatialRelator_2
    CURVE_BOUNDARY_RULE_PARAM = Default Rule
    SUCCESS_ATTR = _related_candidates
    LIST_NAME = _relationships
    PREDICATES = TOUCHES
    CALC_CARD = No
    -> AttributeCreator_3
AttributeCreator_3
    ATTR_LIST = kvalitet.målemetode,56,kvalitet.nøyaktighet,50000
    -> ListRenamer_2
ListRenamer_2
    LIST_COMPONENT_NAMES = _relationships{},avgrenser{},gml_id,xlink_href
    LIST_ACTION = Rename
    LIST_NAME = _relationships{}.gml_id
    LEAVE_ORIG = No
    -> SpatialFilter [input 1]
    -> ListExploder
    -> FeatureMerger [input 2]
ListExploder
    ATTR_CONFLICT_RES = Use Original
    INDEX_ATTR = _element_index
    ATTR_ACCUM_MODE = Merge Incoming List
    LIST_ATTR = avgrenser{}
    LIST_FOUND -> AttributeCreator_6
AttributeCreator_6
    ATTR_LIST = xlink_href,#@Value(xlink_href)
    -> ListBuilder
ListBuilder
    GRP_BY = gml_id
    LIST_NAME = avgrenser
    -> FeatureMerger [input 1]
FeatureMerger
    ATTR_ACCUM_MODE = Merge Supplier
    IGNORE_NULLS = No
    MERGE_TYPE = Attributes and Geometry
    ATTR_CONFLICT_RES = Use Requestor
    JOIN_KEYS = @Value(gml_id) @Value(gml_id) AUTO
    SUPPLIERS_FIRST = No
    PROCESS_DUPS = No
    MERGED -> sivilforsvarsdistriktergrense (writer GML_1)
sivilforsvarsdistriktergrense (writer GML_1)
    attributes: objtype xml_buffer, kvalitet.målemetode xml_buffer, kvalitet.nøyaktighet xml_int64, kopidato xml_date, avgrenser{}.xlink_href xml_buffer

Bookmark: Kantutsnitt
TopologyBuilder [off]
    CLEAN_DATA = No
    ALLOW_CYCLES = Yes
    PROP_ATTRS = Yes
    ALL_EDGES = Yes
    MAX = 0
    OVERLAPPING_MODE = Yes
    LINE -> UUIDGenerator_2 [off]
UUIDGenerator_2 [off]
    UUID_ATTR = gml_id
    -> AttributeCreator_5 [off]
AttributeCreator_5 [off]
    ATTR_LIST = _KNR,$(KNR),_FNR,$(FNR),_CLIPPERCOORDS,$(CLIPPERCOORDS),_CLIPPER_FILE,$(CLIPPER_FILE),gml_id,DSB_@Value(gml_id)
    -> SpatialFilter [input 2] [off]
SpatialFilter [off]
    PASS_CRITERIA = Pass Against One Filter
    CURVE_BOUNDARY_RULE_PARAM = Default Rule
    PREDICATE_VALUE = Equals
    BASE_TYPE = Multiple Filters
    PREDATTR = _predicate
    USE_BOUNDING_BOX = No
    MERGE_ATTRS = Yes
    FAILED -> SpatialRelator_3 [input 1] [off]
    FAILED -> SpatialRelator [input 2]
SpatialRelator_3 [off]
    CURVE_BOUNDARY_RULE_PARAM = Default Rule
    SUCCESS_ATTR = _related_candidates
    LIST_NAME = _relationships
    PREDICATES = TOUCHES
    CALC_CARD = No
    -> AttributeCreator_4 [off]
AttributeCreator_4 [off]
    ATTR_LIST = kvalitet.Posisjonskvalitet.målemetode,56,kvalitet.Posisjonskvalitet.nøyaktighet,50000,objtype,kantutsnitt
    -> ListRenamer_3 [off]
ListRenamer_3 [off]
    LIST_COMPONENT_NAMES = _relationships{},avgrenser{},gml_id,xlink_href
    LIST_ACTION = Rename
    LIST_NAME = _relationships{}.gml_id
    LEAVE_ORIG = No
    -> kantutsnitt (writer GML_1) [off]
kantutsnitt (writer GML_1) [off]
    attributes: objtype xml_buffer, kvalitet.Posisjonskvalitet.målemetode xml_buffer, kvalitet.Posisjonskvalitet.nøyaktighet xml_int64, kopidato xml_date, avgrenser{}.xlink_href xml_buffer

Bookmark: Flater
SpatialRelator
    CURVE_BOUNDARY_RULE_PARAM = Default Rule
    SUCCESS_ATTR = _related_candidates
    LIST_NAME = _relationships
    PREDICATES = TOUCHES
    CALC_CARD = No
    -> ListRenamer
ListRenamer
    LIST_COMPONENT_NAMES = _relationships{},avgrensesAv{},gml_id,xlink_href
    LIST_ACTION = Rename
    LIST_NAME = _relationships{}.gml_id
    LEAVE_ORIG = No
    -> ListExploder_2
    -> FeatureMerger_2 [input 2]
ListExploder_2
    ATTR_CONFLICT_RES = Use Original
    INDEX_ATTR = _element_index
    ATTR_ACCUM_MODE = Merge Incoming List
    LIST_ATTR = avgrensesAv{}
    LIST_FOUND -> AttributeCreator_7
    NOT_FOUND -> AttributeCreator_7
AttributeCreator_7
    ATTR_LIST = xlink_href,#@Value(xlink_href)
    -> ListBuilder_2
ListBuilder_2
    GRP_BY = gml_id
    LIST_NAME = avgrensesAv
    -> FeatureMerger_2 [input 1]
FeatureMerger_2
    ATTR_ACCUM_MODE = Merge Supplier
    IGNORE_NULLS = No
    MERGE_TYPE = Attributes and Geometry
    ATTR_CONFLICT_RES = Use Requestor
    JOIN_KEYS = @Value(gml_id) @Value(gml_id) AUTO
    SUPPLIERS_FIRST = No
    PROCESS_DUPS = No
    MERGED -> sivilforsvarsdistrikter (writer GML_1)
sivilforsvarsdistrikter (writer GML_1)
    attributes: Administrasjonssenter.Identifikasjon.lokalid xml_buffer, Administrasjonssenter.Identifikasjon.navnerom xml_buffer, Administrasjonssenter.Identifikasjon.versjonid xml_char(2), sivdistrik xml_buffer, url xml_buffer, navn xml_buffer, kopidato xml_date, originaldatavert xml_buffer, omådeid xml_int32, objtype xml_buffer, avgrensesAv{}.xlink_href xml_buffer

FME custom transformer CreateClipper

Parameters:
- CLIPPERCOORDS = 253577 6650999 253577 6651246 253763 6651246 253763 6650999 253577 6650999   # Clipper Coordinate List
- CLIPPERCOORDSYS = EPSG:25833   # Clipper Coordinate System
- DESTCOORDSYS = "ESRIWKT|ETRS_1989_UTM_Zone_35N|PROJCS["ETRS_1989_UTM_Zone_35N",GEOGCS["GCS_ETRS_1989",DATUM["D_ETRS_1989",SPHEROID["GRS_1980",6378137.0,298.257222101]],PRIMEM["Greenwich",0.0],UNIT["Degree",0.0174532925199433]],PROJECTION["Transverse_Mercator"],PARAMETER["False_Easting",500000.0],PARAMETER["False_Northing",0.0],PARAMETER["Central_Meridian",27.0],PARAMETER["Scale_Factor",0.9996],PARAMETER["Latitude_Of_Origin",0.0],UNIT["Meter",1.0]]"   # Destination Coordinate System

Note: Creating geometry from / the Clipper coords
Creator
    NUM = 1
    GEOMTYPE = 2D Coordinate List
    COORDSYS = $(CLIPPERCOORDSYS)
    COORDS = $(CLIPPERCOORDS)
    CREATED -> BoundingBoxAccumulator
Note: Calculating the bounding / box (envelope) from the geometry
BoundingBoxAccumulator
    TOPFER_INDEX = No
    BOUNDING_BOX -> SpatialFilter [input 1]
    ORIGINAL -> SpatialFilter [input 2]
Note: If the geometry is equal to its / own bounding box - it is a rectangle!
SpatialFilter
    PASS_CRITERIA = Pass Against One Base
    CURVE_BOUNDARY_RULE_PARAM = Default Rule
    BASE_TYPE = Single Base
    PREDATTR = _predicate
    USE_BOUNDING_BOX = No
    PREDICATES = EQUALS
    MERGE_ATTRS = No
    PASSED -> Reprojector
    FAILED -> Reprojector_2
Note: If rectangle, reproject the / geometry to the destination / coordinate system
Reprojector
    SOURCE = Read from feature
    INTERPOLATION_TYPE_NAME = Nearest Neighbor
    STROKE_ARCS = Yes
    RASTER_CELL_SIZE = Preserve Cells
    DEST = $(DESTCOORDSYS)
    REPROJECTED -> BoundingBoxAccumulator_2
Note: Then calculate the bounding / box from the projected geoemtry
BoundingBoxAccumulator_2
    TOPFER_INDEX = No
    BOUNDING_BOX -> Reprojector_3
Note: Reproject the geometry back to / the DB coordsys (LL/EUREF89)
Reprojector_3
    SOURCE = Read from feature
    INTERPOLATION_TYPE_NAME = Nearest Neighbor
    STROKE_ARCS = Yes
    RASTER_CELL_SIZE = Preserve Cells
    DEST = EPSG:4258
    REPROJECTED -> reprojectBboxESRI_REPROJECTED_2 (output)
Note: Reproject clipper to / the DB coordsys (LL/EUREF89)
Reprojector_2
    SOURCE = Read from feature
    INTERPOLATION_TYPE_NAME = Nearest Neighbor
    STROKE_ARCS = Yes
    RASTER_CELL_SIZE = Preserve Cells
    DEST = EPSG:4258
    REPROJECTED -> reprojectBboxESRI_REPROJECTED_2 (output)
reprojectBboxESRI_REPROJECTED_2 (output)
