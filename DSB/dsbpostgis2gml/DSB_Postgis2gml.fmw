FME workspace DSB_Postgis2gml.fmw
# Copyright: (c) xgrimor 2015
# Licence: <your licence>
Title: DSB data fra PostGIS til SOSI
Shutdown Python:
      # -*- coding: utf-8 -*-
      #-------------------------------------------------------------------------------
      # Name:        zipfiles.py
      # Purpose:     Pakker filer i output folderen
      #
      # Author:      xsunknu
      #
      # Created:     18.09.2015
      # Copyright:   (c) xsunknu 2015
      # Licence:     <your licence>
      #-------------------------------------------------------------------------------

      import sys, os, zipfile, fme

      def zip(gmlfile, zfile):
          from os.path import basename

          # Lager korresponderende zip-fil av SOSI-fil
          if os.path.isfile(zfile):
              os.remove(zfile)

          zf = zipfile.ZipFile(zfile, "w", zipfile.ZIP_DEFLATED)

          # Ønsker ikke full sti inn i ZIP-filen
          arcname = basename(gmlfile)
          # ZIP-formatet støtter ikke non-ascii tegn
          # Erstatter AØÅæøå med ascii-tegn
          arcname = arcname.replace('\xc6', 'E')
          arcname = arcname.replace('\xd8', 'O')
          arcname = arcname.replace('\xc5', 'A')
          arcname = arcname.replace('\xe6', 'e')
          arcname = arcname.replace('\xf8', 'o')
          arcname = arcname.replace('\xe5', 'a')

          zf.write(gmlfile, arcname)
          #Sjekker om det finnes xsd - fil til zipfila.
          xsdfile = os.path.splitext(gmlfile)[0] + '.xsd'
          print xsdfile
          print arcname
          if os.path.isfile(xsdfile):
              # Ønsker ikke full sti inn i ZIP-filen
              arcname2 = basename(xsdfile)
              # ZIP-formatet støtter ikke non-ascii tegn
              #  Erstatter AØÅæøå med ascii-tegn
              arcname2 = arcname2.replace('\xc6', 'E')
              arcname2 = arcname2.replace('\xd8', 'O')
              arcname2 = arcname2.replace('\xc5', 'A')
              arcname2 = arcname2.replace('\xe6', 'e')
              arcname2 = arcname2.replace('\xf8', 'o')
              arcname2 = arcname2.replace('\xe5', 'a')

              zf.write(xsdfile, arcname2)
          zf.close()
          os.remove(gmlfile)
          os.remove(xsdfile)

          return

      def main():

          # Kjøres ikke på FME Server, da FME Server selv sørger for pakkingen
          if not 'FME_SERVER_DEST_DIR' in fme.macroValues:
              if 'FANOUT_FOLDER' in fme.macroValues:
                  path = fme.macroValues['FANOUT_FOLDER']
                  for dirpath, dnames, fnames in os.walk(path):
                      for f in fnames:
                          if f.endswith(".gml"):
                              # Scanner gjennom alle GML-filer
                              gmlfile = os.path.join(path, f)
                              zfile = os.path.splitext(gmlfile)[0] + '.zip'
                              if os.path.isfile(zfile):

                                  # Korresponderende ZIP-fil finnes, sjekker timestamps
                                  sositstamp = os.stat(gmlfile).st_mtime
                                  ziptstamp = os.stat(zfile).st_mtime

                                  if sositstamp > ziptstamp:
                                      # SOSI-fil er nyere enn ZIP-fila, ZIP-fila oppdateres
                                      # SOSI-fila slettes
                                      try:
                                          zip(gmlfile, zfile)
                                      except:
                                          print 'Kunne ikke pakke: ' + gmlfile
                                  else:
                                      # SOSI-fila er eldre enn ZIP-fila
                                      # SOSI-fila slettes
                                      try:
                                          os.remove(gmlfile)
                                      except:
                                          print 'Kunne ikke slette: ' + gmlfile
                              else:
                                  # ZIP-fila eksisterer ikke og lages
                                  # SOSI-fila slettes
                                  try:
                                      zip(gmlfile, zfile)
                                  except:
                                      print 'Kunne ikke pakke: ' + gmlfile


      if __name__ == '__main__':
          main()

Parameters:
- KNR =   # Kommune(r)
- FNR =   # Fylke(r)
- CLIPPERCOORDS =   # Klippekoordinater
- CLIPPER_EPSG_CODE = 4258   # EPSGkode (kun tall)
- CLIPPER_FILE =   # "" Clipper file (any format)
- OUTPUT_EPSG_CODE =   # Output EPSG code
- FANOUT =   # Fanout områder
- DestDataset_GML = $(FME_MF_DIR)return.gml   # Destination Geography Markup Language (GML) File
- CONFIG_FILE:   # Python Script
      #-------------------------------------------------------------------------------
      # Name:        GetConfigFile
      # Purpose:
      #
      # Author:      xsunknu
      #
      # Created:     21.08.2015
      # Copyright:   (c) xsunknu 2015
      # Licence:     <your licence>
      #-------------------------------------------------------------------------------
      
      import os, fme
      
      fmwdir = fme.macroValues['FME_MF_DIR']
      fmwfile = fme.macroValues['FME_MF_NAME']
      
      fmwfile = os.path.join(fmwdir, fmwfile)
      configfile = os.path.splitext(fmwfile)[0] + '_config.xml'
      
      return configfile
- PG_PWD:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgpwd').text
      
      return value
- PG_USER:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pguser').text
      
      return value
- PG_HOST:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pghost').text
      
      return value
- FIXEDCLIPPERCOORDS:   # Python Script
      #-------------------------------------------------------------------------------
      # Name:        FixClipperCoords
      # Purpose:
      #
      # Author:      xsunknu
      #
      # Created:     21.08.2015
      # Copyright:   (c) xsunknu 2015
      # Licence:     <your licence>
      #-------------------------------------------------------------------------------
      
      import fme
      clippercoords = fme.macroValues['CLIPPERCOORDS']
      
      if clippercoords == '':
          clippercoords = '1 1'
      
      return clippercoords
- DESTCOORDSYS:   # Python Script
      #-------------------------------------------------------------------------------
      # Name:        SetCoordinateSystem
      # Purpose:
      #
      # Author:      xsunknu
      #
      # Created:     21.08.2015
      # Copyright:   (c) xsunknu 2015
      # Licence:     <your licence>
      #-------------------------------------------------------------------------------
      
      import os, fme
      
      EPSGvalue = fme.macroValues['OUTPUT_EPSG_CODE']
      EPSGcode  = 'EPSG:' + EPSGvalue
      
      return EPSGcode
- CLIPPERCOORDSYS:   # Python Script
      #-------------------------------------------------------------------------------
      # Name:        SetCoordinateSystem
      # Purpose:
      #
      # Author:      xsunknu
      #
      # Created:     21.08.2015
      # Copyright:   (c) xsunknu 2015
      # Licence:     <your licence>
      #-------------------------------------------------------------------------------
      
      import os, fme
      
      EPSGvalue = fme.macroValues['CLIPPER_EPSG_CODE']
      EPSGcode  = 'EPSG:' + EPSGvalue
      
      return EPSGcode
- GML_FILE = DSB   # GML file
- SourceDataset_POSTGIS_3 = geonor01tst   # Database
- FANOUT_FOLDER:   # Python Script
      #-------------------------------------------------------------------------------
      # Name:        GetConfigFile
      # Purpose:
      #
      # Author:      xsunknu
      #
      # Created:     21.08.2015
      # Copyright:   (c) xsunknu 2015
      # Licence:     <your licence>
      #-------------------------------------------------------------------------------
      
      import os, fme
      from xml.etree import ElementTree as ET
      
      if 'FME_SERVER_DEST_DIR' in fme.macroValues:
          value = fme.macroValues['FME_SERVER_DEST_DIR']
      else:
          #Read XML config file
          configtree = ET.parse(fme.macroValues['CONFIG_FILE'])
          configdoc = configtree.getroot()
          value = configdoc.find('destdir').text
      
      return value

Readers:
- POSTGIS_1: POSTGIS from $(SourceDataset_POSTGIS_3) in EPSG:4258
- POSTGIS_2: POSTGIS from geonor01tst

Writers:
- GML_1: GML to $(DestDataset_GML)

CreateClipper
    CLIPPERCOORDS = $(FIXEDCLIPPERCOORDS)
    CLIPPERCOORDSYS = $(CLIPPERCOORDSYS)
    DESTCOORDSYS = $(DESTCOORDSYS)
    reprojectBboxESRI_REPROJECTED_2 -> Clipper [input 1]
AttributeCreator_2
    ATTR_LIST = _KNR,$(KNR),_FNR,$(FNR),_CLIPPERCOORDS,$(CLIPPERCOORDS),_CLIPPER_FILE,$(CLIPPER_FILE)
    -> Tester_3
Note: Sjekker om det er sendt inn klippere
Tester_3
    BOOL_OP = AND
    TEST_CLAUSE:
      TEST _KNR ATTRIBUTE_IS_EMPTY ""
      TEST _FNR ATTRIBUTE_IS_EMPTY ""
      TEST _CLIPPER_FILE ATTRIBUTE_IS_EMPTY ""
      TEST _CLIPPERCOORDS ATTRIBUTE_IS_EMPTY ""
    TEST_MODE = Automatic
    TEST_DESCRIPTION = ""
    PASSED -> Reprojector
    FAILED -> Clipper [input 2]
Clipper
    ATTR_CONFLICT_RES = Use Clippee
    CREATE_AGGREGATES = Yes
    PRESERVE_CLIPPEE_EXTENTS = No
    BOUNDARY_CASES = Treat as Inside
    CLIP_TYPE = Multiple Clippers
    CLIPPED_ATTR = _clipped
    ATTR_ACCUM_MODE = Merge Clipper
    INSIDE -> Reprojector
Note: Reprojiserer til destcoordsys
Reprojector
    RASTER_CELL_SIZE = Preserve Cells
    SOURCE = Read from feature
    INTERPOLATION_TYPE_NAME = Nearest Neighbor
    DEST = $(DESTCOORDSYS)
    REPROJECTED -> AttributeCreator
AttributeCreator
    ATTR_LIST = komm,"FME_CONDITIONAL:DEFAULT_VALUE'@PadLeft(@Value(kommuneid),4,0)'BOOL_OP;OR;COMPOSITE_TEST;<Unused>;TEST kommuneid ATTRIBUTE_IS_MISSING _FME_BLANK_STRING_'FME_NULL_VALUE'FME_NUM_CONDITIONS2___",gmlfile,"FME_CONDITIONAL:DEFAULT_VALUE'$(GML_FILE)_$(OUTPUT_EPSG_CODE)'BOOL_OP;OR;COMPOSITE_TEST;<Unused>;TEST $(FANOUT) LIKE Kommuner'$(GML_FILE)_@PadLeft(@Value(kommuneid),4,0)_@Value(kommunenavn)_$(OUTPUT_EPSG_CODE)'BOOL_OP;OR;COMPOSITE_TEST;<Unused>;TEST $(FANOUT) LIKE Fylker'$(GML_FILE)_@PadLeft(@Value(fylkeid),2,0)_@Value(fylkesnavn)_$(OUTPUT_EPSG_CODE)'FME_NUM_CONDITIONS3___",fylkesnr,@Value(fylkeid),dataeier,DSB
    -> FeatureTypeFilter
FeatureTypeFilter
    ATTRIBUTES = <BLANK>,<UNFILTERED>,dsb.sivilforsvaret_distriktskontor,dsb.sentraldistrikter110,dsb.sivilforsvarsdistrikter,dsb.brannstasjoner,dsb.sentraldistrikter110grense,dsb.sivilforsvarsdistriktergrense
    dsb.sivilforsvarsdistrikter -> dsb.sivilforsvarsdistrikter (writer GML_1)
    dsb.sentraldistrikter110 -> dsb.sentraldistrikter110 (writer GML_1)
    dsb.sivilforsvaret_distriktskontor -> dsb.sivilforsvaret_distriktskontor (writer GML_1)
    dsb.sentraldistrikter110grense -> dsb.sentraldistrikter110grense (writer GML_1)
    dsb.sivilforsvarsdistriktergrense -> dsb.sivilforsvarsdistriktgrense (writer GML_1)
    dsb.brannstasjoner -> dsb.brannstasjoner (writer GML_1)
dsb.sivilforsvaret_distriktskontor (writer GML_1) [off]
    attributes: _creation_instance xml_char(20), kommuneid xml_int32, kommunenavn xml_char(20), fylkeid xml_int32, fylkesnavn xml_char(20), lokalid xml_char(200), navnerom xml_char(200), versjonid xml_char(200), brannstasjon xml_char(200), kasernert xml_char(200), brannvesen xml_char(200), anleggid xml_char(200), ajourdato xml_char(200), informasjon xml_char(200), opphav xml_char(200), stasjonstype xml_char(200), objtype xml_char(200), dato xml_char(200), omradeid xml_char(200), kopidato xml_char(200), originaldatavert xml_char(200), _KNR xml_char(200), _FNR xml_char(200), _CLIPPERCOORDS xml_char(200), _CLIPPER_FILE xml_char(200), _clipped xml_char(20), komm xml_char(20), gmlfile xml_char(200), fylkesnr xml_char(20), dataeier xml_char(20)
dsb.sentraldistrikter110 (writer GML_1) [off]
    attributes: _creation_instance xml_char(20), kommuneid xml_int32, kommunenavn xml_char(20), fylkeid xml_int32, fylkesnavn xml_char(20), lokalid xml_char(200), navnerom xml_char(200), versjonid xml_char(200), brannstasjon xml_char(200), kasernert xml_char(200), brannvesen xml_char(200), anleggid xml_char(200), ajourdato xml_char(200), informasjon xml_char(200), opphav xml_char(200), stasjonstype xml_char(200), objtype xml_char(200), dato xml_char(200), omradeid xml_char(200), kopidato xml_char(200), originaldatavert xml_char(200), _KNR xml_char(200), _FNR xml_char(200), _CLIPPERCOORDS xml_char(200), _CLIPPER_FILE xml_char(200), _clipped xml_char(20), komm xml_char(20), gmlfile xml_char(200), fylkesnr xml_char(20), dataeier xml_char(20)
dsb.sivilforsvarsdistrikter (writer GML_1) [off]
    attributes: _creation_instance xml_char(20), kommuneid xml_int32, kommunenavn xml_char(20), fylkeid xml_int32, fylkesnavn xml_char(20), lokalid xml_char(200), navnerom xml_char(200), versjonid xml_char(200), brannstasjon xml_char(200), kasernert xml_char(200), brannvesen xml_char(200), anleggid xml_char(200), ajourdato xml_char(200), informasjon xml_char(200), opphav xml_char(200), stasjonstype xml_char(200), objtype xml_char(200), dato xml_char(200), omradeid xml_char(200), kopidato xml_char(200), originaldatavert xml_char(200), _KNR xml_char(200), _FNR xml_char(200), _CLIPPERCOORDS xml_char(200), _CLIPPER_FILE xml_char(200), _clipped xml_char(20), komm xml_char(20), gmlfile xml_char(200), fylkesnr xml_char(20), dataeier xml_char(20)
dsb.brannstasjoner (writer GML_1)
    attributes: lokalid xml_buffer, navnerom xml_buffer, versjonid xml_char(2), brannstasjon xml_char(20), kasernert xml_buffer, brannvesen xml_buffer, anleggid xml_buffer, ajourdato xml_char(8), informasjon xml_buffer, opphav xml_buffer, stasjonstype xml_buffer, objtype xml_buffer, dato xml_char(8), omradeid xml_int64, kopidato xml_char(20), originaldatavert xml_buffer
dsb.sentraldistrikter110grense (writer GML_1) [off]
    attributes: OBJTYPE xml_char(20)
dsb.sivilforsvarsdistriktgrense (writer GML_1) [off]
    attributes: OBJTYPE xml_char(20)

Bookmark: Fylke og/eller kommune clippers
admingrense.fylkeflate (reader POSTGIS_2)
    attributes: fylkeid int4, navn varchar(80)
    -> AttributeRenamer
AttributeRenamer
    ATTR_LIST = navn,fylkesnavn,
    -> Tester
Tester
    BOOL_OP = OR
    TEST_CLAUSE = TEST @Value(fylkeid) IN $(FNR)
    TEST_MODE = Automatic
    TEST_DESCRIPTION = ""
    PASSED -> Reprojector_2
admingrense.kommuneflate (reader POSTGIS_2)
    attributes: kommuneid int4, navn varchar(80)
    -> AttributeRenamer_2
AttributeRenamer_2
    ATTR_LIST = navn,kommunenavn,
    -> Tester_2
Tester_2
    BOOL_OP = OR
    TEST_CLAUSE = TEST @Value(kommuneid) IN $(KNR)
    TEST_MODE = Automatic
    TEST_DESCRIPTION = ""
    PASSED -> Reprojector_2
Reprojector_2
    RASTER_CELL_SIZE = Preserve Cells
    SOURCE = Read from feature
    INTERPOLATION_TYPE_NAME = Nearest Neighbor
    DEST = EPSG:4258
    REPROJECTED -> Clipper [input 1]

Bookmark: Clipper file (any format)
Creator
    GEOMTYPE = Geometry Object
    NUM = 1
    CREATED -> FeatureReader
FeatureReader
    FORMAT = GENERIC
    ATTRIBUTES = NewFeatureType,
    FEATURETYPES_RADIO = FEATURETYPES
    ATTR_ACCUM_MODE = Only Use Result
    OUTPUT_FEATURES_DISPLAY = Based on Connections
    COMBINE_GEOM = Use Result
    INTERACT = <No Spatial Filter>
    DATASET = $(CLIPPER_FILE)
    GENERIC_REAL_FORMAT = GUESS_FROM_EXTENSION
    <OTHER> -> Clipper [input 1]

Bookmark: PostGIS inn
dsb.sivilforsvaret_distriktskontor (reader POSTGIS_1) [off]
    attributes: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
dsb.sivilforsvarsdistrikter (reader POSTGIS_1) [off]
    attributes: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
dsb.brannstasjoner (reader POSTGIS_1)
    attributes: lokalid uuid, navnerom text, versjonid varchar(2), msgeometry text, brannstasjon text, kasernert text, brannvesen text, anleggid text, ajourdato date, informasjon text, opphav text, stasjonstype text, objtype text, dato date, brannsta_ text, omradeid int8, kopidato timestamp, originaldatavert text
    -> AttributeCreator_2
dsb.sentraldistrikter110 (reader POSTGIS_1) [off]
    attributes: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
dsb.sentraldistrikter110grense (reader POSTGIS_1) [off]
    attributes: objtype varchar(32)
dsb.sivilforsvarsdistriktergrense (reader POSTGIS_1) [off]
    attributes: objtype text

FME custom transformer CreateClipper

Parameters:
- CLIPPERCOORDS = 253577 6650999 253577 6651246 253763 6651246 253763 6650999 253577 6650999   # Clipper Coordinate List
- CLIPPERCOORDSYS = EPSG:25833   # Clipper Coordinate System
- DESTCOORDSYS = "ESRIWKT|ETRS_1989_UTM_Zone_35N|PROJCS["ETRS_1989_UTM_Zone_35N",GEOGCS["GCS_ETRS_1989",DATUM["D_ETRS_1989",SPHEROID["GRS_1980",6378137.0,298.257222101]],PRIMEM["Greenwich",0.0],UNIT["Degree",0.0174532925199433]],PROJECTION["Transverse_Mercator"],PARAMETER["False_Easting",500000.0],PARAMETER["False_Northing",0.0],PARAMETER["Central_Meridian",27.0],PARAMETER["Scale_Factor",0.9996],PARAMETER["Latitude_Of_Origin",0.0],UNIT["Meter",1.0]]"   # Destination Coordinate System

Note: Creating geometry from / the Clipper coords
Creator
    GEOMTYPE = 2D Coordinate List
    COORDSYS = $(CLIPPERCOORDSYS)
    COORDS = $(CLIPPERCOORDS)
    NUM = 1
    CREATED -> BoundingBoxAccumulator
Note: Calculating the bounding / box (envelope) from the geometry
BoundingBoxAccumulator
    TOPFER_INDEX = No
    BOUNDING_BOX -> SpatialFilter [input 1]
    ORIGINAL -> SpatialFilter [input 2]
Note: If the geometry is equal to its / own bounding box - it is a rectangle!
SpatialFilter
    MERGE_ATTRS = No
    PASS_CRITERIA = Pass Against One Base
    BASE_TYPE = Single Base
    PREDICATES = EQUALS
    PREDATTR = _predicate
    CURVE_BOUNDARY_RULE_PARAM = Default Rule
    USE_BOUNDING_BOX = No
    PASSED -> Reprojector
    FAILED -> Reprojector_2
Note: If rectangle, reproject the / geometry to the destination / coordinate system
Reprojector
    RASTER_CELL_SIZE = Preserve Cells
    SOURCE = Read from feature
    STROKE_ARCS = Yes
    INTERPOLATION_TYPE_NAME = Nearest Neighbor
    DEST = $(DESTCOORDSYS)
    REPROJECTED -> BoundingBoxAccumulator_2
Note: Then calculate the bounding / box from the projected geoemtry
BoundingBoxAccumulator_2
    TOPFER_INDEX = No
    BOUNDING_BOX -> Reprojector_3
Note: Reproject the geometry back to / the DB coordsys (LL/EUREF89)
Reprojector_3
    RASTER_CELL_SIZE = Preserve Cells
    SOURCE = Read from feature
    STROKE_ARCS = Yes
    INTERPOLATION_TYPE_NAME = Nearest Neighbor
    DEST = EPSG:4258
    REPROJECTED -> reprojectBboxESRI_REPROJECTED_2 (output)
Note: Reproject clipper to / the DB coordsys (LL/EUREF89)
Reprojector_2
    RASTER_CELL_SIZE = Preserve Cells
    SOURCE = Read from feature
    STROKE_ARCS = Yes
    INTERPOLATION_TYPE_NAME = Nearest Neighbor
    DEST = EPSG:4258
    REPROJECTED -> reprojectBboxESRI_REPROJECTED_2 (output)
reprojectBboxESRI_REPROJECTED_2 (output)
