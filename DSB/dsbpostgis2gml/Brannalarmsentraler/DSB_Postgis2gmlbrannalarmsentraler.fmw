FME workspace DSB_Postgis2gmlbrannalarmsentraler.fmw
# Copyright: (c) xgrimor 2015
# Licence: <your licence>
Title: DSB data fra PostGIS til SOSI
Shutdown Python:
      # -*- coding: utf-8 -*-
      #-------------------------------------------------------------------------------
      # Name:        zipfiles.py
      # Purpose:     Pakker filer i output folderen
      #
      # Author:      xsunknu
      #
      # Created:     18.09.2015
      # Copyright:   (c) xsunknu 2015
      # Licence:     <your licence>
      #-------------------------------------------------------------------------------

      import sys, os, zipfile, fme

      def zip(gmlfile, zfile):
          from os.path import basename

          # Lager korresponderende zip-fil av SOSI-fil
          if os.path.isfile(zfile):
              os.remove(zfile)

          zf = zipfile.ZipFile(zfile, "w", zipfile.ZIP_DEFLATED)

          # Ønsker ikke full sti inn i ZIP-filen
          arcname = basename(gmlfile)

          # ZIP-formatet støtter ikke non-ascii tegn
          # Erstatter AØÅæøå med ascii-tegn
          arcname = arcname.replace('\xc6', 'E')
          arcname = arcname.replace('\xd8', 'O')
          arcname = arcname.replace('\xc5', 'A')
          arcname = arcname.replace('\xe6', 'e')
          arcname = arcname.replace('\xf8', 'o')
          arcname = arcname.replace('\xe5', 'a')

          zf.write(gmlfile, arcname)
          zf.close()
          os.remove(gmlfile)

          return

      def main():

          # Kjøres ikke på FME Server, da FME Server selv sørger for pakkingen
          if not 'FME_SERVER_DEST_DIR' in fme.macroValues:
              if 'FANOUT_FOLDER' in fme.macroValues:
                  path = fme.macroValues['FANOUT_FOLDER']
                  for dirpath, dnames, fnames in os.walk(path):
                      for f in fnames:
                          if f.endswith(".gml"):
                              # Scanner gjennom alle SOSI-filer
                              gmlfile = os.path.join(path, f)
                              zfile = os.path.splitext(gmlfile)[0] + '.zip'
                              if os.path.isfile(zfile):

                                  # Korresponderende ZIP-fil finnes, sjekker timestamps
                                  sositstamp = os.stat(gmlfile).st_mtime
                                  ziptstamp = os.stat(zfile).st_mtime

                                  if sositstamp > ziptstamp:
                                      # SOSI-fil er nyere enn ZIP-fila, ZIP-fila oppdateres
                                      # SOSI-fila slettes
                                      try:
                                          zip(gmlfile, zfile)
                                      except:
                                          print 'Kunne ikke pakke: ' + gmlfile
                                  else:
                                      # SOSI-fila er eldre enn ZIP-fila
                                      # SOSI-fila slettes
                                      try:
                                          os.remove(gmlfile)
                                      except:
                                          print 'Kunne ikke slette: ' + gmlfile
                              else:
                                  # ZIP-fila eksisterer ikke og lages
                                  # SOSI-fila slettes
                                  try:
                                      zip(gmlfile, zfile)
                                  except:
                                      print 'Kunne ikke pakke: ' + gmlfile


      if __name__ == '__main__':
          main()

Parameters:
- KNR =   # Kommune(r)
- FNR =   # Fylke(r)
- CLIPPERCOORDS =   # Klippekoordinater
- CLIPPER_EPSG_CODE = 4258   # EPSGkode (kun tall)
- CLIPPER_FILE =   # "" Clipper file (any format)
- OUTPUT_EPSG_CODE = 4258   # Output EPSG code
- FANOUT =   # Fanout områder
- DestDataset_GML = $(FME_MF_DIR)Brannalarmsentraler.gml   # Destination Geography Markup Language (GML) File
- CONFIG_FILE:   # Python Script
      #-------------------------------------------------------------------------------
      # Name:        GetConfigFile
      # Purpose:
      #
      # Author:      xsunknu
      #
      # Created:     21.08.2015
      # Copyright:   (c) xsunknu 2015
      # Licence:     <your licence>
      #-------------------------------------------------------------------------------
      
      import os, fme
      
      fmwdir = fme.macroValues['FME_MF_DIR']
      fmwfile = fme.macroValues['FME_MF_NAME']
      
      fmwfile = os.path.join(fmwdir, fmwfile)
      configfile = os.path.splitext(fmwfile)[0] + '_config.xml'
      
      return configfile
- PG_PWD:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgpwd').text
      
      return value
- PG_USER:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pguser').text
      
      return value
- PG_HOST:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pghost').text
      
      return value
- FIXEDCLIPPERCOORDS:   # Python Script
      #-------------------------------------------------------------------------------
      # Name:        FixClipperCoords
      # Purpose:
      #
      # Author:      xsunknu
      #
      # Created:     21.08.2015
      # Copyright:   (c) xsunknu 2015
      # Licence:     <your licence>
      #-------------------------------------------------------------------------------
      
      import fme
      clippercoords = fme.macroValues['CLIPPERCOORDS']
      
      if clippercoords == '':
          clippercoords = '1 1'
      
      return clippercoords
- DESTCOORDSYS:   # Python Script
      #-------------------------------------------------------------------------------
      # Name:        SetCoordinateSystem
      # Purpose:
      #
      # Author:      xsunknu
      #
      # Created:     21.08.2015
      # Copyright:   (c) xsunknu 2015
      # Licence:     <your licence>
      #-------------------------------------------------------------------------------
      
      import os, fme
      
      EPSGvalue = fme.macroValues['OUTPUT_EPSG_CODE']
      EPSGcode  = 'EPSG:' + EPSGvalue
      
      return EPSGcode
- CLIPPERCOORDSYS:   # Python Script
      #-------------------------------------------------------------------------------
      # Name:        SetCoordinateSystem
      # Purpose:
      #
      # Author:      xsunknu
      #
      # Created:     21.08.2015
      # Copyright:   (c) xsunknu 2015
      # Licence:     <your licence>
      #-------------------------------------------------------------------------------
      
      import os, fme
      
      EPSGvalue = fme.macroValues['CLIPPER_EPSG_CODE']
      EPSGcode  = 'EPSG:' + EPSGvalue
      
      return EPSGcode
- SOSI_FILE = Samfunnssikkerhet   # SOSI file
- FANOUT_FOLDER:   # Python Script
      #-------------------------------------------------------------------------------
      # Name:        GetConfigFile
      # Purpose:
      #
      # Author:      xsunknu
      #
      # Created:     21.08.2015
      # Copyright:   (c) xsunknu 2015
      # Licence:     <your licence>
      #-------------------------------------------------------------------------------
      
      import os, fme
      from xml.etree import ElementTree as ET
      
      if 'FME_SERVER_DEST_DIR' in fme.macroValues:
          value = fme.macroValues['FME_SERVER_DEST_DIR']
      else:
          #Read XML config file
          configtree = ET.parse(fme.macroValues['CONFIG_FILE'])
          configdoc = configtree.getroot()
          value = configdoc.find('destdir').text
      
      return value
- PG_DB:   # Python Script
      #-------------------------------------------------------------------------------
      # Name:        ReadValueFromConfigFile
      # Purpose:
      #
      # Author:      xsunknu
      #
      # Created:     21.08.2015
      # Copyright:   (c) xsunknu 2015
      # Licence:     <your licence>
      #-------------------------------------------------------------------------------
      
      import fme
      from xml.etree import ElementTree as ET
      
      #Read XML config file
      configtree = ET.parse(fme.macroValues['CONFIG_FILE'])
      configdoc = configtree.getroot()
      value = configdoc.find('pgdb').text
      
      return value

Readers:
- POSTGIS_1: POSTGIS from $(PG_DB)
- POSTGIS_2: POSTGIS in EPSG:4258

Writers:
- GML_1: GML to $(DestDataset_GML)

CreateClipper
    DESTCOORDSYS = $(DESTCOORDSYS)
    CLIPPERCOORDSYS = $(CLIPPERCOORDSYS)
    CLIPPERCOORDS = $(FIXEDCLIPPERCOORDS)
    reprojectBboxESRI_REPROJECTED_2 -> Clipper [input 1]
Deaggregator_2
    ID_ATTR = _hierarchy_id
    SPLIT_COMPOSITES = No
    MODE = Flatten One Level
    GEOM_NAME_FIELD = _geometry_name
    PARENT_ID_ATTR = _hierarchy_parent_id
    EXPLODE_INSTANCES = No
    LIST_ATTR_MODE_LOOKUP = LEAN
    ID_SELECTION = ID and Parent ID
    CHILD_ID_ATTR = _hierarchy_child_id_list
    COPY_ATTR = Every Node
    PART_NUMBER_FIELD = _part_number
    DEAGGREGATED -> AttributeCreator_2
AttributeCreator_2
    ATTR_LIST = _KNR,$(KNR),_FNR,$(FNR),_CLIPPERCOORDS,$(CLIPPERCOORDS),_CLIPPER_FILE,$(CLIPPER_FILE)
    -> Tester_3
Note: Sjekker om det er sendt inn klippere
Tester_3
    TEST_DESCRIPTION = ""
    BOOL_OP = AND
    TEST_CLAUSE:
      TEST _KNR ATTRIBUTE_IS_EMPTY ""
      TEST _FNR ATTRIBUTE_IS_EMPTY ""
      TEST _CLIPPER_FILE ATTRIBUTE_IS_EMPTY ""
      TEST _CLIPPERCOORDS ATTRIBUTE_IS_EMPTY ""
    TEST_MODE = Automatic
    PASSED -> Reprojector
    FAILED -> Reprojector_3
Reprojector_3
    INTERPOLATION_TYPE_NAME = Nearest Neighbor
    SOURCE = Read from feature
    DEST = EPSG:4258
    RASTER_CELL_SIZE = Preserve Cells
    REPROJECTED -> Clipper [input 2]
Clipper
    CLIPPED_ATTR = _clipped
    ATTR_ACCUM_MODE = Merge Clipper
    ATTR_CONFLICT_RES = Use Clippee
    CREATE_AGGREGATES = Yes
    BOUNDARY_CASES = Treat as Inside
    PRESERVE_CLIPPEE_EXTENTS = No
    CLIP_TYPE = Multiple Clippers
    INSIDE -> Reprojector
Note: Reprojiserer til destcoordsys
Reprojector
    INTERPOLATION_TYPE_NAME = Nearest Neighbor
    SOURCE = Read from feature
    DEST = $(DESTCOORDSYS)
    RASTER_CELL_SIZE = Preserve Cells
    REPROJECTED -> Deaggregator
Deaggregator
    ID_ATTR = _hierarchy_id
    SPLIT_COMPOSITES = No
    MODE = Flatten One Level
    GEOM_NAME_FIELD = _geometry_name
    PARENT_ID_ATTR = _hierarchy_parent_id
    EXPLODE_INSTANCES = No
    LIST_ATTR_MODE_LOOKUP = LEAN
    ID_SELECTION = ID and Parent ID
    CHILD_ID_ATTR = _hierarchy_child_id_list
    COPY_ATTR = Every Node
    PART_NUMBER_FIELD = _part_number
    DEAGGREGATED -> AttributeCreator
AttributeCreator
    ATTR_LIST = sosifile,"FME_CONDITIONAL:DEFAULT_VALUE'$(SOSI_FILE)_$(OUTPUT_EPSG_CODE)_Brannalarmsentraler_GML'BOOL_OP;OR;COMPOSITE_TEST;<Unused>;TEST $(FANOUT) LIKE Kommuner'$(SOSI_FILE)_@PadLeft(@Value(kommuneid),4,0)_@Value(kommunenavn)_$(OUTPUT_EPSG_CODE)_Brannalarmsentraler_GML'BOOL_OP;OR;COMPOSITE_TEST;<Unused>;TEST $(FANOUT) LIKE Fylker'$(SOSI_FILE)_@PadLeft(@Value(fylkeid),2,0)_@Value(fylkesnavn)_$(OUTPUT_EPSG_CODE)_Brannalarmsentraler_GML'BOOL_OP;OR;COMPOSITE_TEST;<Unused>;TEST $(FANOUT) LIKE Norge'$(SOSI_FILE)_0000_Norge_$(OUTPUT_EPSG_CODE)_Brannalarmsentraler_GML'FME_NUM_CONDITIONS4___",dataeier,DSB,fylkesnr,@Value(fylkeid),komm,"FME_CONDITIONAL:DEFAULT_VALUE'@PadLeft(@Value(kommuneid),4,0)'BOOL_OP;OR;COMPOSITE_TEST;<Unused>;TEST kommuneid ATTRIBUTE_IS_MISSING _FME_BLANK_STRING_'FME_NULL_VALUE'FME_NUM_CONDITIONS2___"
    -> StringReplacer
StringReplacer
    SRC_ATTRS = sosifile
    CASE = no
    REGEXP = no
    NO_MATCH = _FME_NO_OP_
    REPLACE_TEXT = _
    FIND_TEXT = " "
    -> FeatureTypeFilter
FeatureTypeFilter
    ATTRIBUTES = <BLANK>,<UNFILTERED>,dsb.sentraldistrikter110
    <UNFILTERED> -> SpatialRelator_2 [input 1]
    dsb.sentraldistrikter110 -> SpatialRelator_2 [input 2]
    dsb.sentraldistrikter110 -> SpatialRelator [input 1]
    dsb.sentraldistrikter110 -> TopologyBuilder [input 3]
    dsb.sentraldistrikter110 -> SpatialRelator_3 [input 2]

Bookmark: Fylke og/eller kommune clippers
admingrense.fylkeflate (reader POSTGIS_1)
    attributes: fylkeid int4, navn varchar(80)
    -> AttributeRenamer
AttributeRenamer
    ATTR_LIST = navn,fylkesnavn,
    -> Tester
Tester
    TEST_DESCRIPTION = ""
    BOOL_OP = OR
    TEST_CLAUSE = TEST @Value(fylkeid) IN $(FNR)
    TEST_MODE = Automatic
    PASSED -> Reprojector_2
admingrense.kommuneflate (reader POSTGIS_1)
    attributes: kommuneid int4, navn varchar(80)
    -> AttributeRenamer_2
AttributeRenamer_2
    ATTR_LIST = navn,kommunenavn,
    -> Tester_2
Tester_2
    TEST_DESCRIPTION = ""
    BOOL_OP = OR
    TEST_CLAUSE = TEST @Value(kommuneid) IN $(KNR)
    TEST_MODE = Automatic
    PASSED -> Reprojector_2
Reprojector_2
    INTERPOLATION_TYPE_NAME = Nearest Neighbor
    SOURCE = Read from feature
    DEST = EPSG:4258
    RASTER_CELL_SIZE = Preserve Cells
    REPROJECTED -> Clipper [input 1]

Bookmark: Clipper file (any format)
Creator
    GEOMTYPE = Geometry Object
    NUM = 1
    CREATED -> FeatureReader
FeatureReader
    DATASET = $(CLIPPER_FILE)
    FORMAT = GENERIC
    INTERACT = <No Spatial Filter>
    FEATURETYPES_RADIO = FEATURETYPES
    COMBINE_GEOM = Use Result
    GENERIC_REAL_FORMAT = GUESS_FROM_EXTENSION
    OUTPUT_FEATURES_DISPLAY = Based on Connections
    ATTRIBUTES = NewFeatureType,
    ATTR_ACCUM_MODE = Only Use Result
    <OTHER> -> Clipper [input 1]

Bookmark: PostGIS inn
dsb.sentraldistrikter110 (reader POSTGIS_2)
    attributes: lokalid uuid, navnerom text, versjonid varchar(2), msgeometry text, poly_ text, poly_id text, area text, perimeter text, oppr text, x float8, y float8, koordh text, sentral text, lokalisering text, opphav text, omradeid int8, originaldatavert text, kopidato timestamp, malemetode text, noyaktighet int8, synbarhet text, h_malemetode text, h_noyaktig text, max_avvik text, objtype text, navn text, datafangstdato date
    -> UUIDGenerator
dsb.sentraldistrikter110grense (reader POSTGIS_2)
    attributes: objtype varchar(32)
    -> UUIDGenerator

Bookmark: Unike IDer
UUIDGenerator
    UUID_ATTR = gml_id
    -> AttributeCreator_3
AttributeCreator_3
    ATTR_LIST = _KNR,$(KNR),_FNR,$(FNR),_CLIPPERCOORDS,$(CLIPPERCOORDS),_CLIPPER_FILE,$(CLIPPER_FILE),gml_id,DSB_@Value(gml_id)
    -> Deaggregator_2

Bookmark: Avgrensningslinjer
SpatialRelator_2
    LIST_NAME = _relationships
    SUCCESS_ATTR = _related_candidates
    CALC_CARD = No
    CURVE_BOUNDARY_RULE_PARAM = Default Rule
    PREDICATES = TOUCHES
    -> AttributeCreator_6
AttributeCreator_6
    ATTR_LIST = kvalitet.målemetode,56,kvalitet.nøyaktighet,50000
    -> ListRenamer_2
ListRenamer_2
    LIST_NAME = _relationships{}.gml_id
    LIST_COMPONENT_NAMES = _relationships{},avgrenser{},gml_id,xlink_href
    LIST_ACTION = Rename
    LEAVE_ORIG = No
    -> sentraldistrikter110grense (writer GML_1)
    -> SpatialRelator [input 2]
    -> SpatialFilter [input 1]
sentraldistrikter110grense (writer GML_1)
    attributes: objtype xml_char(32), kvalitet.målemetode xml_char(32), kvalitet.nøyaktighet xml_char(32), kopidato xml_char(32), avgrenser{}.xlink_href xml_char(32)

Bookmark: Kantutsnitt ved klipping
TopologyBuilder [off]
    ALLOW_CYCLES = Yes
    ALL_EDGES = Yes
    MAX = 0
    CLEAN_DATA = No
    PROP_ATTRS = Yes
    OVERLAPPING_MODE = Yes
    LINE -> UUIDGenerator_2 [off]
UUIDGenerator_2 [off]
    UUID_ATTR = gml_id
    -> AttributeCreator_5 [off]
AttributeCreator_5 [off]
    ATTR_LIST = _KNR,$(KNR),_FNR,$(FNR),_CLIPPERCOORDS,$(CLIPPERCOORDS),_CLIPPER_FILE,$(CLIPPER_FILE),gml_id,DSB_@Value(gml_id)
    -> SpatialFilter [input 2] [off]
SpatialFilter [off]
    PREDATTR = _predicate
    USE_BOUNDING_BOX = No
    PASS_CRITERIA = Pass Against One Filter
    CURVE_BOUNDARY_RULE_PARAM = Default Rule
    MERGE_ATTRS = Yes
    BASE_TYPE = Multiple Filters
    PREDICATE_VALUE = Equals
    FAILED -> SpatialRelator_3 [input 1] [off]
    FAILED -> SpatialRelator [input 2]
SpatialRelator_3 [off]
    LIST_NAME = _relationships
    SUCCESS_ATTR = _related_candidates
    CALC_CARD = No
    CURVE_BOUNDARY_RULE_PARAM = Default Rule
    PREDICATES = TOUCHES
    -> AttributeCreator_4 [off]
AttributeCreator_4 [off]
    ATTR_LIST = kvalitet.Posisjonskvalitet.målemetode,56,kvalitet.Posisjonskvalitet.nøyaktighet,50000,objtype,kantutsnitt
    -> ListRenamer_3 [off]
ListRenamer_3 [off]
    LIST_NAME = _relationships{}.gml_id
    LIST_COMPONENT_NAMES = _relationships{},avgrenser{},gml_id,xlink_href
    LIST_ACTION = Rename
    LEAVE_ORIG = No
    -> kantutsnitt (writer GML_1) [off]
kantutsnitt (writer GML_1) [off]
    attributes: objtype xml_buffer, kvalitet.Posisjonskvalitet.målemetode xml_buffer, kvalitet.Posisjonskvalitet.nøyaktighet xml_int64, kopidato xml_date, avgrenser{}.xlink_href xml_buffer

Bookmark: Sentraldistrikter
SpatialRelator
    LIST_NAME = _relationships
    SUCCESS_ATTR = _related_candidates
    CALC_CARD = No
    CURVE_BOUNDARY_RULE_PARAM = Default Rule
    PREDICATES = TOUCHES
    -> ListRenamer
ListRenamer
    LIST_NAME = _relationships{}.gml_id
    LIST_COMPONENT_NAMES = _relationships{},avgrensesAv{},gml_id,xlink_href
    LIST_ACTION = Rename
    LEAVE_ORIG = No
    -> DateFormatter
DateFormatter
    FMT = ISO DateTime (%Y-%m-%dT%H:%M:%S)
    DATE_ATTR = datafangstdato,kopidato
    INVALID_DATE_VALUE = _FME_NO_OP_
    SRCFMT = Unknown - Automatic Detection
    -> AttributeRenamer_3
AttributeRenamer_3
    ATTR_LIST = lokalid,Administrasjonssenter.Identifikasjon.Lokalid,,navnerom,Administrasjonssenter.Identifikasjon.Navnerom,,versjonid,Administrasjonssenter.Identifikasjon.VersjonID,,area,Area,,koordh,Koordh,,omradeid,Kopidata.Områdeid,,originaldatavert,Kopidata.Originaldatavert,,kopidato,Kopidata.Kopidato,,malemetode,Kvalitet.Målemetode,,noyaktighet,Kvalitet.Nøyaktighet,,synbarhet,Kvalitet.Synbarhet,,h_malemetode,Kvalitet.H-målemetode,,h_noyaktig,Kvalitet.H-nøyaktighet,,sentral,Sentral,,lokalisering,Lokalisering,,opphav,Opphav,,max_avvik,Kvalitet.Max-avvik,,objtype,Objtype,,navn,Navn,,datafangstdato,Datafangstdato,
    -> NullAttributeMapper
NullAttributeMapper
    SOURCE_ATTR_VAL = Empty "Missing (Selected Attributes Only)" Null
    ATTRCHOICE = Selected Attributes
    ATTRLIST = Area Datafangstdato Kopidata.Kopidato Kopidata.Områdeid Kopidata.Originaldatavert Kvalitet.H-målemetode Kvalitet.H-nøyaktighet Kvalitet.Max-avvik Kvalitet.Målemetode Kvalitet.Nøyaktighet Kvalitet.Synbarhet Lokalisering Navn Objtype Opphav Sentral Administrasjonssenter.Identifikasjon.Lokalid Administrasjonssenter.Identifikasjon.Navnerom Administrasjonssenter.Identifikasjon.VersjonID
    NULL_TREATMENT = Missing
    -> sentraldistrikter110 (writer GML_1)
sentraldistrikter110 (writer GML_1)
    attributes: Administrasjonssenter.Identifikasjon.Lokalid xml_buffer, Administrasjonssenter.Identifikasjon.Navnerom xml_buffer, Administrasjonssenter.Identifikasjon.VersjonID xml_char(2), Area xml_buffer, Koordh xml_buffer, Sentral xml_buffer, Lokalisering xml_buffer, Opphav xml_buffer, Kopidata.Områdeid xml_int64, Kopidata.Originaldatavert xml_buffer, Kopidata.Kopidato xml_char(20), Kvalitet.Målemetode xml_buffer, Kvalitet.Nøyaktighet xml_int64, Kvalitet.Synbarhet xml_buffer, Kvalitet.H-målemetode xml_buffer, Kvalitet.H-nøyaktighet xml_buffer, Kvalitet.Max-avvik xml_buffer, Objtype xml_buffer, Navn xml_buffer, Datafangstdato xml_char(20), avgrensesAv{}.xlink_href xml_char(8)

FME custom transformer CreateClipper

Parameters:
- CLIPPERCOORDS = 253577 6650999 253577 6651246 253763 6651246 253763 6650999 253577 6650999   # Clipper Coordinate List
- CLIPPERCOORDSYS = EPSG:25833   # Clipper Coordinate System
- DESTCOORDSYS = "ESRIWKT|ETRS_1989_UTM_Zone_35N|PROJCS["ETRS_1989_UTM_Zone_35N",GEOGCS["GCS_ETRS_1989",DATUM["D_ETRS_1989",SPHEROID["GRS_1980",6378137.0,298.257222101]],PRIMEM["Greenwich",0.0],UNIT["Degree",0.0174532925199433]],PROJECTION["Transverse_Mercator"],PARAMETER["False_Easting",500000.0],PARAMETER["False_Northing",0.0],PARAMETER["Central_Meridian",27.0],PARAMETER["Scale_Factor",0.9996],PARAMETER["Latitude_Of_Origin",0.0],UNIT["Meter",1.0]]"   # Destination Coordinate System

Note: Creating geometry from / the Clipper coords
Creator
    COORDS = $(CLIPPERCOORDS)
    GEOMTYPE = 2D Coordinate List
    COORDSYS = $(CLIPPERCOORDSYS)
    NUM = 1
    CREATED -> BoundingBoxAccumulator
Note: Calculating the bounding / box (envelope) from the geometry
BoundingBoxAccumulator
    TOPFER_INDEX = No
    BOUNDING_BOX -> SpatialFilter [input 1]
    ORIGINAL -> SpatialFilter [input 2]
Note: If the geometry is equal to its / own bounding box - it is a rectangle!
SpatialFilter
    PREDATTR = _predicate
    USE_BOUNDING_BOX = No
    PASS_CRITERIA = Pass Against One Base
    CURVE_BOUNDARY_RULE_PARAM = Default Rule
    MERGE_ATTRS = No
    BASE_TYPE = Single Base
    PREDICATES = EQUALS
    PASSED -> Reprojector
    FAILED -> Reprojector_2
Note: If rectangle, reproject the / geometry to the destination / coordinate system
Reprojector
    INTERPOLATION_TYPE_NAME = Nearest Neighbor
    SOURCE = Read from feature
    STROKE_ARCS = Yes
    DEST = $(DESTCOORDSYS)
    RASTER_CELL_SIZE = Preserve Cells
    REPROJECTED -> BoundingBoxAccumulator_2
Note: Then calculate the bounding / box from the projected geoemtry
BoundingBoxAccumulator_2
    TOPFER_INDEX = No
    BOUNDING_BOX -> Reprojector_3
Note: Reproject the geometry back to / the DB coordsys (LL/EUREF89)
Reprojector_3
    INTERPOLATION_TYPE_NAME = Nearest Neighbor
    SOURCE = Read from feature
    STROKE_ARCS = Yes
    DEST = EPSG:4258
    RASTER_CELL_SIZE = Preserve Cells
    REPROJECTED -> reprojectBboxESRI_REPROJECTED_2 (output)
Note: Reproject clipper to / the DB coordsys (LL/EUREF89)
Reprojector_2
    INTERPOLATION_TYPE_NAME = Nearest Neighbor
    SOURCE = Read from feature
    STROKE_ARCS = Yes
    DEST = EPSG:4258
    RASTER_CELL_SIZE = Preserve Cells
    REPROJECTED -> reprojectBboxESRI_REPROJECTED_2 (output)
reprojectBboxESRI_REPROJECTED_2 (output)
