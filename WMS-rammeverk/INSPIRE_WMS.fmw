FME workspace INSPIRE_WMS.fmw
Title: INSPIRE_WMS.fmw
Description: This WMS workspace reads from an INSPIRE staging PostGIS database and uses WFS to publish GML via the data streaming service, based on the query parameters provided by the WFS client. The Loader workspaces (INSPIRE_WFS_A1.CadastralParcels.Loader.fmw, INSPIRE_WFS_A1.GeoNames.Loader.fmw) handle data loading, reprojection and schema mapping to the databases 'INSPIRE like' data model. 
INSPIRE_WFS.fmw is a WFS 'service broker' workspace. This just needs to be published to the data streaming service and will accept WFS GET or POST requests (GetCapabilities, DescribeFeature and GetFeatrue) and generate the appropriate responses as XML or GML data streams (GetCapabilities, Describe feature XML docs or GML features). Supports XMLfilters which is something our built in WFS did not do. 
Also, configured to support FME Data Inspector as a WFS client. Note that 
this requires FME Server 2014 or later to function. This is required 
to support the new GML writer.
Requirements: FME 2014 14229+
History: 1/8/2014,Dean,Created / published

Parameters:
- SERVICE = WMS   # Service
- REQUEST = GetCapabilities   # Request
- VERSION = 1.1.1   # Version

Readers:
- TEXTLINE_1: TEXTLINE from .\GETrequest.txt

Writers:
- TEXTLINE_2: TEXTLINE to responseMessage.xml

text_line (reader TEXTLINE_1)
    attributes: text_line_data buffer
    -> ParameterFetcher
Note: Text File writer used for / web service message responses
text_line (writer TEXTLINE_2)
    attributes: text_line_data buffer

Bookmark: 1. Process GET Request
Note: Get URL parameters
ParameterFetcher
    ATTR_LIST = _VERSION {$(VERSION)} _REQUEST {$(REQUEST)} _SERVICE {$(SERVICE)}
    -> TestFilter
Note: Filter by request type
TestFilter
    TEST_LIST:
      BOOL_OP,AND,COMPOSITE_TEST,<Unused>,TEST_CLAUSE,"TEST @Value(_REQUEST) LIKE GetCapabilities
      TEST @Value(_SERVICE) LIKE WMS",GetCapabilities,BOOL_OP,OR,COMPOSITE_TEST,<Unused>,TEST_CLAUSE,"TEST @Value(_REQUEST) LIKE GetMap",GetMap
    DEFAULT_VALUE = <UNFILTERED>
    GetCapabilities -> AttributeFileReader
    GetMap -> Logger_GetMap
    <UNFILTERED> -> Logger_Unknown

Bookmark: 2. Generate GetCapabilities Response
Note: Read GetCapabilities.xml from file, the content / will be used in the GetCapabilities response
AttributeFileReader
    CHAR_ENCODING = utf-8
    FILE_NAME = GetCapabilities.xml
    DEST_ATTR = text_line_data
    -> text_line (writer TEXTLINE_2)

Bookmark: Error Handling
Note: Invalid GetMap request
Logger_GetMap
    MAXCOORDS = 20
    MESSAGE = ERROR Feature is:
    MAXFEATS = 20
    LOGGED -> XMLTemplater
Note: Unexpected input
Logger_Unknown
    MAXCOORDS = 20
    MESSAGE = Feature is:
    MAXFEATS = 20
    LOGGED -> XMLTemplater
Note: Generate Error Response
XMLTemplater
    RESULT_ATTRIBUTE = text_line_data
    VISIBLE_QUERY_VALIDATE = Yes
    OUTPUT_XML_HEADER = Yes
    ROOT_QUERY_EXPR:
      <error>
          <unexpectedInput>
              <warning>Unexpected Input Received from WFS client</warning>
              <request>{fme:get-attribute("_REQUEST")}</request>
              <service>{fme:get-attribute("_SERVICE")}</service>
              <version>{fme:get-attribute("_VERSION")}</version>
          </unexpectedInput>
      </error>
    -> text_line (writer TEXTLINE_2)
